-- ============================================================================
-- Copyright (C) 2010 by HUAWEI TECHNOLOGIES. All rights reserved.
-- Description: This is the MIB module for Huawei musa MD5500 private objects 
--              for service information.
-- Reference: 
-- Version: V1.19
-- ============================================================================
--  
-- Document description: HWMD5500PortAdmin module, MD5500 V100R001, Huawei 
-- Prepared by: Zeng Guibiao 24853
-- Created on: 2000/12/13 
-- Modified on: 2000/12/20
-- Modified by: Zeng Guibiao 24853 
-- 
-- 

    HWMUSA-UP-MIB DEFINITIONS ::= BEGIN
 
        IMPORTS
            hwProducts          
                FROM HUAWEI-MIB         
            OBJECT-TYPE, MODULE-IDENTITY,Integer32,NOTIFICATION-TYPE            
                FROM SNMPv2-SMI         
            RowStatus, TruthValue           
                FROM SNMPv2-TC;
    
        hwMD5500PortAdminMIB MODULE-IDENTITY 
                    LAST-UPDATED "201605191500Z"
                    ORGANIZATION "Huawei Technologies Co.,Ltd."
                    CONTACT-INFO                                        
                                 "Huawei Industrial Base                
                                  Bantian, Longgang                     
                                  Shenzhen 518129                       
                                  People's Republic of China            
                                  Website: http://www.huawei.com        
                                  Email: support@huawei.com             
                                 "                                      
                    DESCRIPTION 
                        "This is the MIB module for Huawei musa MD5500 
                        private objects for service information."

--  Revision history

					REVISION    "201605191500Z"
                    DESCRIPTION "V1.19, change in this revision:
                                -Modified the description of node: hwSysParaConfigSerialNum"
								
					REVISION    "201601131500Z"
                    DESCRIPTION "V1.18, change in this revision:
                                -Modified the description of node: hwSysParaConfigSerialNum"
								
                    REVISION    "201510271500Z"
                    DESCRIPTION "V1.17, change in this revision:
                                -Modified the description of node: hwSysParaConfigSerialNum" 
                                
                    REVISION    "201508131100Z"
                    DESCRIPTION "V1.16, change in this revision:
                                -Modified the description of node: hwSysParaConfigSerialNum " 
                                                                
                    REVISION    "201501231000Z"
                    DESCRIPTION "V1.15, change in this revision:
                                -added a new node: hwIsdnBraL1DegradeEndService"      
                                                          
                    REVISION    "201011172040Z"
                    DESCRIPTION "V1.14, change in this revision:
                                -Modified the description" 
                                 
                    REVISION    "201007270000Z"
                    DESCRIPTION "V1.13, change in this revision:
                                -Description change"              
                                    
                    REVISION    "201003240000Z"
                    DESCRIPTION "V1.12, change in this revision:
                                -Corrected the SYNTAX."
                    ::= { hwMd5500Mib 4 }
        

        musa OBJECT IDENTIFIER ::= { hwProducts 6 }
        

        hwMd5500Mib OBJECT IDENTIFIER ::= { musa 4 }
        

-- PSTN port MIB

        hwMD5500PSTNPort OBJECT IDENTIFIER ::= { hwMD5500PortAdminMIB 6 }
        

        hwMD5500PSTNPortPhyTable OBJECT-TYPE
            SYNTAX SEQUENCE OF HwMD5500PSTNPortPhyEntry
            MAX-ACCESS not-accessible
            STATUS current
            DESCRIPTION
                "
                The indexes of this table are hwMD5500PSTNPortFrameIndex, hwMD5500PSTNPortSlotIndex, 
                and hwMD5500PSTNPortIndex.
                "
            ::= { hwMD5500PSTNPort 1 }
        
        hwMD5500PSTNPortPhyEntry OBJECT-TYPE
            SYNTAX HwMD5500PSTNPortPhyEntry
            MAX-ACCESS not-accessible
            STATUS current
            DESCRIPTION
                " 
                The indexes of this entry are hwMD5500PSTNPortFrameIndex, hwMD5500PSTNPortSlotIndex, 
                and hwMD5500PSTNPortIndex.
                "
            INDEX { hwMD5500PSTNPortFrameIndex, hwMD5500PSTNPortSlotIndex, hwMD5500PSTNPortIndex }
            ::= { hwMD5500PSTNPortPhyTable 1 }
        
        HwMD5500PSTNPortPhyEntry ::=
            SEQUENCE { 
                hwMD5500PSTNPortFrameIndex
                    Integer32,
                hwMD5500PSTNPortSlotIndex
                    Integer32,
                hwMD5500PSTNPortIndex
                    Integer32,
                v5ID
                    Integer32,
                l3Addr
                    Integer32,
                v51Ts
                    Integer32,
                telNo
                    OCTET STRING,
                serviceType
                    INTEGER,
                pSTNState
                    INTEGER,
                fSMState
                    INTEGER,
                portState
                    INTEGER,
                operate
                    INTEGER,
                hwPSTNPortMaintainStatus
                    INTEGER,
                rowStatus
                    RowStatus
             }

        hwMD5500PSTNPortFrameIndex OBJECT-TYPE
            SYNTAX Integer32
            MAX-ACCESS not-accessible
            STATUS current
            DESCRIPTION
                " "
            ::= { hwMD5500PSTNPortPhyEntry 1 }
        
        hwMD5500PSTNPortSlotIndex OBJECT-TYPE
            SYNTAX Integer32
            MAX-ACCESS not-accessible
            STATUS current
            DESCRIPTION
                " "
            ::= { hwMD5500PSTNPortPhyEntry 2 }
        
        hwMD5500PSTNPortIndex OBJECT-TYPE
            SYNTAX Integer32
            MAX-ACCESS not-accessible
            STATUS current
            DESCRIPTION
                " "
            ::= { hwMD5500PSTNPortPhyEntry 3 }
        
        v5ID OBJECT-TYPE
            SYNTAX Integer32 (0..16777215)
            MAX-ACCESS read-write
            STATUS current
            DESCRIPTION
                " "
            ::= { hwMD5500PSTNPortPhyEntry 4 }
        
        l3Addr OBJECT-TYPE
            SYNTAX Integer32 (0..32767)
            MAX-ACCESS read-write
            STATUS current
            DESCRIPTION
                " "
            ::= { hwMD5500PSTNPortPhyEntry 5 }
        
        v51Ts OBJECT-TYPE
            SYNTAX Integer32 (1..15 | 17..31)
            MAX-ACCESS read-write
            STATUS current
            DESCRIPTION
                " "
            ::= { hwMD5500PSTNPortPhyEntry 6 }
        
        telNo OBJECT-TYPE
            SYNTAX OCTET STRING (SIZE (16))
            MAX-ACCESS read-write
            STATUS current
            DESCRIPTION
                " "
            ::= { hwMD5500PSTNPortPhyEntry 7 }
        
        serviceType OBJECT-TYPE
            SYNTAX INTEGER
                {
                currenser(1),
                insidespc(2),
                v5spc(3),
                v5preconn(4),
                hireline(5)
                }
            MAX-ACCESS read-only
            STATUS current
            DESCRIPTION
                "Options:
                 1.currenser(1)   -indicates the type is currenser    
                 2.insidespc(2)   -indicates the type is insidespc    
                 3.v5spc(3)       -indicates the type is v5spc        
                 4.v5preconn(4)   -indicates the type is v5preconn    
                 5.hireline(5)    -indicates the type is hireline     
                 "
            ::= { hwMD5500PSTNPortPhyEntry 8 }
        
        pSTNState OBJECT-TYPE
            SYNTAX INTEGER
                {
                ano(1),
                an1(2),
                an2(3),
                an3(4),
                an4(5),
                an5(6),
                an6(7),
                an7(8)
                }
            MAX-ACCESS read-only
            STATUS current
            DESCRIPTION
                "Options:
                 1.ano(1)   -indicates the state is ano
                 2.an1(2)   -indicates the state is an1
                 3.an2(3)   -indicates the state is an2
                 4.an3(4)   -indicates the state is an3
                 5.an4(5)   -indicates the state is an4
                 6.an5(6)   -indicates the state is an5
                 7.an6(7)   -indicates the state is an6
                 8.an7(8)   -indicates the state is an7
                 "
            ::= { hwMD5500PSTNPortPhyEntry 9 }
        
        fSMState OBJECT-TYPE
            SYNTAX INTEGER
                {
                an10(1),   
                an11(2),   
                an12(3),   
                an20(4),   
                an21(5),
                an22(6),
                an31(7),
                an32(8)
                }
            MAX-ACCESS read-only
            STATUS current
            DESCRIPTION
                "Options:
                 1.an10(1)  -indicates the state is an10
                 2.an11(2)  -indicates the state is an11
                 3.an12(3)  -indicates the state is an12
                 4.an20(4)  -indicates the state is an20
                 5.an21(5)  -indicates the state is an21
                 6.an22(6)  -indicates the state is an22
                 7.an31(7)  -indicates the state is an31
                 8.an32(8)  -indicates the state is an32
                "
            ::= { hwMD5500PSTNPortPhyEntry 10 }
        
        portState OBJECT-TYPE
            SYNTAX INTEGER
                {
                idle(1),
                fault(2),
                test(3),
                maintain(4),
                localblock(5),
                oppblock(6),
                lock(7),
                busy(8),
                viruser(9),
                farloop(10),
                nearloop(11),
                b1codetest(12),
                b2codetest(13)
                }
            MAX-ACCESS read-only
            STATUS current
            DESCRIPTION
                "Options:
                 1.idle(1)            -indicates the port state is idle
                 2.fault(2)           -indicates the port state is fault
                 3.test(3)            -indicates the port state is test
                 4.maintain(4)        -indicates the port state is maintain
                 5.localblock(5)      -indicates the port state is localblock
                 6.oppblock(6)        -indicates the port state is oppblock
                 7.lock(7)            -indicates the port state is lock
                 8.busy(8)            -indicates the port state is busy
                 9.viruser(9)         -indicates the port state is viruser
                 10.farloop(10)       -indicates the port state is farloop
                 11.nearloop(11)      -indicates the port state is nearloop
                 12.b1codetest(12)    -indicates the port state is b1codetest
                 13.b2codetest(13)    -indicates the port state is b2codetest
                "
            ::= { hwMD5500PSTNPortPhyEntry 11 }
        
        operate OBJECT-TYPE
            SYNTAX INTEGER
                {
                block(1),
                delayblock(2),
                unblock(3),
                reset(4),
                nearloop(5),
                unloop(6)
                }
            MAX-ACCESS read-write
            STATUS current
            DESCRIPTION
                "Options:
                 1.block(1)           -indicates the operation is block
                 2.delayblock(2)      -indicates the operation is delayblock
                 3.unblock(3)         -indicates the operation is unblock
                 4.reset(4)           -indicates the operation is reset
                 5.nearloop(5)        -indicates the operation is nearloop
                 6.unloop(6)          -indicates the operation is unloop
                "
            ::= { hwMD5500PSTNPortPhyEntry 12 }
        
        hwPSTNPortMaintainStatus OBJECT-TYPE
            SYNTAX INTEGER
                {
                mgcfged(1),
                v5cfged(2),
                notcfged(3),
                spcmcfged(4)
                }
            MAX-ACCESS read-only
            STATUS current
            DESCRIPTION
                "Options:
                 1. mgcfged(1)        -indicates the maintainstatus of the PSTN port is mgcfged
                 2. v5cfged(2)        -indicates the maintainstatus of the PSTN port is v5cfged
                 3. notcfged(3)       -indicates the maintainstatus of the PSTN port is notcfged
                 4. spcmcfged(4)      -indicates the maintainstatus of the PSTN port is spcmcfged
                "
            ::= { hwMD5500PSTNPortPhyEntry 13 }
        
        rowStatus OBJECT-TYPE
            SYNTAX RowStatus
            MAX-ACCESS read-write
            STATUS current
            DESCRIPTION
                "Indicates the row status."
            ::= { hwMD5500PSTNPortPhyEntry 14 }
        
        hwPstnV5PortDataTable OBJECT-TYPE
            SYNTAX SEQUENCE OF HwPstnV5PortDataEntry
            MAX-ACCESS not-accessible
            STATUS current
            DESCRIPTION
                "The indexes of this table are hwMD5500PSTNPortV5IDIndex and hwMD5500PSTNPortL3AddrIndex."
            ::= { hwMD5500PSTNPort 2 }
        
        hwPstnV5PortDataEntry OBJECT-TYPE
            SYNTAX HwPstnV5PortDataEntry
            MAX-ACCESS not-accessible
            STATUS current
            DESCRIPTION
                "The indexes of this entry are hwMD5500PSTNPortV5IDIndex and hwMD5500PSTNPortL3AddrIndex."
            INDEX { hwMD5500PSTNPortV5IDIndex, hwMD5500PSTNPortL3AddrIndex }
            ::= { hwPstnV5PortDataTable 1 }
        
        HwPstnV5PortDataEntry ::=
            SEQUENCE { 
                hwMD5500PSTNPortV5IDIndex
                    Integer32,
                hwMD5500PSTNPortL3AddrIndex
                    Integer32,
                hwMD5500PSTNPortFrame
                    Integer32,
                hwMD5500PSTNPortSlot
                    Integer32,
                hwMD5500PSTNPortNumber
                    Integer32,
                hwMD5500PSTNPortv51Ts
                    Integer32,
                hwMD5500PSTNPorttelNo
                    OCTET STRING,
                hwMD5500PSTNPortserviceType
                    INTEGER,
                hwMD5500PSTNPortpSTNState
                    INTEGER,
                hwMD5500PSTNPortfSMState
                    INTEGER,
                hwMD5500PSTNPortportState
                    INTEGER,
                hwMD5500PSTNPortoperate
                    INTEGER
             }

        hwMD5500PSTNPortV5IDIndex OBJECT-TYPE
            SYNTAX Integer32 (0..16777215)
            MAX-ACCESS not-accessible
            STATUS current
            DESCRIPTION
                " "
            ::= { hwPstnV5PortDataEntry 1 }
        
        hwMD5500PSTNPortL3AddrIndex OBJECT-TYPE
            SYNTAX Integer32 (0..32767)
            MAX-ACCESS not-accessible
            STATUS current
            DESCRIPTION
                " "
            ::= { hwPstnV5PortDataEntry 2 }
        
        hwMD5500PSTNPortFrame OBJECT-TYPE
            SYNTAX Integer32 (0..63)
            MAX-ACCESS read-only
            STATUS current
            DESCRIPTION
                " "
            ::= { hwPstnV5PortDataEntry 3 }
        
        hwMD5500PSTNPortSlot OBJECT-TYPE
            SYNTAX Integer32 (0..63)
            MAX-ACCESS read-only
            STATUS current
            DESCRIPTION
                " "
            ::= { hwPstnV5PortDataEntry 4 }
        
        hwMD5500PSTNPortNumber OBJECT-TYPE
            SYNTAX Integer32 (0..63)
            MAX-ACCESS read-only
            STATUS current
            DESCRIPTION
                " "
            ::= { hwPstnV5PortDataEntry 5 }
        
        hwMD5500PSTNPortv51Ts OBJECT-TYPE
            SYNTAX Integer32 (1..15 | 17..31)
            MAX-ACCESS read-only
            STATUS current
            DESCRIPTION
                " "
            ::= { hwPstnV5PortDataEntry 6 }
        
        hwMD5500PSTNPorttelNo OBJECT-TYPE
            SYNTAX OCTET STRING (SIZE (16))
            MAX-ACCESS read-only
            STATUS current
            DESCRIPTION
                " "
            ::= { hwPstnV5PortDataEntry 7 }
        
        hwMD5500PSTNPortserviceType OBJECT-TYPE
            SYNTAX INTEGER
                {
                currenser(1),
                insidespc(2),
                v5spc(3),
                v5preconn(4),
                hireline(5)
                }
            MAX-ACCESS read-only
            STATUS current
            DESCRIPTION
                "Options:
                 1.currenser(1)     -indicates the type is currenser 
                 2.insidespc(2)     -indicates the type is insidespc 
                 3.v5spc(3)         -indicates the type is v5spc     
                 4.v5preconn(4)     -indicates the type is v5preconn 
                 5.hireline(5)      -indicates the type is hireline  
                "
            ::= { hwPstnV5PortDataEntry 8 }
        
        hwMD5500PSTNPortpSTNState OBJECT-TYPE
            SYNTAX INTEGER
                {
                an0(1),
                an1(2),
                an2(3),
                an3(4),
                an4(5),
                an5(6),
                an6(7),
                an7(8)
                }
            MAX-ACCESS read-only
            STATUS current
            DESCRIPTION
                "Options:
                 1.an0(1)           -indicates the state is ano
                 2.an1(2)           -indicates the state is an1
                 3.an2(3)           -indicates the state is an2
                 4.an3(4)           -indicates the state is an3
                 5.an4(5)           -indicates the state is an4
                 6.an5(6)           -indicates the state is an5
                 7.an6(7)           -indicates the state is an6
                 8.an7(8)           -indicates the state is an7
                "
            ::= { hwPstnV5PortDataEntry 9 }
        
        hwMD5500PSTNPortfSMState OBJECT-TYPE
            SYNTAX INTEGER
                {
                an10(1),
                an11(2),
                an12(3),
                an20(4),
                an21(5),
                an22(6),
                an31(7),
                an32(8)
                }
            MAX-ACCESS read-only
            STATUS current
            DESCRIPTION
                "Options:
                 1.an10(1)           -indicates the state is an10 
                 2.an11(2)           -indicates the state is an11
                 3.an12(3)           -indicates the state is an12
                 4.an20(4)           -indicates the state is an20
                 5.an21(5)           -indicates the state is an21
                 6.an22(6)           -indicates the state is an22
                 7.an31(7)           -indicates the state is an31
                 8.an32(8)           -indicates the state is an32
                "
            ::= { hwPstnV5PortDataEntry 10 }
        
        hwMD5500PSTNPortportState OBJECT-TYPE
            SYNTAX INTEGER
                {
                idle(1),
                fault(2),
                test(3),
                maintain(4),
                localblock(5),
                oppblock(6),
                lock(7),
                busy(8),
                viruser(9),
                farloop(10),
                nearloop(11),
                b1codetest(12),
                b2codetest(13)
                }
            MAX-ACCESS read-only
            STATUS current
            DESCRIPTION
                "Options:
                 1.idle(1)                  -indicates the port state is idle      
                 2.fault(2)                 -indicates the port state is fault     
                 3.test(3)                  -indicates the port state is test      
                 4.maintain(4)              -indicates the port state is maintain  
                 5.localblock(5)            -indicates the port state is localblock
                 6.oppblock(6)              -indicates the port state is oppblock  
                 7.lock(7)                  -indicates the port state is lock      
                 8.busy(8)                  -indicates the port state is busy      
                 9.viruser(9)               -indicates the port state is viruser   
                 10.farloop(10)             -indicates the port state is farloop   
                 11.nearloop(11)            -indicates the port state is nearloop  
                 12.b1codetest(12)          -indicates the port state is b1codetest
                 13.b2codetest(13)          -indicates the port state is b2codetest
                "
            ::= { hwPstnV5PortDataEntry 11 }
        
        hwMD5500PSTNPortoperate OBJECT-TYPE
            SYNTAX INTEGER
                {
                block(1),
                delayblock(2),
                unblock(3),
                reset(4),
                nearloop(5),
                unloop(6)
                }
            MAX-ACCESS read-write
            STATUS current
            DESCRIPTION          
                "Options:
                 1.block(1)                -indicates the operation is block      
                 2.delayblock(2)           -indicates the operation is delayblock
                 3.unblock(3)              -indicates the operation is unblock   
                 4.reset(4)                -indicates the operation is reset     
                 5.nearloop(5)             -indicates the operation is nearloop  
                 6.unloop(6)               -indicates the operation is unloop    
                "
            ::= { hwPstnV5PortDataEntry 12 }
        
        hwPstnPortAttrTable OBJECT-TYPE
            SYNTAX SEQUENCE OF HwPstnPortAttrEntry
            MAX-ACCESS not-accessible
            STATUS current
            DESCRIPTION
                "The indexes of this table are hwMD5500PSTNPortFrameIndex, hwMD5500PSTNPortSlotIndex, 
                 and hwMD5500PSTNPortIndex."
            ::= { hwMD5500PSTNPort 3 }
        
        hwPstnPortAttrEntry OBJECT-TYPE
            SYNTAX HwPstnPortAttrEntry
            MAX-ACCESS not-accessible
            STATUS current
            DESCRIPTION
                "The indexes of this entry are hwMD5500PSTNPortFrameIndex, hwMD5500PSTNPortSlotIndex, 
                 and hwMD5500PSTNPortIndex."
            INDEX { hwMD5500PSTNPortFrameIndex, hwMD5500PSTNPortSlotIndex, hwMD5500PSTNPortIndex }
            ::= { hwPstnPortAttrTable 1 }
        
        HwPstnPortAttrEntry ::=
            SEQUENCE { 
                hwMD5500PSTNPortVoiceGain
                    INTEGER,
                hwMD5500PSTNPortAttribute0
                    INTEGER,
                hwMD5500PSTNPortAttribute1
                    INTEGER,
                hwMD5500PSTNPortRowStatus
                    RowStatus,
                hwMD5500PSTNPortReversePoleLevel
                    Integer32,
                hwMD5500PSTNPortLReversePoleEnable
                    INTEGER,
                hwMD5500PSTNPortUserType
                    INTEGER,
                hwMD5500PSTNPortImpedance
                    Integer32,
                hwMD5500PSTNPortCurrent
                    Integer32,
                hwMD5500PSTNPortDCTime
                    Integer32,
--The configuration interface is not provided currently, which may be added in the future. Therefore, the code is retained.
                --hwMD5500PSTNPortPITime
                    --INTEGER,
                hwMD5500PSTNPortFSKDelayInterval
                    Integer32,
                hwMD5500PSTNPortActualGain
                    Integer32,
                hwMD5500PSTNPortCidTransWhen
                    INTEGER,
                hwMD5500PSTNPortCidFormat
                    INTEGER,
                    --P300-YY-Start by Wang Baoxing 2006-8-18
                    hwMD5500PSTNPortCidReversePole
                    INTEGER,                    
                    --P300-YY-Start by Wang Baoxing 2006-8-18
                hwMD5500PSTNPortAGCEnableMarker
                    INTEGER,
                hwMD5500PSTNPortAGCEnableLevel
                    Integer32,
                hwMD5500PSTNPortSNSEnableMarker
                    INTEGER,
                hwMD5500PSTNPortSNSEnableLevel
                    Integer32,  
                                hwMD5500PSTNPortDspInputGain    
                    Integer32,  
                hwMD5500PSTNPortDspOutputGain
                    Integer32,  
                hwMD5500PSTNPortlinelock
                    INTEGER 
             }

        hwMD5500PSTNPortVoiceGain OBJECT-TYPE
            SYNTAX INTEGER
                {
                high(1),          
                low(2),           
                range1(3),        
                range2(4),        
                range3(5),        
                range4(6),        
                range5(7),        
                range6(8),        
                range7(9),        
                range8(10),       
                range9(11),       
                range10(12),      
                range11(13),      
                range12(14),      
                range13(15),      
                range14(16),      
                range15(17),      
                range16(18),      
                range17(19),      
                range18(20),          
                range19(21),      
                range20(22),      
                range21(23),      
                range22(24),      
                range23(25),      
                range24(26),      
                range25(27),      
                range26(28),      
                range27(29),      
                range28(30),      
                range29(31),      
                range29(32),      
                agc(255)          
                }
            MAX-ACCESS read-write
            STATUS current
            DESCRIPTION
                "Options:
                 1.high(1)            -indicates the VoiceGain of the PSTN port is high   
                 2.low(2)             -indicates the VoiceGain of the PSTN port is low    
                 3.range1(3)          -indicates the VoiceGain of the PSTN port is range1 
                 4.range2(4)          -indicates the VoiceGain of the PSTN port is range2 
                 5.range3(5)          -indicates the VoiceGain of the PSTN port is range3 
                 6.range4(6)          -indicates the VoiceGain of the PSTN port is range4 
                 7.range5(7)          -indicates the VoiceGain of the PSTN port is range5 
                 8.range6(8)          -indicates the VoiceGain of the PSTN port is range6 
                 9.range7(9)          -indicates the VoiceGain of the PSTN port is range7 
                 10.range8(10)        -indicates the VoiceGain of the PSTN port is range8 
                 11.range9(11)        -indicates the VoiceGain of the PSTN port is range9 
                 12.range10(12)       -indicates the VoiceGain of the PSTN port is range10
                 13.range11(13)       -indicates the VoiceGain of the PSTN port is range11
                 14.range12(14)       -indicates the VoiceGain of the PSTN port is range12
                 15.range13(15)       -indicates the VoiceGain of the PSTN port is range13
                 16.range14(16)       -indicates the VoiceGain of the PSTN port is range14
                 17.range15(17)       -indicates the VoiceGain of the PSTN port is range15
                 18.range16(18)       -indicates the VoiceGain of the PSTN port is range16
                 19.range17(19)       -indicates the VoiceGain of the PSTN port is range17
                 20.range18(20)       -indicates the VoiceGain of the PSTN port is range18
                 21.range19(21)       -indicates the VoiceGain of the PSTN port is range19
                 22.range20(22)       -indicates the VoiceGain of the PSTN port is range20
                 23.range21(23)       -indicates the VoiceGain of the PSTN port is range21
                 24.range22(24)       -indicates the VoiceGain of the PSTN port is range22
                 25.range23(25)       -indicates the VoiceGain of the PSTN port is range23
                 26.range24(26)       -indicates the VoiceGain of the PSTN port is range24
                 27.range25(27)       -indicates the VoiceGain of the PSTN port is range25
                 28.range26(28)       -indicates the VoiceGain of the PSTN port is range26
                 29.range27(29)       -indicates the VoiceGain of the PSTN port is range27
                 30.range28(30)       -indicates the VoiceGain of the PSTN port is range28
                 31.range29(31)       -indicates the VoiceGain of the PSTN port is range29
                 32.range29(32)       -indicates the VoiceGain of the PSTN port is range30
                 33.agc(255)          -indicates the VoiceGain of the PSTN port is agc    
               "                      
            DEFVAL { 1 }
            ::= { hwPstnPortAttrEntry 1 }
        
        hwMD5500PSTNPortAttribute0 OBJECT-TYPE
            SYNTAX INTEGER
                {
                nolimt(1),
                limt(2),                
                mode-DTMF-pulse-dial(3),
                mode-DTMF-dial-only(4),
                mode-pulse-dial-only(5)
                }
            MAX-ACCESS read-write
            STATUS current
            DESCRIPTION
                "Options:
                 1.nolimt(1)                  -indicates the attribute of the PSTN port is nolimt
                 2.limt(2)                    -indicates the attribute of the PSTN port is limt
                 3.mode-DTMF-pulse-dial(3)    -indicates the dial mode are both pulse and DTMF        
                 4.mode-DTMF-dial-only(4)     -indicates the dial mode is only DTMF           
                 5.mode-pulse-dial-only(5)    -indicates the dial mode is only pulse          
                "
            ::= { hwPstnPortAttrEntry 2 }
        
        hwMD5500PSTNPortAttribute1 OBJECT-TYPE
            SYNTAX INTEGER
                {
                notsupport(1),
                support(2)
                }
            MAX-ACCESS read-write
            STATUS current
            DESCRIPTION
                "Options:
                 1.notsupport(1)              -indicates the attribute of the PSTN port is not supported
                 2.support(2)                 -indicates the attribute of the PSTN port is supported
                "
            ::= { hwPstnPortAttrEntry 3 }
        
        hwMD5500PSTNPortRowStatus OBJECT-TYPE
            SYNTAX RowStatus
            MAX-ACCESS read-write
            STATUS current
            DESCRIPTION
                " indicates the row status."
            ::= { hwPstnPortAttrEntry 4 }
                    
        hwMD5500PSTNPortReversePoleLevel OBJECT-TYPE
            SYNTAX Integer32 (20..2560)
            MAX-ACCESS read-write
            STATUS current
            DESCRIPTION
                " indicates the reverse pole level of the PSTN port of md5500"
            ::= { hwPstnPortAttrEntry 5 }
        
        
        hwMD5500PSTNPortLReversePoleEnable OBJECT-TYPE
            SYNTAX INTEGER
                {
                reversePoleDisable(1),
                reversePoleEnable(2)
                }
            MAX-ACCESS read-write
            STATUS current
            DESCRIPTION
                "Options:
                 1.reversePoleDisable(1)      -indicates the reverse pole level of the port is disable
                 2.reversePoleEnable(2)       -indicates the reverse pole level of the port is enbale
                "
            ::= { hwPstnPortAttrEntry 6 }

        hwMD5500PSTNPortUserType OBJECT-TYPE
            SYNTAX INTEGER
                {
                del(1),
                lcpbx(2),
                ecpbx(3),
                payphone(4)
                }
            MAX-ACCESS read-write
            STATUS current
            DESCRIPTION
                "Options:
                 1.del(1)       -indicates the del user
                 2.lcpbx(2)     -indicates the loop calling PBX
                 3.ecpbx(3)     -indicates the earth calling PBX
                 4.payphone(4)  -indicates the payphone"
            DEFVAL { 1 }
            ::= { hwPstnPortAttrEntry 7 }
        
        hwMD5500PSTNPortImpedance OBJECT-TYPE
               --P300-YY-Start by Wang Baoxing 2006-8-18
            SYNTAX Integer32 (1..15 )
               --P300-YY-End by Wang Baoxing 2006-8-18
            MAX-ACCESS read-write
            STATUS current
            DESCRIPTION
                "
                Port impedance of the port. The following values indicate different impedances in 
                different application circumstances.
                1    --    Bureau machine in China (200+680|| 100nf)
                2    --    User machine in China (200+560|| 100nf)
                3    --    600 ohm interface
                4    --    Interface of Russia (150+510|| 47nf)
                5    --    (220+820|| 115nf )
                6    --    (220+820|| 120nf )
                7    --    900 ohm interface
                8    --    Interface of Brazil (800|| 50nf)
                9    --    BT0 (Zin=87+1052||228nF+229||28.4nF, Zload=93+615||471nF+179||495nF+244||32nF)
                10   --    HK_BT3 (Zin=370+620|| 310nf,Zload=600)
                11   --    HK_BT5 (Zin=270+264|| 357nf+1434|| 265nf,Zload=600)
                12   --    BT1 (BT0 without AGC)
                13   --    BT2 (Zin=(87 +1052 //228nF+229 //28.4nF),Zload=(270 +264 //357nF+1434 //265nF))
                14   --    BT3 (Zin=(87 +1052 //228nF+229 //28.4nF),Zload=(164 +162 //363nF+1227 //350nF))
                   --P300-YY-Start by Wang Baoxing 2006-8-18
                15   --    KPN (Zin= 270+750|| 150nf)
                   --P300-YY-End by Wang Baoxing 2006-8-18
                
                
                The impedance values of the ports on the board are as follows. Different values correspond to the requirements for the impedance in different application scenarios.
                1 -- Bureau device in China (200+680 || 100 nf)
                2 -- China subscriber device (200+560 || 100 nf)
                3 -- 600 ohm interface
                4 -- Interface in Russia (150+510 || 47 nf)
                5 -- (220+820 || 115 nf)
                6 -- (220+820 || 120 nf)
                7 -- 900 ohm interface
                8 -- Interface in Brazil (800 || 50 nf)
                9 -- BT0 (Zin=87+1052||228nF+229||28.4nF, Zload=93+615||471nF+179||495nF+244||32nF)
                10 -- HK_BT3 (Zin=370+620|| 310nf,Zload=600)
                11 -- HK_BT5 (Zin=270+264|| 357nf+1434|| 265nf,Zload=600)
                12 -- BT1 (BT0 without AGC)
                13 -- BT2 (Zin=(87+1052 //228nF+229 //28.4nF),Zload=(270+264 //357nF+1434 //265nF))
                14 -- BT3 (Zin=(87 +1052 //228nF+229 //28.4nF),Zload=(164 +162 //363nF+1227 //350nF))
                          --P300-YY-Start by Wang Baoxing 2006-8-18
                15 -- KPN(Zin= 270+750|| 150nf)
                          --P300-YY-End by Wang Baoxing 2006-8-18
                "
            DEFVAL { 3 }
            ::= { hwPstnPortAttrEntry 8 }
        
        hwMD5500PSTNPortCurrent OBJECT-TYPE
            SYNTAX Integer32 (1..19)
            MAX-ACCESS read-write
            STATUS current
            DESCRIPTION
                "
                Port current supported by the board. The value ranges from 1 to 17, 
                which indicates the port current value supported under certain loopline impedance.
                1    --    25mA steady current
                2    --    16mA steady current
                3    --    32mA steady current
                4    --    40mA steady current
                5    --    35mA 2*200 ohm
                6    --    35mA 2*250 ohm
                7    --    35mA 2*400 ohm
                8    --    47mA 2*200 ohm
                9    --    47mA 2*250 ohm
                10   --    47mA 2*400 ohm
                11   --    20mA 2*200 ohm
                12   --    20mA 2*250 ohm
                13   --    20mA 2*400 ohm
                14   --    30mA 2*200 ohm
                15   --    30mA 2*250 ohm
                16   --    30mA 2*400 ohm
                17   --    40mA 2*200 ohm
                18   --    40mA 2*250 ohm
                19   --    40mA 2*400 ohm
                
                The current values of the ports on the board are as follows.
                The following values indicate the current values for different loop resistances of loop lines (for example 2*400 ?). 
                1 -- 25mA constant current
                2 -- 16mA constant current
                3 -- 32mA constant current
                4 -- 40mA constant current
                5 -- 35mA 2*200 ohm
                6 -- 35mA 2*250 ohm
                7 -- 35mA 2*400 ohm
                8 -- 47mA 2*200 ohm
                9 -- 47mA 2*250 ohm
                10 -- 47mA 2*400 ohm
                11 -- 20mA 2*200 ohm
                12 -- 20mA 2*250 ohm
                13 -- 20mA 2*400 ohm
                14 -- 30mA 2*200 ohm
                15 -- 30mA 2*250 ohm
                16 -- 30mA 2*400 ohm
                17 -- 40mA 2*200 ohm
                18 -- 40mA 2*250 ohm
                19 -- 40mA 2*400 ohm
                                        "
            DEFVAL { 1 }
            ::= { hwPstnPortAttrEntry 9 }
            
        hwMD5500PSTNPortDCTime OBJECT-TYPE
            SYNTAX Integer32 (1..100)
            MAX-ACCESS read-write
            STATUS current
            DESCRIPTION
                "Disconnect clear time (*10 ms)."
            DEFVAL { 10 }
            ::= { hwPstnPortAttrEntry 10 }

-- The configuration interface is not provided currently, which may be added in the future. Therefore, the code is retained.            
--      hwMD5500PSTNPortPITime OBJECT-TYPE
--          SYNTAX Integer32 (0..20)
--          MAX-ACCESS read-write
--          STATUS current
--          DESCRIPTION
--              "Proceed indication time (*10 ms)."
--          DEFVAL { 16 }
--          ::= { hwPstnPortAttrEntry 11 }
        
        hwMD5500PSTNPortFSKDelayInterval OBJECT-TYPE
                SYNTAX      Integer32(0..100)
                MAX-ACCESS  read-write
                STATUS      current
                DESCRIPTION
                        "Time length of the delay for transmitting the FSK calling number (unit: 10 ms)."
                DEFVAL { 80 }
                ::= { hwPstnPortAttrEntry 12 }
        
        hwMD5500PSTNPortActualGain OBJECT-TYPE
            SYNTAX Integer32(0..255)
            MAX-ACCESS read-only
            STATUS current
            DESCRIPTION
                "Port actual gain."
            ::= { hwPstnPortAttrEntry 13 }
            
        hwMD5500PSTNPortCidTransWhen OBJECT-TYPE
            SYNTAX INTEGER
                {
                after-ring(1),
                before-ring(2)
                }
            MAX-ACCESS read-write
            STATUS current
            DESCRIPTION
                "Options:
                 1.after-ring(1)    -After ringing
                 2.before-ring(2)   -Before ringing
                 "
            DEFVAL { 1 }
            ::= { hwPstnPortAttrEntry 14 }
            
        hwMD5500PSTNPortCidFormat OBJECT-TYPE
            SYNTAX INTEGER
                {
                sdmf-fsk(1),
                mdmf-fsk(2),
                dtmf(3),
                r15(4)
                }
            MAX-ACCESS read-write
            STATUS current
            DESCRIPTION
                "Options:
                 1.sdmf-fsk(1)    -sdmf (FSK simple data message format)
                 2.mdmf-fsk(2)    -mdmf (FSK multi-data message format)
                 3.dtmf(3)        -dtmf (DTMF format)
                 4.r15(4)         -R1.5
                 "
            DEFVAL { 1 }
            ::= { hwPstnPortAttrEntry 15 }

            --P300-YY-Start by Wang Baoxing 2006-8-18
        hwMD5500PSTNPortCidReversePole OBJECT-TYPE
            SYNTAX INTEGER
                {
                notsend(1),
                send(2)
                }
            MAX-ACCESS read-write
            STATUS current
            DESCRIPTION
                "The polarity reversal is sent before the calling number is transmitted.
                 Options:
                 1.notsend(1)-not send
                 2.send(2)-send
                "
            DEFVAL { 1 }
            ::= { hwPstnPortAttrEntry 16 }          
                         --P300-YY-End by Wang Baoxing 2006-8-18
        hwMD5500PSTNPortAGCEnableMarker OBJECT-TYPE
            SYNTAX INTEGER
                {
                agcDisable(1),
                agcEnable(2)
                }
            MAX-ACCESS read-write
            STATUS current
            DESCRIPTION
                "Options:
                 1.agcDisable(1)      -Disable the auto gain control
                 2.agcEnable(2)       -Enable  the auto gain control
                 "
            ::= { hwPstnPortAttrEntry 17 }
            
        hwMD5500PSTNPortAGCEnableLevel OBJECT-TYPE
            SYNTAX Integer32 (0..15)
            MAX-ACCESS read-write
            STATUS current
            DESCRIPTION
                "Automatic gain control parameter setting. 
                0-15 maps -9 dbm0 to -24 dbm0.
                The default value is 13.
                 "
            ::= { hwPstnPortAttrEntry 18 }
        
        hwMD5500PSTNPortSNSEnableMarker OBJECT-TYPE
            SYNTAX INTEGER
                {
                snsDisable(1),
                snsEnable(2)
                }
            MAX-ACCESS read-write
            STATUS current
            DESCRIPTION
                "Options:
                 1.snsDisable(1)  -Disable
                 2.snsEnable(2)   -Enable
                 "
            ::= { hwPstnPortAttrEntry 19 }
    
        hwMD5500PSTNPortSNSEnableLevel OBJECT-TYPE
            SYNTAX Integer32 (6..20)
            MAX-ACCESS read-write
            STATUS current
            DESCRIPTION
                "Spectral noise suppression parameter setting (6 db-20 db).
                The default value is 12 db.
                "
            ::= { hwPstnPortAttrEntry 20 }
            
        hwMD5500PSTNPortDspInputGain OBJECT-TYPE
            SYNTAX Integer32 (1..16)
            MAX-ACCESS read-write
            STATUS current
            DESCRIPTION
                "DSP input gain of PSTN port parameter setting (PCM->IP, 1-16 correspond to -10 db to +5 db).
                The default value is 11.
                "
            ::= { hwPstnPortAttrEntry 21 }
            
        hwMD5500PSTNPortDspOutputGain OBJECT-TYPE
            SYNTAX Integer32 (1..21)
            MAX-ACCESS read-write
            STATUS current
            DESCRIPTION
                "DSP output gain of PSTN port parameter setting (IP->PCM, 1-21 correspond to -10 db to +10 db).
                The default value is 11.
                "
            ::= { hwPstnPortAttrEntry 22 }
            
        hwMD5500PSTNPortlinelock OBJECT-TYPE
            SYNTAX INTEGER 
                {
                disable(1),
                enable(2)
                }
            MAX-ACCESS read-write
            STATUS current
            DESCRIPTION
                "Whether the port can be locked or not. 1. cannot be locked; 2. can be locked.
                 Options:
                 1.disable(1)   -disable
                 2.enable(2)    -enable 
                "
            DEFVAL { {enable(2)} }
            ::= { hwPstnPortAttrEntry 23 }
        
        hwPstn16KCAttrTable OBJECT-TYPE
            SYNTAX SEQUENCE OF HwPstn16KCAttrEntry
            MAX-ACCESS not-accessible
            STATUS current
            DESCRIPTION
                "The indexes of this table are hwMD5500PSTNPortFrameIndex, hwMD5500PSTNPortSlotIndex, 
                 and hwMD5500PSTNPortIndex."
            ::= { hwMD5500PSTNPort 5 }
        
        hwPstn16KCAttrEntry OBJECT-TYPE
            SYNTAX HwPstn16KCAttrEntry
            MAX-ACCESS not-accessible
            STATUS current
            DESCRIPTION
                "The indexes of this entry are hwMD5500PSTNPortFrameIndex, hwMD5500PSTNPortSlotIndex, 
                 and hwMD5500PSTNPortIndex."
            INDEX { hwMD5500PSTNPortFrameIndex, hwMD5500PSTNPortSlotIndex, hwMD5500PSTNPortIndex }
            ::= { hwPstn16KCAttrTable 1 }
        
        HwPstn16KCAttrEntry ::=
            SEQUENCE { 
                hwMD5500PSTNPortHighLevel
                    Integer32,
                hwMD5500PSTNPortLowLevel
                    Integer32,
                hwMD5500PSTNPortKCType
                    INTEGER,
                hwMD5500PSTNPortVoltage
                    INTEGER,
                hwMD5500PSTNPortKCRowStatus
                    RowStatus
             }

        hwMD5500PSTNPortHighLevel OBJECT-TYPE
            SYNTAX Integer32 (20..500)
            MAX-ACCESS read-write
            STATUS current
            DESCRIPTION
                " "
            ::= { hwPstn16KCAttrEntry 1 }
        
        hwMD5500PSTNPortLowLevel OBJECT-TYPE
            SYNTAX Integer32 (20..500)
            MAX-ACCESS read-write
            STATUS current
            DESCRIPTION
                " "
            ::= { hwPstn16KCAttrEntry 2 }
        
        hwMD5500PSTNPortKCType OBJECT-TYPE
            SYNTAX INTEGER
                {
                port1216kcselector16kc(1),
                port1216kcselector12kc(2)
                }
            MAX-ACCESS read-write
            STATUS current
            DESCRIPTION
                "Options:
                 1.port1216kcselector16kc(1)   -indicates the Kc type is 16kc
                 2.port1216kcselector12kc(2)   -indicates the Kc type is 12kc
                "
            ::= { hwPstn16KCAttrEntry 3 }
        
        hwMD5500PSTNPortVoltage OBJECT-TYPE
            SYNTAX INTEGER
                {
                port1216kcvalidvoltage0(1),
                port1216kcvalidvoltage1(2),
                port1216kcvalidvoltage2(3),
                port1216kcvalidvoltage3(4),
                port1216kcvalidvoltage4(5),
                port1216kcvalidvoltage5(6),
                port1216kcvalidvoltage6(7),
                port1216kcvalidvoltage7(8),
                port1216kcvalidvoltage8(9),
                port1216kcvalidvoltage9(10)
                }
            MAX-ACCESS read-write
            STATUS current
            DESCRIPTION
                "Options:
                 1.port1216kcvalidvoltage0(1)     -indicates the validvoltage value
                 2.port1216kcvalidvoltage1(2)     -indicates the validvoltage value
                 3.port1216kcvalidvoltage2(3)     -indicates the validvoltage value
                 4.port1216kcvalidvoltage3(4)     -indicates the validvoltage value
                 5.port1216kcvalidvoltage4(5)     -indicates the validvoltage value
                 6.port1216kcvalidvoltage5(6)     -indicates the validvoltage value
                 7.port1216kcvalidvoltage6(7)     -indicates the validvoltage value
                 8.port1216kcvalidvoltage7(8)     -indicates the validvoltage value
                 9.port1216kcvalidvoltage8(9)     -indicates the validvoltage value
                 10.port1216kcvalidvoltage9(10)   -indicates the validvoltage value
                "
            ::= { hwPstn16KCAttrEntry 4 }
        
        hwMD5500PSTNPortKCRowStatus OBJECT-TYPE
            SYNTAX RowStatus
            MAX-ACCESS read-write
            STATUS current
            DESCRIPTION
                " indicates the the row status."
            ::= { hwPstn16KCAttrEntry 5 }
        
-- Description of virtual user on the V5 port
        hwV5VirPortDesTable OBJECT-TYPE
            SYNTAX SEQUENCE OF HwV5VirPortDesEntry
            MAX-ACCESS not-accessible
            STATUS current
            DESCRIPTION
                "The indexes of this table are hwMD5500VirtualuserLEID, hwMD5500VirtualuserAdrrType, 
                 and hwMD5500VirtualAddress."
            ::= { hwMD5500PSTNPort 6 }
        
        hwV5VirPortDesEntry OBJECT-TYPE
            SYNTAX HwV5VirPortDesEntry
            MAX-ACCESS not-accessible
            STATUS current
            DESCRIPTION
                "The indexes of this entry are hwMD5500VirtualuserLEID, hwMD5500VirtualuserAdrrType, 
                 and hwMD5500VirtualAddress."
            INDEX { hwMD5500VirtualuserLEID, hwMD5500VirtualuserAdrrType, hwMD5500VirtualAddress }
            ::= { hwV5VirPortDesTable 1 }
        
        HwV5VirPortDesEntry ::=
            SEQUENCE { 
                hwMD5500VirtualuserLEID
                    Integer32,
                hwMD5500VirtualuserAdrrType
                    INTEGER,
                hwMD5500VirtualAddress
                    Integer32,
                hwMD5500VirtualPortType
                    INTEGER,
                hwMD5500VirtualPortGroup
                    Integer32,
                hwMD5500VirtualRowStatus
                    RowStatus
             }

        hwMD5500VirtualuserLEID OBJECT-TYPE
            SYNTAX Integer32 (0..16777215)
            MAX-ACCESS not-accessible
            STATUS current
            DESCRIPTION
                "
                LEV5 interface ID "
            ::= { hwV5VirPortDesEntry 1 }
        
        hwMD5500VirtualuserAdrrType OBJECT-TYPE
            SYNTAX INTEGER
                {
                l3address(1),
                efaddress(2)
                }
            MAX-ACCESS not-accessible
            STATUS current
            DESCRIPTION
                "Options:
                 1.l3address(1)       -indicates the addr type is l3
                 2.efaddress(2)       -indicates the addr type is efa
                "
            ::= { hwV5VirPortDesEntry 2 }
        
        hwMD5500VirtualAddress OBJECT-TYPE
            SYNTAX Integer32 (0..32767)
            MAX-ACCESS not-accessible
            STATUS current
            DESCRIPTION
                "
                Address "
            ::= { hwV5VirPortDesEntry 3 }
        
        hwMD5500VirtualPortType OBJECT-TYPE
            SYNTAX INTEGER
                {
                pstnPort(1),
                braPort(2),
                praPort(3)
                }
            MAX-ACCESS read-write
            STATUS current
            DESCRIPTION
                "Options:
                 1.pstnPort(1)         -indicates the port type is pstnPort
                 2.braPort(2)          -indicates the port type is braPort
                 3.praPort(3)          -indicates the port type is praPort
                "
            ::= { hwV5VirPortDesEntry 4 }
        
        hwMD5500VirtualPortGroup OBJECT-TYPE
            SYNTAX Integer32 (0..254)
            MAX-ACCESS read-write
            STATUS current
            DESCRIPTION
                "
                Port group number."
            ::= { hwV5VirPortDesEntry 5 }
        
        hwMD5500VirtualRowStatus OBJECT-TYPE
            SYNTAX RowStatus
            MAX-ACCESS read-write
            STATUS current
            DESCRIPTION
                "
                Row status."
            ::= { hwV5VirPortDesEntry 6 }
-- System parameter configuration table             
        hwSysParaConfigTable OBJECT-TYPE
            SYNTAX SEQUENCE OF HwSysParaConfigEntry
            MAX-ACCESS not-accessible
            STATUS current
            DESCRIPTION
                "System parameter configuration table. 
                The index of this table is hwSysParaConfigSerialNum."
            ::= { hwMD5500PSTNPort 7 }
        
        hwSysParaConfigEntry OBJECT-TYPE
            SYNTAX HwSysParaConfigEntry
            MAX-ACCESS not-accessible
            STATUS current
            DESCRIPTION
                "System parameter configuration table. 
                The index of this entry is hwSysParaConfigSerialNum."
            INDEX { hwSysParaConfigSerialNum }
            ::= { hwSysParaConfigTable 1 }
        
        HwSysParaConfigEntry ::=
            SEQUENCE { 
                hwSysParaConfigSerialNum
                    Integer32,
                hwSysParaValue
                    Integer32
             }

        hwSysParaConfigSerialNum OBJECT-TYPE
            SYNTAX Integer32 (0..255)
            MAX-ACCESS not-accessible
            STATUS current
            DESCRIPTION
                "System parameter ID.
                Options:
                0. Sending howler tone flag
                1. Overseas version flag
                9. Stop initial ringing flag
                24. The mode of voicemail
                35. Global digitmap support flag
                39. Transfer mode of media stream in a device
                40. Howler tone source
                44. QOS alarm number
                48. Take the initiative to establish PRA Q.921 link flag
                49. Report TEI status indication flag
                50. Report touching power line alarm flag
                51. The mode for sending 2833 packets
                52. EC mode 
                53. Processing mode in the basic mode of a loop line test
                54. Indicates whether the ISDN Layer2 link status alarms will be reported
                55. Indicates whether the alarm indication signal (AIS) will be sent to the peer end after all the B channels of the PRA port are disabled
                56. Indicates the voltage adjustment factor for an on-hook PSTN port
                57..255. Reserved"
            ::= { hwSysParaConfigEntry 1 }
           
           hwSysParaValue OBJECT-TYPE
            SYNTAX Integer32 (0..65535)
            MAX-ACCESS read-write
            STATUS current
            DESCRIPTION
                "
                System parameter value."
            ::= { hwSysParaConfigEntry 2 }
    
-- Overseas parameter configuration table               
        hwOverSeaConfigTable OBJECT-TYPE
            SYNTAX SEQUENCE OF HwOverSeaConfigEntry
            MAX-ACCESS not-accessible
            STATUS current
            DESCRIPTION
                "
                Find and configure the oversea parameters according to the hwOverSeaConfigSerialNum.
                The index of this table is hwOverSeaConfigSerialNum."
            ::= { hwMD5500PSTNPort 8 }
        
        hwOverSeaConfigEntry OBJECT-TYPE
            SYNTAX HwOverSeaConfigEntry
            MAX-ACCESS not-accessible
            STATUS current
            DESCRIPTION
                "
                Find and configure the oversea parameters according to the hwOverSeaConfigSerialNum.
                The index of this entry is hwOverSeaConfigSerialNum."
            INDEX { hwOverSeaConfigSerialNum }
            ::= { hwOverSeaConfigTable 1 }
        
        HwOverSeaConfigEntry ::=
            SEQUENCE { 
                hwOverSeaConfigSerialNum
                    Integer32,
                hwOverSeaValue
                    Integer32
             }

        hwOverSeaConfigSerialNum OBJECT-TYPE
            SYNTAX Integer32 (0..255)
            MAX-ACCESS not-accessible
            STATUS current
            DESCRIPTION
                "Overseas parameter ID.
                Options:
                3. hwOverSeaValue
                4. Hooking lower threshold
                5. Flag of changing TEI value for software switch
                37. Flag of applying PARKED LINE FEED or not when user port is locked
                38. The detect time of flash upper limit to onhook
                53. DTMF Detector Tuning
                54..255. Reserved parameter"
            ::= { hwOverSeaConfigEntry 1 }
           
        hwOverSeaValue OBJECT-TYPE
            SYNTAX Integer32 (0..65535)
            MAX-ACCESS read-write
            STATUS current
            DESCRIPTION
                "
                Oversea parameter value."
            ::= { hwOverSeaConfigEntry 2 }      
            
    hwPortGlobalAttrTable OBJECT IDENTIFIER ::= { hwMD5500PSTNPort  9}
    
    hwPortGlobalAttrTANSON OBJECT-TYPE
    SYNTAX Integer32 (1..4)
    MAX-ACCESS  read-write
    STATUS      current
    DESCRIPTION
        " 
        Sets the eliminating jitter time during the PSTN port on-hook signaling state.
        1 -- 50ms
        2 -- 100ms
        3 -- 150ms
        4 -- 200ms
        "
    ::= { hwPortGlobalAttrTable 1 } 
    
    hwPortGlobalAttrTANSOFF OBJECT-TYPE
    SYNTAX Integer32 (15..20)
    MAX-ACCESS  read-write
    STATUS      current
    DESCRIPTION
        " 
        Sets the eliminating jitter time during the PSTN port off-hook state.
        15 -- 150ms
        16 -- 160ms
        17 -- 170ms
        18 -- 180ms
        19 -- 190ms
        20 -- 200ms
        "
    ::= { hwPortGlobalAttrTable 2 } 
    
    
        hwMD5500BRAPort OBJECT IDENTIFIER ::= { hwMD5500PortAdminMIB 7 }
        
-- Data table of the BRA port
        hwIsdnPhyPortDataTable OBJECT-TYPE
            SYNTAX SEQUENCE OF HwIsdnPhyPortDataEntry
            MAX-ACCESS not-accessible
            STATUS current
            DESCRIPTION
                "The indexes of this table are hwMD5500BRAPortFrameIndex, hwMD5500BRAPortSlotIndex, 
                 and hwMD5500BRAPortIndex."
            ::= { hwMD5500BRAPort 1 }
        
        hwIsdnPhyPortDataEntry OBJECT-TYPE
            SYNTAX HwIsdnPhyPortDataEntry
            MAX-ACCESS not-accessible
            STATUS current
            DESCRIPTION
                "The indexes of this entry are hwMD5500BRAPortFrameIndex, hwMD5500BRAPortSlotIndex, 
                 and hwMD5500BRAPortIndex."
            INDEX { hwMD5500BRAPortFrameIndex, hwMD5500BRAPortSlotIndex, hwMD5500BRAPortIndex }
            ::= { hwIsdnPhyPortDataTable 1 }
        
        HwIsdnPhyPortDataEntry ::=
            SEQUENCE { 
                hwMD5500BRAPortFrameIndex
                    Integer32,
                hwMD5500BRAPortSlotIndex
                    Integer32,
                hwMD5500BRAPortIndex
                    Integer32,
                hwMD5500BRAPortV5ID
                    Integer32,
                hwMD5500BRAPortGrpNo
                    Integer32,
                hwMD5500BRAEfAddr
                    Integer32,
                hwMD5500BRAV51Ts1
                    Integer32,
                hwMD5500BRAV51Ts2
                    Integer32,
                hwMD5500BRATelNo
                    OCTET STRING,
                hwMD5500BRAServiceType
                    INTEGER,
                hwMD5500BRAFSMState
                    INTEGER,
                hwMD5500BRAPortState
                    INTEGER,
                hwMD5500BRAOperate
                    INTEGER,
                hwMD5500BRAMaintainStatus
                    INTEGER,
                hwMD5500BRARowStatus
                    RowStatus
             }

        hwMD5500BRAPortFrameIndex OBJECT-TYPE
            SYNTAX Integer32
            MAX-ACCESS not-accessible
            STATUS current
            DESCRIPTION
                " "
            ::= { hwIsdnPhyPortDataEntry 1 }
        
        hwMD5500BRAPortSlotIndex OBJECT-TYPE
            SYNTAX Integer32
            MAX-ACCESS not-accessible
            STATUS current
            DESCRIPTION
                " "
            ::= { hwIsdnPhyPortDataEntry 2 }
        
        hwMD5500BRAPortIndex OBJECT-TYPE
            SYNTAX Integer32
            MAX-ACCESS not-accessible
            STATUS current
            DESCRIPTION
                " "
            ::= { hwIsdnPhyPortDataEntry 3 }
        
        hwMD5500BRAPortV5ID OBJECT-TYPE
            SYNTAX Integer32 (0..16777215)
            MAX-ACCESS read-write
            STATUS current
            DESCRIPTION
                " "
            ::= { hwIsdnPhyPortDataEntry 4 }
        
        hwMD5500BRAPortGrpNo OBJECT-TYPE
            SYNTAX Integer32 (0..254)
            MAX-ACCESS read-write
            STATUS current
            DESCRIPTION
                " "
            ::= { hwIsdnPhyPortDataEntry 5 }
        
        hwMD5500BRAEfAddr OBJECT-TYPE
            SYNTAX Integer32 (0..8175)
            MAX-ACCESS read-write
            STATUS current
            DESCRIPTION
                " "
            ::= { hwIsdnPhyPortDataEntry 6 }
        
        hwMD5500BRAV51Ts1 OBJECT-TYPE
            SYNTAX Integer32 (1..15 | 17..31)
            MAX-ACCESS read-write
            STATUS current
            DESCRIPTION
                " "
            ::= { hwIsdnPhyPortDataEntry 7 }
        
        hwMD5500BRAV51Ts2 OBJECT-TYPE
            SYNTAX Integer32 (1..15 | 17..31)
            MAX-ACCESS read-write
            STATUS current
            DESCRIPTION
                " "
            ::= { hwIsdnPhyPortDataEntry 8 }
        
        hwMD5500BRATelNo OBJECT-TYPE
            SYNTAX OCTET STRING (SIZE (16))
            MAX-ACCESS read-write
            STATUS current
            DESCRIPTION
                " "
            ::= { hwIsdnPhyPortDataEntry 9 }        
        
        
        hwMD5500BRAServiceType OBJECT-TYPE
            SYNTAX INTEGER
                {
                currenser(1),     
                insidespc(2),     
                v5spc(3),         
                v5preconn(4),     
                hireline(5)       
                }
            MAX-ACCESS read-only
            STATUS current
            DESCRIPTION
                "Options:
                 1.currenser(1)    -indicates the type is currenser
                 2.insidespc(2)    -indicates the type is insidespc
                 3.v5spc(3)        -indicates the type is v5spc    
                 4.v5preconn(4)    -indicates the type is v5preconn
                 5.hireline(5)     -indicates the type is hireline 
                "
            ::= { hwIsdnPhyPortDataEntry 10 }
        
        hwMD5500BRAFSMState OBJECT-TYPE
            SYNTAX INTEGER
                {
                an10(1),
                an11(2),
                an12(3),
                an20(4),
                an21(5),
                an22(6),
                an31(7),
                an32(8)
                }
            MAX-ACCESS read-only
            STATUS current
            DESCRIPTION
                "Options:
                 1.an10(1)         -indicates the state is an10
                 2.an11(2)         -indicates the state is an11
                 3.an12(3)         -indicates the state is an12
                 4.an20(4)         -indicates the state is an20
                 5.an21(5)         -indicates the state is an21
                 6.an22(6)         -indicates the state is an22
                 7.an31(7)         -indicates the state is an31
                 8.an32(8)         -indicates the state is an32
                "
            ::= { hwIsdnPhyPortDataEntry 11 }
        
        hwMD5500BRAPortState OBJECT-TYPE
            SYNTAX INTEGER
                {
                active(1),
                inactive(2),
                fault(3),
                test(4),
                maintain(5),
                localblock(6),
                oppblock(7),
                lock(8),
                busy(9),
                viruser(10),
                farloop(11),
                nearloop(12),
                b1codetest(13),
                b2codetest(14)
                }
            MAX-ACCESS read-only
            STATUS current
            DESCRIPTION
                "Options:
                 1.active(1)          -indicates the port state is active     
                 2.inactive(2)        -indicates the port state is inactive      
                 3.fault(3)           -indicates the port state is fault     
                 4.test(4)            -indicates the port state is test      
                 5.maintain(5)        -indicates the port state is maintain  
                 6.localblock(6)      -indicates the port state is localblock
                 7.oppblock(7)        -indicates the port state is oppblock  
                 8.lock(8)            -indicates the port state is lock      
                 9.busy(9)            -indicates the port state is busy      
                 10.viruser(10)       -indicates the port state is viruser   
                 11.farloop(11)       -indicates the port state is farloop   
                 12.nearloop(12)      -indicates the port state is nearloop  
                 13.b1codetest(13)    -indicates the port state is b1codetest
                 14.b2codetest(14)    -indicates the port state is b2codetest
                "
            ::= { hwIsdnPhyPortDataEntry 12 }       
        
        
        hwMD5500BRAOperate OBJECT-TYPE
            SYNTAX INTEGER
                {
                block(1),
                delayblock(2),
                unblock(3),
                reset(4),
                nearloop(5),
                farloop(6),
                unloop(7)
                }
            MAX-ACCESS read-write
            STATUS current
            DESCRIPTION
                "Options:           
                 1.block(1)         -indicates the operation is block      
                 2.delayblock(2)    -indicates the operation is delayblock    
                 3.unblock(3)       -indicates the operation is unblock    
                 4.reset(4)         -indicates the operation is reset      
                 5.nearloop(5)      -indicates the operation is nearloop   
                 6.farloop(6)       -indicates the operation is farloop 
                 7.unloop(7)        -indicates the operation is unloop    
                "
            ::= { hwIsdnPhyPortDataEntry 13 }
        
        hwMD5500BRAMaintainStatus OBJECT-TYPE
            SYNTAX INTEGER
                {
                mgcfged(1),
                v5cfged(2),
                notcfged(3)
                }
            MAX-ACCESS read-only
            STATUS current
            DESCRIPTION
                "Options:
                 1.mgcfged(1)       -indicates the maintainstatus of the PSTN port is mgcfged      
                 2.v5cfged(2)       -indicates the maintainstatus of the PSTN port is v5cfged 
                 3.notcfged(3)      -indicates the maintainstatus of the PSTN port is notcfged
                "                   
            ::= { hwIsdnPhyPortDataEntry 14 }
        
        hwMD5500BRARowStatus OBJECT-TYPE
            SYNTAX RowStatus
            MAX-ACCESS read-write
            STATUS current
            DESCRIPTION
                " "
            ::= { hwIsdnPhyPortDataEntry 15 }
        
-- Data table of the port
        hwIsdnV5PortDataTable OBJECT-TYPE
            SYNTAX SEQUENCE OF HwIsdnV5PortDataEntry
            MAX-ACCESS not-accessible
            STATUS current
            DESCRIPTION
                "Data table of the port.
                 The indexes of this table are hwMD5500BRAPortV5IDIndex and  hwMD5500BRAPortEFAddrIndex."
            ::= { hwMD5500BRAPort 2 }
        
        hwIsdnV5PortDataEntry OBJECT-TYPE
            SYNTAX HwIsdnV5PortDataEntry
            MAX-ACCESS not-accessible
            STATUS current
            DESCRIPTION
                "Data table of the port.
                 The indexes of this entry are hwMD5500BRAPortV5IDIndex and  hwMD5500BRAPortEFAddrIndex."
            INDEX { hwMD5500BRAPortV5IDIndex, hwMD5500BRAPortEFAddrIndex }
            ::= { hwIsdnV5PortDataTable 1 }
        
        HwIsdnV5PortDataEntry ::=
            SEQUENCE { 
                hwMD5500BRAPortV5IDIndex
                    Integer32,
                hwMD5500BRAPortEFAddrIndex
                    Integer32,
                hwMD5500BRAPortFrameID
                    Integer32,
                hwMD5500BRAPortSlotID
                    Integer32,
                hwMD5500BRAPortID
                    Integer32,
                hwMD5500BRAPortPortGrpNo
                    Integer32,
                hwMD5500BRAPortV51Ts1
                    Integer32,
                hwMD5500BRAPortV51Ts2
                    Integer32,
                hwMD5500BRAPortTelNo
                    OCTET STRING,
                hwMD5500BRAPortServiceType
                    INTEGER,
                hwMD5500BRAPortFSMState
                    INTEGER,
                hwMD5500BRAPortPortState
                    INTEGER,
                hwMD5500BRAPortOperate
                    INTEGER
             }

        hwMD5500BRAPortV5IDIndex OBJECT-TYPE
            SYNTAX Integer32
            MAX-ACCESS not-accessible
            STATUS current
            DESCRIPTION
                " "
            ::= { hwIsdnV5PortDataEntry 1 }
        
        hwMD5500BRAPortEFAddrIndex OBJECT-TYPE
            SYNTAX Integer32 (0..8175)
            MAX-ACCESS not-accessible
            STATUS current
            DESCRIPTION
                " "
            ::= { hwIsdnV5PortDataEntry 2 }
        
        hwMD5500BRAPortFrameID OBJECT-TYPE
            SYNTAX Integer32 (0..63)
            MAX-ACCESS read-only
            STATUS current
            DESCRIPTION
                " "
            ::= { hwIsdnV5PortDataEntry 3 }
        
        hwMD5500BRAPortSlotID OBJECT-TYPE
            SYNTAX Integer32 (0..63)
            MAX-ACCESS read-only
            STATUS current
            DESCRIPTION
                " "
            ::= { hwIsdnV5PortDataEntry 4 }
        
        hwMD5500BRAPortID OBJECT-TYPE
            SYNTAX Integer32 (0..63)
            MAX-ACCESS read-only
            STATUS current
            DESCRIPTION
                " "
            ::= { hwIsdnV5PortDataEntry 5 }
        
        hwMD5500BRAPortPortGrpNo OBJECT-TYPE
            SYNTAX Integer32 (0..254)
            MAX-ACCESS read-only
            STATUS current
            DESCRIPTION
                " "
            ::= { hwIsdnV5PortDataEntry 6 }
        
        hwMD5500BRAPortV51Ts1 OBJECT-TYPE
            SYNTAX Integer32 (1..15 | 17..31)
            MAX-ACCESS read-only
            STATUS current
            DESCRIPTION
                " "
            ::= { hwIsdnV5PortDataEntry 7 }
        
        hwMD5500BRAPortV51Ts2 OBJECT-TYPE
            SYNTAX Integer32 (1..15 | 17..31)
            MAX-ACCESS read-only
            STATUS current
            DESCRIPTION
                " "
            ::= { hwIsdnV5PortDataEntry 8 }
        
        hwMD5500BRAPortTelNo OBJECT-TYPE
            SYNTAX OCTET STRING (SIZE (16))
            MAX-ACCESS read-only
            STATUS current
            DESCRIPTION
                " "
            ::= { hwIsdnV5PortDataEntry 9 }     
        
        hwMD5500BRAPortServiceType OBJECT-TYPE
            SYNTAX INTEGER
                {
                currenser(1),
                insidespc(2),
                v5spc(3),
                v5preconn(4),
                hireline(5)
                }
            MAX-ACCESS read-only
            STATUS current
            DESCRIPTION
                "Options:
                 1.currenser(1)   -indicates the type is currenser
                 2.insidespc(2)   -indicates the type is insidespc
                 3.v5spc(3)       -indicates the type is v5spc    
                 4.v5preconn(4)   -indicates the type is v5preconn
                 5.hireline(5)    -indicates the type is hireline 
                "
            ::= { hwIsdnV5PortDataEntry 10 }
        
        hwMD5500BRAPortFSMState OBJECT-TYPE
            SYNTAX INTEGER
                {
                an10(1),
                an11(2),
                an12(3),
                an20(4),
                an21(5),
                an22(6),
                an31(7),
                an32(8)
                }
            MAX-ACCESS read-only
            STATUS current
            DESCRIPTION
                "Options:
                 1.an10(1)        -indicates the state is an10
                 2.an11(2)        -indicates the state is an11
                 3.an12(3)        -indicates the state is an12
                 4.an20(4)        -indicates the state is an20
                 5.an21(5)        -indicates the state is an21
                 6.an22(6)        -indicates the state is an22
                 7.an31(7)        -indicates the state is an31
                 8.an32(8)        -indicates the state is an32
                " 
            ::= { hwIsdnV5PortDataEntry 11 }
        
        hwMD5500BRAPortPortState OBJECT-TYPE
            SYNTAX INTEGER
                {
                active(1),
                inactive(2),
                fault(3),
                test(4),
                maintain(5),
                localblock(6),
                oppblock(7),
                lock(8),
                busy(9),
                viruser(10),
                farloop(11),
                nearloop(12),
                b1codetest(13),
                b2codetest(14)
                }
            MAX-ACCESS read-only
            STATUS current
            DESCRIPTION
                "Options:
                 1.active(1)            -indicates the port state is active    
                 2.inactive(2)          -indicates the port state is inactive  
                 3.fault(3)             -indicates the port state is fault     
                 4.test(4)              -indicates the port state is test      
                 5.maintain(5)          -indicates the port state is maintain  
                 6.localblock(6)        -indicates the port state is localblock
                 7.oppblock(7)          -indicates the port state is oppblock  
                 8.lock(8)              -indicates the port state is lock      
                 9.busy(9)              -indicates the port state is busy      
                 10.viruser(10)         -indicates the port state is viruser   
                 11.farloop(11)         -indicates the port state is farloop   
                 12.nearloop(12)        -indicates the port state is nearloop  
                 13.b1codetest(13)      -indicates the port state is b1codetest
                 14.b2codetest(14)      -indicates the port state is b2codetest
                "
            ::= { hwIsdnV5PortDataEntry 12 }
        
            
        hwMD5500BRAPortOperate OBJECT-TYPE
            SYNTAX INTEGER
                {
                block(1),
                delayblock(2),
                unblock(3),
                reset(4),
                nearloop(5),
                farloop(6),
                unloop(7)
                }
            MAX-ACCESS read-write
            STATUS current
            DESCRIPTION
                "Options:
                 1.block(1)            -indicates the operation is block     
                 2.delayblock(2)       -indicates the operation is delayblock
                 3.unblock(3)          -indicates the operation is unblock   
                 4.reset(4)            -indicates the operation is reset     
                 5.nearloop(5)         -indicates the operation is nearloop  
                 6.farloop(6)          -indicates the operation is farloop   
                 7.unloop(7)           -indicates the operation is unloop    
                "
            ::= { hwIsdnV5PortDataEntry 13 }    
            
-- hwIsdnBraPortAttrTable parameters            
    hwIsdnBraPortAttrTable OBJECT-TYPE
     SYNTAX      SEQUENCE OF HwIsdnBraPortAttrEntry
     MAX-ACCESS  not-accessible
     STATUS      current
     DESCRIPTION
       "
       Configuration table of the ISDN BRA port attributes.
       The index of this table is hwIsdnBraPortIndex.
       "
     ::= { hwMD5500BRAPort 3 } 
     
    hwIsdnBraPortAttrEntry OBJECT-TYPE
    SYNTAX      HwIsdnBraPortAttrEntry
    MAX-ACCESS  not-accessible
    STATUS      current
    DESCRIPTION
      "
      Configuration table of the ISDN BRA port attributes.
      The index of this entry is hwIsdnBraPortIndex.
      "
    INDEX    {  
              hwIsdnBraPortIndex
             }
    ::= { hwIsdnBraPortAttrTable 1 }
    
    HwIsdnBraPortAttrEntry ::=
    SEQUENCE
    {
      hwIsdnBraPortIndex     Integer32,
      hwMgIsdnTerminationRPower INTEGER,
      hwIsdnbraPortWorkMode  INTEGER, 
      hwIsdnbraPortBad       INTEGER,
      hwIsdnbraPortBadDelay   Integer32,
      hwMgIsdnBraCodeMode    INTEGER,
      hwMgIsdnBraL1ActiveMode   INTEGER,
      hwMgIsdnBraL2InfoMonitorEnable    INTEGER
    }
    
    hwIsdnBraPortIndex OBJECT-TYPE
    SYNTAX      Integer32
    MAX-ACCESS  not-accessible
    STATUS      current
    DESCRIPTION
        " 
        Shelf/Slot/Port 
        "
    ::= { hwIsdnBraPortAttrEntry 1 }    
    
    hwMgIsdnTerminationRPower OBJECT-TYPE
    SYNTAX      INTEGER{disable(0), enable(1)}
    MAX-ACCESS  read-write
    STATUS      current
    DESCRIPTION
        " 
        Whether the remote supply is supported. 0-Disable; 1-Enable.
        Options:
        1. disable(0) -Disable the remote supply
        2. enable(1)  -Enable the remote supply
        "
    ::= { hwIsdnBraPortAttrEntry 2 }
    
    hwIsdnbraPortWorkMode OBJECT-TYPE
    SYNTAX      INTEGER{p2mp(0), p2p(1)}
    MAX-ACCESS  read-write
    STATUS      current
    DESCRIPTION
        "  
        The change of the working mode of the BRA port may take effect after the board is reset. If the board type is H601DSLD, it need not be reset. If the board type is DSL, it needs to be reset.
        Options:
        1.p2mp(0)   --point to multi-points
        2.p2p(1)    --point to point
        "
    ::= { hwIsdnBraPortAttrEntry 3 } 
    
    hwIsdnbraPortBad OBJECT-TYPE
    SYNTAX      INTEGER{disable(0), enable(1)}
    MAX-ACCESS  read-write
    STATUS      current
    DESCRIPTION
        "
        Options:
        1.disable(0)    -disable
        2.enable(1)     -enable    
        "
    ::= { hwIsdnBraPortAttrEntry 4 }    
    
    hwIsdnbraPortBadDelay OBJECT-TYPE
    SYNTAX      Integer32(10..360) 
    MAX-ACCESS  read-write
    STATUS      current
    DESCRIPTION
        "
        Deactivation delay of the BRA basic access (unit: second)
        "  
    ::= { hwIsdnBraPortAttrEntry 5 }
    
    hwMgIsdnBraCodeMode OBJECT-TYPE
    SYNTAX      INTEGER{code-2B1Q(0), code-4B3T(1)}
    MAX-ACCESS  read-only
    STATUS      current
    DESCRIPTION
        " 
        Options:
        1.code-2B1Q(0)    -indicates the mode is 2b1q
        2.code-4B3T(1)    -indicates the mode is 4b3t       
        "
    ::= { hwIsdnBraPortAttrEntry 6 }    

    hwMgIsdnBraL1ActiveMode OBJECT-TYPE
    SYNTAX      INTEGER{longActive(1),notLongActive(2)}
    MAX-ACCESS  read-write
    STATUS      current
    DESCRIPTION
        " 
        Options:
        1.longActive(1)     --stable-active
        2.notLongActive(2)  --unstable-active
        "
    DEFVAL { {longActive(1)} }
    ::= { hwIsdnBraPortAttrEntry 7 } 
  
    hwMgIsdnBraL2InfoMonitorEnable OBJECT-TYPE
    SYNTAX      INTEGER{disable(1),enable(2)}
    MAX-ACCESS  read-write
    STATUS      current
    DESCRIPTION
        " 
        Options:
        1.disable(1)     -disable the bra l2 monitor
        2.enable(2)      -enable the bra l2 monitor  
        "
    DEFVAL { {enable(2)} }    
    ::= { hwIsdnBraPortAttrEntry 8 } 
    
    -- hwIsdnPortPerformanceStatTable parameters                
    hwIsdnPortPerformanceStatTable OBJECT-TYPE
     SYNTAX      SEQUENCE OF HwIsdnPortPerformanceStatEntry
     MAX-ACCESS  not-accessible
     STATUS      current
     DESCRIPTION
       "
       Configuration table of the ISDN BRA performance statistics function.
       The index of this table is hwIsdnPortIndex.
       "
     ::= { hwMD5500BRAPort 4 } 
     
    hwIsdnPortPerformanceStatEntry OBJECT-TYPE
    SYNTAX      HwIsdnPortPerformanceStatEntry
    MAX-ACCESS  not-accessible
    STATUS      current
    DESCRIPTION
      "
       Configuration table of the ISDN BRA performance statistics function.
       The index of this entry is hwIsdnPortIndex.
      "
    INDEX    {  
              hwIsdnPortIndex
             }
    ::= { hwIsdnPortPerformanceStatTable 1 }
    
    HwIsdnPortPerformanceStatEntry ::=
    SEQUENCE
    {
      hwIsdnPortIndex    Integer32,
      hwIsdnPortPerformanceStatOprType INTEGER,
      hwIsdnPortPerformanceStatPeri  Integer32, 
      hwIsdnPortErrorcode       Integer32, 
      hwIsdnPortNebeUas       Integer32,
      hwIsdnPortFebeUas       Integer32,
      hwIsdnPortNebeEs       Integer32,
      hwIsdnPortFebeEs       Integer32,
      hwIsdnPortNebeSes       Integer32,
      hwIsdnPortFebeSes       Integer32
    }
    
    hwIsdnPortIndex OBJECT-TYPE
    SYNTAX      Integer32
    MAX-ACCESS  not-accessible
    STATUS      current
    DESCRIPTION
        " 
        Shelf/Slot/Port 
        "
    ::= { hwIsdnPortPerformanceStatEntry 1 }    
    
    hwIsdnPortPerformanceStatOprType OBJECT-TYPE
    SYNTAX      INTEGER{stop(0), start(1)}
    MAX-ACCESS  read-write
    STATUS      current
    DESCRIPTION
        " 
        Options:
        1.stop(0)       -stop the performance statistics
        2.start(1)      -start the performance statistics
        "
    ::= { hwIsdnPortPerformanceStatEntry 2 }   
    
    hwIsdnPortPerformanceStatPeri OBJECT-TYPE
    SYNTAX      Integer32(0..5)
    MAX-ACCESS  read-write
    STATUS      current
    DESCRIPTION
        " 
        Starting cycle (minute).
        "
    ::= { hwIsdnPortPerformanceStatEntry 3 }   
    
    hwIsdnPortErrorcode OBJECT-TYPE
    SYNTAX      Integer32(0 |50..84)
    MAX-ACCESS  read-write
    STATUS      current
    DESCRIPTION
        " 
        Error bit threshold setting.
        "
    ::= { hwIsdnPortPerformanceStatEntry 4 }
    
    hwIsdnPortNebeUas OBJECT-TYPE
    SYNTAX      Integer32
    MAX-ACCESS  read-only
    STATUS      current
    DESCRIPTION
        "
         Near end block error (NEBE).
        "
    ::= { hwIsdnPortPerformanceStatEntry 5 }   
    
    hwIsdnPortFebeUas OBJECT-TYPE
    SYNTAX      Integer32
    MAX-ACCESS  read-only
    STATUS      current
    DESCRIPTION
        "
         Far end block error (FEBE). 
        "
    ::= { hwIsdnPortPerformanceStatEntry 6 }
    
    hwIsdnPortNebeEs OBJECT-TYPE
    SYNTAX      Integer32
    MAX-ACCESS  read-only
    STATUS      current
    DESCRIPTION
        "
         Near end block error (NEBE) errored second (s). 
        "
    ::= { hwIsdnPortPerformanceStatEntry 7 }
    
    hwIsdnPortFebeEs OBJECT-TYPE
    SYNTAX      Integer32
    MAX-ACCESS  read-only
    STATUS      current
    DESCRIPTION
        "
         Far end block error (FEBE) errored second (s). 
        "
    ::= { hwIsdnPortPerformanceStatEntry 8 }
    
    hwIsdnPortNebeSes OBJECT-TYPE
    SYNTAX      Integer32
    MAX-ACCESS  read-only
    STATUS      current
    DESCRIPTION
        "
         Near end block error (NEBE) severely errored second (s). 
        "
    ::= { hwIsdnPortPerformanceStatEntry 9 }
    
    hwIsdnPortFebeSes OBJECT-TYPE
    SYNTAX      Integer32
    MAX-ACCESS  read-only
    STATUS      current
    DESCRIPTION
        "
         Far end block error (FEBE) severely errored second (s). 
        "
    ::= { hwIsdnPortPerformanceStatEntry 10 }
  hwIsdnBraL1CRCErrTable OBJECT IDENTIFIER ::= { hwMD5500BRAPort  5}
    
    hwIsdnBraL1DMDegradedThreshold OBJECT-TYPE
    SYNTAX      Integer32(1..60)
    MAX-ACCESS  read-write
    STATUS      current
    DESCRIPTION
        " 
        BRA degraded-minutes degrade threshold.
        "
    ::= { hwIsdnBraL1CRCErrTable 1 } 
    
    hwIsdnBraL1ESDegradedThreshold OBJECT-TYPE
    SYNTAX      Integer32(1..3600)
    MAX-ACCESS  read-write
    STATUS      current
    DESCRIPTION
        " 
        BRA errored-seconds degrade threshold.
        "
    ::= { hwIsdnBraL1CRCErrTable 2 } 
    
    hwIsdnBraL1CSESDegradedThreshold OBJECT-TYPE
    SYNTAX      Integer32(1..60)
    MAX-ACCESS  read-write
    STATUS      current
    DESCRIPTION
        " 
        BRA consecutive-severely-errored-seconds degrade threshold.
        "
    ::= { hwIsdnBraL1CRCErrTable 3 } 
    
    hwIsdnBraL1DMAlarmThreshold OBJECT-TYPE
    SYNTAX      Integer32(1..60)
    MAX-ACCESS  read-write
    STATUS      current
    DESCRIPTION
        " 
        BRA consecutive-severely-errored-seconds degrade threshold.
        "
    ::= { hwIsdnBraL1CRCErrTable 4 }      
    
    hwIsdnBraL1ESAlarmThreshold OBJECT-TYPE
    SYNTAX      Integer32(1..3600)
    MAX-ACCESS  read-write
    STATUS      current
    DESCRIPTION
        " 
        BRA errored-seconds alarm threshold.
        "
    ::= { hwIsdnBraL1CRCErrTable 5 }    
    
    hwIsdnBraL1CSESAlarmThreshold OBJECT-TYPE
    SYNTAX      Integer32(1..60)
    MAX-ACCESS  read-write
    STATUS      current
    DESCRIPTION
        " 
        BRA consecutive-severely-errored-seconds alarm threshold.
        "
    ::= { hwIsdnBraL1CRCErrTable 6 }     
    
    hwIsdnBraL1CRCErrESThreshold OBJECT-TYPE
    SYNTAX      Integer32(1..100)
    MAX-ACCESS  read-write
    STATUS      current
    DESCRIPTION
        " 
        BRA errored-seconds define threshold.
        "
    ::= { hwIsdnBraL1CRCErrTable 7 }     
    
    hwIsdnBraL1CRCErrSESThreshold OBJECT-TYPE
    SYNTAX      Integer32(1..100)
    MAX-ACCESS  read-write
    STATUS      current
    DESCRIPTION
        " 
        BRA severely-errored-seconds define threshold.
        "
    ::= { hwIsdnBraL1CRCErrTable 8 }     
    
    hwIsdnBraL1CRCErrDMThreshold OBJECT-TYPE
    SYNTAX      Integer32(1..256)
    MAX-ACCESS  read-write
    STATUS      current
    DESCRIPTION
        " 
        BRA degraded-minutes define threshold.
        "
    ::= { hwIsdnBraL1CRCErrTable 9 }  

    hwIsdnBraL1DegradeEndService OBJECT-TYPE
     SYNTAX      INTEGER{enable(1),disable(2)}
     MAX-ACCESS  read-write
     STATUS      current
     DESCRIPTION
         "
         Whether port goes out of service when line quality gets worse. 
         Options:
         1.enable(1)  -indicates port goes out of service
         2.disable(2) -indicates port does not go out of service
         "
         DEFVAL      { enable }
     ::= { hwIsdnBraL1CRCErrTable 10 }

    hwIsdnTEICheckCfgTable OBJECT IDENTIFIER ::= { hwMD5500BRAPort  6}
  
    
    hwIsdnTEICheckCycle OBJECT-TYPE
    SYNTAX  Integer32(0..180)
    MAX-ACCESS  read-write
    STATUS  current
    DESCRIPTION
        "
        TEI check period (unit: minute).
        "
    ::= { hwIsdnTEICheckCfgTable 1 }
    
    hwIsdnL2DegradedAlarmCfgTable OBJECT-TYPE
     SYNTAX      SEQUENCE OF HwIsdnL2DegradedAlarmCfgEntry
     MAX-ACCESS  not-accessible
     STATUS      current
     DESCRIPTION
       "
       ISDN L2 degraded alarm configuration table.
       The index of this table is hwIsdnBraL2DAPortIndex.
       "
     ::= { hwMD5500BRAPort 7 } 
     
    hwIsdnL2DegradedAlarmCfgEntry OBJECT-TYPE
    SYNTAX      HwIsdnL2DegradedAlarmCfgEntry
    MAX-ACCESS  not-accessible
    STATUS      current
    DESCRIPTION
       "
       ISDN L2 degraded alarm configuration table.
       The index of this entry is hwIsdnBraL2DAPortIndex."
    INDEX    {  
              hwIsdnBraL2DAPortIndex
             }
    ::= { hwIsdnL2DegradedAlarmCfgTable 1 }
    
    HwIsdnL2DegradedAlarmCfgEntry ::=
    SEQUENCE
    {
        hwIsdnBraL2DAPortIndex  Integer32,
        hwIsdnBraL2DAUnexpectRespondThreshold   Integer32,
        hwIsdnBraL2DARebuiltLinkRequestThreshold    Integer32,
        hwIsdnBraL2DAN200OutTimeThreshold   Integer32,
        hwIsdnBraL2DAQ921AddrDomainErrThreshold Integer32,
        hwIsdnBraL2DAMDLERRJThreshold   Integer32,
        hwIsdnBraL2DAMDLERRKThreshold   Integer32,
        hwIsdnBraL2DAMDLERRLThreshold   Integer32,
        hwIsdnBraL2DAMDLERRMThreshold   Integer32,
        hwIsdnBraL2DAMDLERRNThreshold   Integer32,
        hwIsdnBraL2DAMDLERROThreshold   Integer32,
        hwIsdnBraL2DAFrameSNErrThreshold    Integer32,
        hwIsdnBraL2DABufferOverFlowThreshold    Integer32
    }
    
    hwIsdnBraL2DAPortIndex OBJECT-TYPE
    SYNTAX      Integer32
    MAX-ACCESS  not-accessible
    STATUS      current
    DESCRIPTION
        " 
        Port index. Shelf<<24|Slot<<16|Port.
        "
    ::= { hwIsdnL2DegradedAlarmCfgEntry 1 }    
    
    hwIsdnBraL2DAUnexpectRespondThreshold OBJECT-TYPE
    SYNTAX      Integer32(0..25)
    MAX-ACCESS  read-write
    STATUS      current
    DESCRIPTION
        " 
        Unsolicited responses received.
        "
    DEFVAL { 0 }
    ::= { hwIsdnL2DegradedAlarmCfgEntry 2 }    
   
    hwIsdnBraL2DARebuiltLinkRequestThreshold OBJECT-TYPE
    SYNTAX      Integer32(0..25)
    MAX-ACCESS  read-write
    STATUS      current
    DESCRIPTION
        " 
        Peer initiated re-establishments when in multiple frame established state.
        "
    DEFVAL { 0 }
    ::= { hwIsdnL2DegradedAlarmCfgEntry 3 }    
   
    hwIsdnBraL2DAN200OutTimeThreshold OBJECT-TYPE
    SYNTAX      Integer32(0..25)
    MAX-ACCESS  read-write
    STATUS      current
    DESCRIPTION
        " 
        Unsuccessful re-transmissions N200 times.
        "
    DEFVAL { 0 }
    ::= { hwIsdnL2DegradedAlarmCfgEntry 4 }    
   
    hwIsdnBraL2DAQ921AddrDomainErrThreshold OBJECT-TYPE
    SYNTAX      Integer32(0..25)
    MAX-ACCESS  read-write
    STATUS      current
    DESCRIPTION
        " 
        Q.921 address field errors.
        "
    DEFVAL { 0 }
    ::= { hwIsdnL2DegradedAlarmCfgEntry 5 }     

    hwIsdnBraL2DAMDLERRJThreshold OBJECT-TYPE
    SYNTAX      Integer32(0..25)
    MAX-ACCESS  read-write
    STATUS      current
    DESCRIPTION
        " 
        Q.921 MDL errors J.
        "
    DEFVAL { 0 }
    ::= { hwIsdnL2DegradedAlarmCfgEntry 6 } 
   
    hwIsdnBraL2DAMDLERRKThreshold OBJECT-TYPE
    SYNTAX      Integer32(0..25)
    MAX-ACCESS  read-write
    STATUS      current
    DESCRIPTION
        " 
        Q.921 MDL errors K.
        "
    DEFVAL { 0 }
    ::= { hwIsdnL2DegradedAlarmCfgEntry 7 }     
   
    hwIsdnBraL2DAMDLERRLThreshold OBJECT-TYPE
    SYNTAX      Integer32(0..25)
    MAX-ACCESS  read-write
    STATUS      current
    DESCRIPTION
        " 
        Invalid/Unrecognized frame.
        "
    DEFVAL { 0 }
    ::= { hwIsdnL2DegradedAlarmCfgEntry 8 }     
 
    hwIsdnBraL2DAMDLERRMThreshold OBJECT-TYPE
    SYNTAX      Integer32(0..25)
    MAX-ACCESS  read-write
    STATUS      current
    DESCRIPTION
        " 
        Unexpected/Not permitted I-field received.
        "
    DEFVAL { 0 }
    ::= { hwIsdnL2DegradedAlarmCfgEntry 9 } 
 
    hwIsdnBraL2DAMDLERRNThreshold OBJECT-TYPE
    SYNTAX      Integer32(0..25)
    MAX-ACCESS  read-write
    STATUS      current
    DESCRIPTION
        " 
        Q.921 MDL errors N.
        "
    DEFVAL { 0 }
    ::= { hwIsdnL2DegradedAlarmCfgEntry 10 }  
 
    hwIsdnBraL2DAMDLERROThreshold OBJECT-TYPE
    SYNTAX      Integer32(0..25)
    MAX-ACCESS  read-write
    STATUS      current
    DESCRIPTION
        " 
        Excess octets in the information field.
        "
    DEFVAL { 0 }
    ::= { hwIsdnL2DegradedAlarmCfgEntry 11 } 
    
    hwIsdnBraL2DAFrameSNErrThreshold OBJECT-TYPE
    SYNTAX      Integer32(0..25)
    MAX-ACCESS  read-write
    STATUS      current
    DESCRIPTION
        " 
        Frame check sequence errors.
        "
    DEFVAL { 0 }
    ::= { hwIsdnL2DegradedAlarmCfgEntry 12 }    
    
    hwIsdnBraL2DABufferOverFlowThreshold OBJECT-TYPE
    SYNTAX      Integer32(0..25)
    MAX-ACCESS  read-write
    STATUS      current
    DESCRIPTION
        " 
        Limit of buffer overflows.
        "
    DEFVAL { 0 }
    ::= { hwIsdnL2DegradedAlarmCfgEntry 13 }     
       
        
        hwMD5500PortStateTrace OBJECT IDENTIFIER ::= { hwMD5500PortAdminMIB 10 }
        
                --MIB table of the status-tracking LED
                hwPortStateTraceTable OBJECT-TYPE
                  SYNTAX      SEQUENCE OF HwPortStateTraceEntry
                  MAX-ACCESS  not-accessible
                  STATUS      current
                  DESCRIPTION
                    "MIB table of this status-tracking LED.
                    The index of this table is hwPortStateTraceFrameId.
                    "
                  ::= { hwMD5500PortStateTrace 1 }
                
                hwPortStateTraceEntry OBJECT-TYPE
                  SYNTAX      HwPortStateTraceEntry
                  MAX-ACCESS  not-accessible
                  STATUS      current
                  DESCRIPTION
                   "MIB table of this status-tracking LED.
                    The index of this entry is hwPortStateTraceFrameId.
                    "
                  INDEX    { hwPortStateTraceFrameId}
                  ::= { hwPortStateTraceTable 1 }
                
                HwPortStateTraceEntry ::=
                  SEQUENCE
                  {
                    hwPortStateTraceFrameId       Integer32,
                    hwPortStateTraceOprType       INTEGER
                  }
                
                hwPortStateTraceFrameId OBJECT-TYPE
                   SYNTAX     Integer32(0..240)
                   MAX-ACCESS not-accessible
                   STATUS     current
                   DESCRIPTION
                       "Frame ID(0..240)
                        Shelf ID (0..240)."
                ::= {hwPortStateTraceEntry 1}
                
                hwPortStateTraceOprType OBJECT-TYPE
                  SYNTAX      INTEGER{stop(1), start(2) , handshake(3)}
                  MAX-ACCESS  read-create
                  STATUS      current
                  DESCRIPTION
                      "Operation type (enumerated: 1-stop port status reporting; 2-start port status reporting; 3-handshake)
                      Options: 
                      1.stop(1)             -stop the trace 
                      2.start(2)            -start the trace 
                      3.handshake(3)        -indicates the handshake of the trace
                      "
                  ::= { hwPortStateTraceEntry 2 }   
-- SPCM port MIB

        hwMD5500SPCMPort OBJECT IDENTIFIER ::= { hwMD5500PortAdminMIB 11 }
        

        hwMD5500SPCMPortPhyTable OBJECT-TYPE
            SYNTAX SEQUENCE OF HwMD5500SPCMPortPhyEntry
            MAX-ACCESS not-accessible
            STATUS current
            DESCRIPTION
                "The indexes of this table are hwMD5500SPCMPortFrameIndex, hwMD5500SPCMPortSlotIndex, 
                 and hwMD5500SPCMPortIndex."
            ::= { hwMD5500SPCMPort 1 }
        
        hwMD5500SPCMPortPhyEntry OBJECT-TYPE
            SYNTAX HwMD5500SPCMPortPhyEntry
            MAX-ACCESS not-accessible
            STATUS current
            DESCRIPTION
                "The indexes of this entry are hwMD5500SPCMPortFrameIndex, hwMD5500SPCMPortSlotIndex, 
                 and hwMD5500SPCMPortIndex. 
                "
            INDEX { hwMD5500SPCMPortFrameIndex, hwMD5500SPCMPortSlotIndex, hwMD5500SPCMPortIndex }
            ::= { hwMD5500SPCMPortPhyTable 1 }
        
        HwMD5500SPCMPortPhyEntry ::=
            SEQUENCE { 
                hwMD5500SPCMPortFrameIndex
                    Integer32,
                hwMD5500SPCMPortSlotIndex
                    Integer32,
                hwMD5500SPCMPortIndex
                    Integer32,
                hwMD5500SPCMInterfaceID
                    Integer32,
                hwMD5500SPCMCASE1Ts
                    Integer32,
                hwMD5500SPCMtelNo
                    OCTET STRING,
                hwMD5500SPCMPortState
                    INTEGER,
                hwMD5500SPCMServiceState
                    INTEGER,
                hwMD5500SPCMOperate
                    INTEGER,
                hwMD5500SPCMPortMaintainStatus
                    INTEGER,
                hwMD5500SPCMRowStatus
                    RowStatus
             }

        hwMD5500SPCMPortFrameIndex OBJECT-TYPE
            SYNTAX Integer32
            MAX-ACCESS not-accessible
            STATUS current
            DESCRIPTION
                " "
            ::= { hwMD5500SPCMPortPhyEntry 1 }
        
        hwMD5500SPCMPortSlotIndex OBJECT-TYPE
            SYNTAX Integer32
            MAX-ACCESS not-accessible
            STATUS current
            DESCRIPTION
                " "
            ::= { hwMD5500SPCMPortPhyEntry 2 }
        
        hwMD5500SPCMPortIndex OBJECT-TYPE
            SYNTAX Integer32
            MAX-ACCESS not-accessible
            STATUS current
            DESCRIPTION
                " "
            ::= { hwMD5500SPCMPortPhyEntry 3 }
        
        hwMD5500SPCMInterfaceID OBJECT-TYPE
            SYNTAX Integer32 (0..254)
            MAX-ACCESS read-write
            STATUS current
            DESCRIPTION
                " "
            ::= { hwMD5500SPCMPortPhyEntry 4 }
        
        hwMD5500SPCMCASE1Ts OBJECT-TYPE
            SYNTAX Integer32 (1..15 | 17..31)
            MAX-ACCESS read-write
            STATUS current
            DESCRIPTION
                " "
            ::= { hwMD5500SPCMPortPhyEntry 5 }
        
        hwMD5500SPCMtelNo OBJECT-TYPE
            SYNTAX OCTET STRING (SIZE (16))
            MAX-ACCESS read-write
            STATUS current
            DESCRIPTION
                " "
            ::= { hwMD5500SPCMPortPhyEntry 6 }
        
        hwMD5500SPCMPortState OBJECT-TYPE
            SYNTAX INTEGER
                {
                idle(1),
                fault(2),
                test(3),
                maintain(4),
                localblock(5),
                oppblock(6),
                lock(7),
                busy(8),
                viruser(9),
                farloop(10),
                nearloop(11),
                b1codetest(12),
                b2codetest(13)
                }
            MAX-ACCESS read-only
            STATUS current
            DESCRIPTION
                "
                Options:
                1.idle(1)              -indicates the port state is idle       
                2.fault(2)             -indicates the port state is fault      
                3.test(3)              -indicates the port state is test       
                4.maintain(4)          -indicates the port state is maintain   
                5.localblock(5)        -indicates the port state is localblock 
                6.oppblock(6)          -indicates the port state is oppblock   
                7.lock(7)              -indicates the port state is lock       
                8.busy(8)              -indicates the port state is busy       
                9.viruser(9)           -indicates the port state is viruser    
                10.farloop(10)         -indicates the port state is farloop    
                11.nearloop(11)        -indicates the port state is nearloop   
                12.b1codetest(12)      -indicates the port state is b1codetest 
                13.b2codetest(13)      -indicates the port state is b2codetest 
                "
            ::= { hwMD5500SPCMPortPhyEntry 7 }

        hwMD5500SPCMServiceState OBJECT-TYPE
            SYNTAX INTEGER
                {
                outofservice(1),
                idle(2),
                calling(3)
                }
            MAX-ACCESS read-only
            STATUS current
            DESCRIPTION
                "
                Options:
                1.outofservice(1)       -indicates the service state is outofservice    
                2.idle(2)               -indicates the service state is idle 
                3.calling(3)            -indicates the service state is calling 
                "
            ::= { hwMD5500SPCMPortPhyEntry 8 }

        hwMD5500SPCMOperate OBJECT-TYPE
            SYNTAX INTEGER
                {
                reset(4),
                nearloop(5),
                unloop(6)
                }
            MAX-ACCESS read-write
            STATUS current
            DESCRIPTION
                "
                Options:
                1.reset(4)    -Operation is reset
                2.nearloop(5) -Operation is near loop
                3.unloop(6)   -Operation is not loop
                "
            ::= { hwMD5500SPCMPortPhyEntry 9 }
        
        hwMD5500SPCMPortMaintainStatus OBJECT-TYPE
            SYNTAX INTEGER
                {
                mgcfged(1),
                v5cfged(2),
                notcfged(3),
                spcmcfged(4)
                }
            MAX-ACCESS read-only
            STATUS current
            DESCRIPTION
                "
                Options:
                1.mgcfged(1)       -indicates the maintainstatus of the PSTN port is mgcfged    
                2.v5cfged(2)       -indicates the maintainstatus of the PSTN port is v5cfged  
                3.notcfged(3)      -indicates the maintainstatus of the PSTN port is notcfged 
                4.spcmcfged(4)     -indicates the maintainstatus of the PSTN port is spcmcfged
                "
            ::= { hwMD5500SPCMPortPhyEntry 10 }
        
        hwMD5500SPCMRowStatus OBJECT-TYPE
            SYNTAX RowStatus
            MAX-ACCESS read-write
            STATUS current
            DESCRIPTION
                " "
            ::= { hwMD5500SPCMPortPhyEntry 11 }
        
            
            
            
            
        hwNarrowUserDataTrapSequence OBJECT IDENTIFIER ::= { hwMD5500PortAdminMIB 12 }
        
        hwNarrowUserDataChangeSequencePstnV5 OBJECT-TYPE
            SYNTAX Integer32
            MAX-ACCESS read-only
            STATUS current
            DESCRIPTION
                "
                Serial number for reporting traps after the V5 PSTN user data changes.
                "
            ::= { hwNarrowUserDataTrapSequence 1 }
        
        hwNarrowUserDataChangeSequencePstnMG OBJECT-TYPE
            SYNTAX Integer32
            MAX-ACCESS read-only
            STATUS current
            DESCRIPTION
                "
                Serial number for reporting traps after the MG PSTN user data changes.
                "
            ::= { hwNarrowUserDataTrapSequence 2 }
        
        hwNarrowUserDataChangeSequencePstnSPCM OBJECT-TYPE
            SYNTAX Integer32
            MAX-ACCESS read-only
            STATUS current
            DESCRIPTION
                "
                Serial number for reporting traps after the SPCM PSTN user data changes.
                "
            ::= { hwNarrowUserDataTrapSequence 3 }
        
        hwNarrowUserDataChangeSequenceIsdnV5 OBJECT-TYPE
            SYNTAX Integer32
            MAX-ACCESS read-only
            STATUS current
            DESCRIPTION
                " 
                Serial number for reporting traps after the V5 ISDN user data changes.
                "
            ::= { hwNarrowUserDataTrapSequence 4 }
            
        hwNarrowUserDataChangeSequenceIsdnMG OBJECT-TYPE
            SYNTAX Integer32
            MAX-ACCESS read-only
            STATUS current
            DESCRIPTION
                " 
                Serial number for reporting traps after the MG ISDN user data changes.
                "
            ::= { hwNarrowUserDataTrapSequence 5 }
            
        hwNarrowUserDataChangeSequenceDdiMG OBJECT-TYPE
            SYNTAX Integer32
            MAX-ACCESS read-only
            STATUS current
            DESCRIPTION
                " 
                Serial number for reporting traps after the MG PSTN user data changes.
                "
            ::= { hwNarrowUserDataTrapSequence 6 }
            
        hwNarrowUserDataChangeSequenceCdiPort OBJECT-TYPE
            SYNTAX Integer32
            MAX-ACCESS read-only
            STATUS current
            DESCRIPTION
                " 
                Serial number for reporting the traps after the CDI PORT attributes change.
                "
            ::= { hwNarrowUserDataTrapSequence 7 }
            
        hwNarrowUserDataChangeSequenceVfbPort OBJECT-TYPE
            SYNTAX Integer32
            MAX-ACCESS read-only
            STATUS current
            DESCRIPTION
                " 
                Serial number for reporting the traps after the VFB PORT attributes change.
                "
            ::= { hwNarrowUserDataTrapSequence 8 }

            hwNarrowUserDataChangeSequencePraV5 OBJECT-TYPE
            SYNTAX Integer32
            MAX-ACCESS read-only
            STATUS current
            DESCRIPTION
                "   
                Serial number for reporting the traps after the V5 PRA user data changes.
                "
            ::= { hwNarrowUserDataTrapSequence 9 }
                hwNarrowUserDataChangeSequencePraMG OBJECT-TYPE
            SYNTAX Integer32
            MAX-ACCESS read-only
            STATUS current
            DESCRIPTION
                " 
                Serial number for reporting the traps after the MG PRA user data changes.
                "
            ::= { hwNarrowUserDataTrapSequence 10 }
        
            
            
            
            
            
                  
        hwPortStateTraceTraps OBJECT IDENTIFIER ::= { hwMD5500PortStateTrace 2 }              
                
        hwPortStateTraceTrapVbOids OBJECT IDENTIFIER ::= { hwPortStateTraceTraps  1}

            hwPortStateTraceFrame OBJECT-TYPE
            SYNTAX Integer32 (0..240)
            MAX-ACCESS accessible-for-notify
            STATUS current
            DESCRIPTION
                "               
                Shelf ID
                "
            ::= { hwPortStateTraceTrapVbOids 1 }
                
                hwPortStateTracePortNumber OBJECT-TYPE
                    SYNTAX Integer32 (1..65535)
            MAX-ACCESS accessible-for-notify
            STATUS current
            DESCRIPTION
                "               
                Number of ports reported each time.
                "
            ::= { hwPortStateTraceTrapVbOids 2 }

                hwPortStateTraceSlotId OBJECT-TYPE
                    SYNTAX Integer32 (0..63)
            MAX-ACCESS accessible-for-notify
            STATUS current
            DESCRIPTION
                "               
                Slot ID in which the port is located
                "
            ::= { hwPortStateTraceTrapVbOids 3 }
                
                hwPortStateTracePortId OBJECT-TYPE
                    SYNTAX Integer32 (0..63)
            MAX-ACCESS accessible-for-notify
            STATUS current
            DESCRIPTION
                "               
                Port ID.
                "
            ::= { hwPortStateTraceTrapVbOids 4 }

                hwPortStateTracePortState OBJECT-TYPE
                    SYNTAX INTEGER
                        {
                            fault(1),
                            testing(2),
                            lock(3),
                            idle(4),
                            busy(5),
                            remoteloop(6),
                            localloop(7),
                            deactive(8),
                            active(9)
                        }
            MAX-ACCESS accessible-for-notify
            STATUS current
            DESCRIPTION
                "
                Options:
                1.fault(1)        -indicates the state of the trace port is fault   
                2.testing(2)      -indicates the state of the trace port is testing
                3.lock(3)         -indicates the state of the trace port is lock   
                4.idle(4)         -indicates the state of the trace port is idle   
                5.busy(5)         -indicates the state of the trace port is busy   
                6.remoteloop(6)   -indicates the state of the trace port is remoteloop 
                7.localloop(7)    -indicates the state of the trace port is localloop   
                8.deactive(8)     -indicates the state of the trace port is deactive   
                9.active(9)       -indicates the state of the trace port is active     
                "
            ::= { hwPortStateTraceTrapVbOids 5 }

                hwV5PortStateTraceTrap NOTIFICATION-TYPE
                   OBJECTS { hwPortStateTraceFrame, hwPortStateTracePortNumber, hwPortStateTraceSlotId, hwPortStateTracePortId, hwPortStateTracePortState }
                   STATUS current
                   DESCRIPTION
                           "
                           For the V5 user port:
                           Port state report trap: 1: frameid; 2: portnum; 3: slotid; 4: portid; 5: portstate.
                           Port state: 1: failed; 2: test; 3: lock; 4: idle; 5: busy; 6: remote loop; 
                                        7: local loop; 8: BRA deactive; 9: BRA active.
                           "
                   ::= { hwPortStateTraceTraps 2 }
                   
               hwAGPortStateTraceTrap NOTIFICATION-TYPE
                   OBJECTS { hwPortStateTraceFrame, hwPortStateTracePortNumber, hwPortStateTraceSlotId, hwPortStateTracePortId, hwPortStateTracePortState }
                   STATUS current
                   DESCRIPTION
                           "
                           For the AG user port:
                           Port state report trap: 1: frameid; 2: portnum; 3: slotid; 4: portid; 5: portstate.
                           Portstate: 1: failed; 2: test; 3: lock; 4: idle; 5: busy; 6: remote loop; 
                                        7: local loop; 8: BRA deactive; 9: BRA active; 10: powerdeny.
                          "
                    ::= { hwPortStateTraceTraps 3 }     
                    
 --  majun add for hwc port start 060208                   
                     -- HWC PORT  MIB ADD  BY XUDONGJIAN  200509  START                    
 hwHwcPort OBJECT IDENTIFIER ::= { hwMD5500PortAdminMIB 13 }
        
        hwHwcPortPhyTable OBJECT-TYPE
            SYNTAX SEQUENCE OF HwHwcPortPhyEntry
            MAX-ACCESS not-accessible
            STATUS current
            DESCRIPTION
                "The index of this table is hwHwcPortPhysicalIndex."
            ::= { hwHwcPort 1 }
        
        hwHwcPortPhyEntry OBJECT-TYPE
            SYNTAX HwHwcPortPhyEntry
            MAX-ACCESS not-accessible
            STATUS current
            DESCRIPTION
                "The index of this entry is hwHwcPortPhysicalIndex."
            INDEX { hwHwcPortPhysicalIndex} 
            ::= { hwHwcPortPhyTable 1 }
        
        HwHwcPortPhyEntry ::=
            SEQUENCE { 
                hwHwcPortPhysicalIndex
                    Integer32,
                hwHwcPortMasterSlaveState
                    INTEGER,
                hwHwcPortPhysicalState
                    INTEGER,
                hwHwcSwitchOperate
                    INTEGER
                
             }

        hwHwcPortPhysicalIndex OBJECT-TYPE
            SYNTAX Integer32
            MAX-ACCESS not-accessible
            STATUS current
            DESCRIPTION
                " "
            ::= { hwHwcPortPhyEntry 1 }     
        
        hwHwcPortMasterSlaveState OBJECT-TYPE
            SYNTAX INTEGER
                {
                master(1),
                slave(2)
                }
            MAX-ACCESS read-only
            STATUS current
            DESCRIPTION
                "
                Options:
                1.master(1)    -indicates the smaster port state
                2.slave(2)     -indicates the slave port state
                "
            ::= { hwHwcPortPhyEntry 2 }

        hwHwcPortPhysicalState OBJECT-TYPE
            SYNTAX INTEGER
                {
                  normal(1),
                  fault(2)
                }
            MAX-ACCESS read-only
            STATUS current
            DESCRIPTION
                "
                Options:
                1.normal(1)    -indicates the physical state of the port is normal
                2.fault(2)     -indicates the physical state of the port is fault 
                "
            ::= { hwHwcPortPhyEntry 3 }

        hwHwcSwitchOperate OBJECT-TYPE
            SYNTAX INTEGER
                {
                switch(1)            
                }
            MAX-ACCESS read-write
            STATUS current
            DESCRIPTION
                "
                Options:
                1.switch(1)  -indicates the switch
                "
            ::= { hwHwcPortPhyEntry 4 }
        
 -- majun add for hwc port end 060208    
-- HWC PORT  MIB ADD  BY  XUDONGJIAN  200509  END       
    
    END
