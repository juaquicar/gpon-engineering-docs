-- ================================================================================
-- Copyright (C) 2014 by  HUAWEI TECHNOLOGIES. All rights reserved.
-- Description: The mib module defines the MIB objects of the Rapid Ring Protection 
--              protocol(RRPP). RRPP provides fast protection switching to layer 2  
--              switches interconnected in an Ethernet ring topology.  When a link in 
--              the ring breaks, the RRPP can recover the data path quickly.
--              Its protection switching is similar to what can be achieved with 
--              the Spanning Tree Protocol (STP), but the converging time is less              
--              than a second after link failure.
--              This MIB defines management information used on products which 
--              support RRPP.             
-- Reference:
-- Version: V1.10
-- =================================================================================
    HUAWEI-DSLAM-RRPP-MIB DEFINITIONS ::= BEGIN
 
        IMPORTS
            hwDatacomm            
                FROM HUAWEI-MIB            
            OBJECT-GROUP, NOTIFICATION-GROUP            
                FROM SNMPv2-CONF            
            Counter32, OBJECT-TYPE, MODULE-IDENTITY, NOTIFICATION-TYPE,Integer32            
                FROM SNMPv2-SMI            
            RowStatus, TEXTUAL-CONVENTION            
                FROM SNMPv2-TC
            InterfaceIndex 
                   FROM IF-MIB;
    
        hwRrpp MODULE-IDENTITY 
            LAST-UPDATED "201406100000Z"        
            ORGANIZATION "Huawei Technologies Co.,Ltd."
            CONTACT-INFO                                        
                "Huawei Industrial Base
                 Bantian, Longgang
                 Shenzhen 518129
                 People's Republic of China
                 Website: http://www.huawei.com
                 Email: support@huawei.com
                "                                      
            DESCRIPTION 
                "The mib module defines the MIB objects of the Rapid Ring Protection 
                 protocol(RRPP). RRPP provides fast protection switching to layer 2  
                 switches interconnected in an Ethernet ring topology.  When a link in 
                 the ring breaks, the RRPP can recover the data path quickly.
                 Its protection switching is similar to what can be achieved with 
                 the Spanning Tree Protocol (STP), but the converging time is less              
                 than a second after link failure.
                 This MIB defines management information used on products which 
                 support RRPP." 
            
            --  Revision history
            REVISION     "201406100000Z"
            DESCRIPTION  "V1.10, modified the MIB name from HUAWEI-RRPP-MIB to HUAWEI-DSLAM-RRPP-MIB."
            
            REVISION     "201302070000Z"
            DESCRIPTION  "V1.09, modified description of leaves."
            
            REVISION     "201111020000Z"
            DESCRIPTION  "V1.08, modified description of leaves."
                        
            REVISION     "201110260000Z"
            DESCRIPTION  "V1.07, modified description of leaves."
            
            REVISION     "201011090000Z"
            DESCRIPTION  "V1.06, modified description of leaves."
            
            REVISION     "201007191620Z"
            DESCRIPTION  "V1.05, modified description of leaves.
                          Modified the range of hwRrppRingPrimaryPort and hwRrppRingSecondaryPort."
            
            REVISION     "201004161620Z"
            DESCRIPTION  "V1.04, modified description of leaves."                         
            
            REVISION     "201004151620Z"
            DESCRIPTION  "V1.03, modified description of leaves."  
                          
            REVISION     "200912311620Z"
            DESCRIPTION  "V1.02, formated the mib file. Modified datatype definition, and description of objects
                         from INTEGER to Integer32."  
                         
            REVISION     "200912301620Z"
            DESCRIPTION  "V1.01, added information of group."             
                       
            REVISION     "200607310000Z"
            DESCRIPTION  "V1.00, initial version"
                  
            ::= { hwDatacomm 113 }

        EnabledStatus ::= TEXTUAL-CONVENTION
            STATUS current
            DESCRIPTION 
                "A simple status value for the object.
                "
            SYNTAX INTEGER
                {
                enabled(1),
                disabled(2)
                }
        hwRrppScalarGroup OBJECT IDENTIFIER ::= { hwRrpp 1 }
        
        hwRrppEnableStatus OBJECT-TYPE
            SYNTAX EnabledStatus
            MAX-ACCESS read-write
            STATUS current
            DESCRIPTION
                "Indicates the RRPP global status.
                 Options: 
                 1. enabled(1)  -indicates the RRPP global switch is on
                 2. disabled(2) -indicates the RRPP global switch is off
                 Default: disabled(2)
                "
            ::= { hwRrppScalarGroup 1 }
		
        hwRrppMode OBJECT-TYPE
            SYNTAX INTEGER
                {
                rrpp(1),
                eaps(2)
                }
            MAX-ACCESS read-write
            STATUS current
            DESCRIPTION
                "Indicates the RRPP protocol mode.
                 Options: 
                 1. rrpp(1) -indicates the RRPP protocol mode is rrpp
                 2. eaps(2) -indicates the RRPP protocol mode is eaps
                 Default: rrpp(1)
                 For details about EAPS(Ethernet Automatic Protection Switching), see RFC 3619.
                "
			::= { hwRrppScalarGroup 2 }
			
        hwRrppTable OBJECT IDENTIFIER ::= { hwRrpp 2 }
        
        hwRrppDomainTable OBJECT-TYPE
            SYNTAX SEQUENCE OF HwRrppDomainEntry
            MAX-ACCESS not-accessible
            STATUS current
            DESCRIPTION
                "Used to manage RRPP domains, such as create and delete domain, config control VLAN,
                 config the time of the HELLO message send timer and FAIL timer, and query the basic
                 information of domains.
                 The index of this table is hwRrppDomainID.
                "
            ::= { hwRrppTable 1 }
        
        hwRrppDomainEntry OBJECT-TYPE
            SYNTAX HwRrppDomainEntry
            MAX-ACCESS not-accessible
            STATUS current
            DESCRIPTION
                "Used to manage RRPP domains, such as create and delete domain, config control VLAN,
                 config the time of the HELLO message send timer and FAIL timer, and query the basic
                 information of domains.
                 The index of this entry is hwRrppDomainID.
                "
            INDEX { hwRrppDomainID }
            ::= { hwRrppDomainTable 1 }
        
        HwRrppDomainEntry ::=
            SEQUENCE { 
                hwRrppDomainID
                    Integer32,
                hwRrppDomainControlVlanID
                    Integer32,
                hwRrppDomainHelloTime
                    Integer32,
                hwRrppDomainFailTime
                    Integer32,
                hwRrppDomainRowStatus
                    RowStatus
             }

        hwRrppDomainID OBJECT-TYPE
            SYNTAX Integer32 (1..8)
            MAX-ACCESS accessible-for-notify
            STATUS current
            DESCRIPTION
                "Indicates the ID of the RRPP domain. This value cannot be modified after it is created. 
                 Range: 1-8
                "
            ::= { hwRrppDomainEntry 1 }
        
        hwRrppDomainControlVlanID OBJECT-TYPE
            SYNTAX Integer32 (1..4093 | 65535)
            MAX-ACCESS read-create
            STATUS current
            DESCRIPTION
                "Indicates the ID of the control VLAN for the RRPP domain. 
                 Range: 1-4093, 65535
                 Only support 2-4092 in current version. The value 65535 indicates that the control VLAN 
                 is not configured. This value cannot be modified after it is created.
                "
            DEFVAL { 65535 }
            ::= { hwRrppDomainEntry 2 }

        hwRrppDomainHelloTime OBJECT-TYPE
            SYNTAX Integer32 (1..10)
            MAX-ACCESS read-create
            STATUS current
            DESCRIPTION
                "Indicates the timer for sending hello packets in the RRPP domain.
                 Range: 1-10
                 Unit: second
                 Default: 1
                 It indicates the interval for the master node to send two successive hello packets. 
                 The value can be modified but cannot be deleted or created.
                "
            DEFVAL { 1 }
            ::= { hwRrppDomainEntry 3 }
        
        hwRrppDomainFailTime OBJECT-TYPE
            SYNTAX Integer32 (3..30)
            MAX-ACCESS read-create
            STATUS current
            DESCRIPTION
                "Indicates the timeout timer for hello packets in the RRPP domain.
                 Range: 3-30
                 Unit: second
                 Default: 3
                 If the master node does not receive the hello packets sent by itself within this timer 
                 period, the master node considers that the ring is faulty. The value can be modified 
                 but cannot be deleted or created. Configure this value to be at least three times the 
                 value of the timer for sending hello packets.
                "
            DEFVAL { 3 }
            ::= { hwRrppDomainEntry 4 }
        
        hwRrppDomainRowStatus OBJECT-TYPE
            SYNTAX RowStatus
            MAX-ACCESS read-create
            STATUS current
            DESCRIPTION
                "Indicates the row status and is used to create or delete an RRPP domain. It only 
                 supports the createAndGo(4) and destroy(6) operations. During query, active(1) 
                 is fixedly returned for this leaf.
                 When creating an RRPP domain, you must set hwRrppDomainRowStatus to createAndGo(4) 
                 in the set operation. hwRrppDomainControlVlanID, hwRrppDomainHelloTime, and 
                 hwRrppDomainFailTime are optional.
                 When deleting an RRPP domain, you must set hwRrppDomainRowStatus to destroy(6) 
                 in the set operation.
                 Options: 
                 1. active(1)      -indicates the query operation
                 2. createAndGo(4) -indicates creating an RRPP domain
                 3. destroy(6)     -indicates deleting an RRPP domain
                "
            ::= { hwRrppDomainEntry 5 }
        
        hwRrppRingTable OBJECT-TYPE
            SYNTAX SEQUENCE OF HwRrppRingEntry
            MAX-ACCESS not-accessible
            STATUS current
            DESCRIPTION
                "Used to manage RRPP rings, such as create and delete ring, enable and disable 
                 ring, and query the basic information of ring.
                 The indexes of this table are hwRrppDomainID and hwRrppRingID.
                "
            ::= { hwRrppTable 2 }
        
        hwRrppRingEntry OBJECT-TYPE
            SYNTAX HwRrppRingEntry
            MAX-ACCESS not-accessible
            STATUS current
            DESCRIPTION
                "Used to manage RRPP rings, such as create and delete ring, enable and disable 
                 ring, and query the basic information of ring.
                 The indexes of this entry are hwRrppDomainID and hwRrppRingID.
                "
            INDEX { hwRrppDomainID, hwRrppRingID }
            ::= { hwRrppRingTable 1 }
        
        HwRrppRingEntry ::=
            SEQUENCE { 
                hwRrppRingID
                    Integer32,
                hwRrppRingEnableStatus
                    EnabledStatus,
                hwRrppRingActive
                    INTEGER,
                hwRrppRingState
                    INTEGER,
                hwRrppRingNodeMode
                    INTEGER,
                hwRrppRingPrimaryPort
                    Integer32,
                hwRrppRingSecondaryPort
                    Integer32,
                hwRrppRingLevel
                    INTEGER,
                hwRrppRingRowStatus
                    RowStatus
             }

        hwRrppRingID OBJECT-TYPE
            SYNTAX Integer32 (1..64)
            MAX-ACCESS accessible-for-notify
            STATUS current
            DESCRIPTION
                "Indicates the ID of the RRPP ring. This value cannot be modified after it is created.
                "
            ::= { hwRrppRingEntry 1 }
        
        hwRrppRingEnableStatus OBJECT-TYPE
            SYNTAX EnabledStatus
            MAX-ACCESS read-create
            STATUS current
            DESCRIPTION
                "Indicates the RRPP ring status.
                 Options: 
                 1. enabled(1)  -indicates the RRPP ring switch is on
                 2. disabled(2) -indicates the RRPP ring switch is off
                 Default: disabled(2)
                "
            ::= { hwRrppRingEntry 2 }
        
        hwRrppRingActive OBJECT-TYPE
            SYNTAX INTEGER
                {
                active(1),
                inactive(2)
                }
            MAX-ACCESS read-only
            STATUS current
            DESCRIPTION
                "Indicates the activation status of the RRPP ring. The RRPP ring is in the active 
                 state only when RRPP is globally enabled and the RRPP ring is enabled.
                 Options: 
                 1. active(1)   -indicates the activation status of the RRPP ring is active
                 2. inactive(2) -indicates the activation status of the RRPP ring is inactive
                "
            ::= { hwRrppRingEntry 3 }
        
        hwRrppRingState OBJECT-TYPE
            SYNTAX INTEGER
                {
                unknown(1),
                health(2),
                fault(3)
                }
            MAX-ACCESS read-only
            STATUS current
            DESCRIPTION
                "Indicates the running status of the RRPP ring.
                 Options: 
                 1. unknown(1) -indicates the running status is unknown
                 2. health(2)  -indicates the running status is health
                 3. fault(3)   -indicates the running status is fault
                "
            ::= { hwRrppRingEntry 4 }
        
        hwRrppRingNodeMode OBJECT-TYPE
            SYNTAX INTEGER
                {
                master(1),
                transit(2),
                edge(3),
                assistantEdge(4)
                }
            MAX-ACCESS read-create
            STATUS current
            DESCRIPTION
                "Indicates the node mode of the RRPP ring. Each ring has only one master node and other 
                 nodes are configured as transit nodes.
                 Options: 
                 1. master(1)         -indicates the node mode of the RRPP ring is master
                 2. transit(2)        -indicates the node mode of the RRPP ring is transit
                 3. edge(3)           -indicates the node mode of the RRPP ring is edge
                 4. assistantEdge(4)  -indicates the node mode of the RRPP ring is assistantEdge                                  
                "
            ::= { hwRrppRingEntry 5 }
        
        hwRrppRingPrimaryPort OBJECT-TYPE
            SYNTAX Integer32
            MAX-ACCESS read-create
            STATUS current
            DESCRIPTION
                "Indicates the ID of the primary port in the RRPP ring.
                "
            ::= { hwRrppRingEntry 6 }
        
        hwRrppRingSecondaryPort OBJECT-TYPE
            SYNTAX Integer32
            MAX-ACCESS read-create
            STATUS current
            DESCRIPTION
                "Indicates the ID of the secondary port in the RRPP ring
                "
            ::= { hwRrppRingEntry 7 }
        
        hwRrppRingLevel OBJECT-TYPE
            SYNTAX INTEGER
                {
                majorRing(0),
                subRing(1)
                }
            MAX-ACCESS read-create
            STATUS current
            DESCRIPTION
                "Indicates the level of the RRPP ring.
                 Options: 
                 1. majorRing(0) -indicates the RRPP ring is major
                 2. subRing(1)   -indicates the RRPP ring is subsidiary
                "
            ::= { hwRrppRingEntry 8 }
        
        hwRrppRingRowStatus OBJECT-TYPE
            SYNTAX RowStatus
            MAX-ACCESS read-create
            STATUS current
            DESCRIPTION
                "Indicates the row status and is used to create or delete an RRPP ring. 
                 It only supports the createAndGo(4) and destroy(6) operations. During query, 
                 active(1) is fixedly returned for this leaf.
                 When creating an RRPP ring, you must enter hwRrppRingNodeMode, hwRrppRingPrimaryPort, 
                 hwRrppRingSecondaryPort, and hwRrppRingLevel, and set hwRrppRingRowStatus to createAndGo(4) 
                 in the set operation. hwRrppRingEnableStatus is optional.
                 When deleting an RRPP ring, you must ensure that the ring to be deleted is disabled 
                 and you must set hwIpDslamMacPoolRowStatus to destroy(6) in the set operation.
                 Options:
                 1. active(1)      -indicates the query operation
                 2. createAndGo(4) -indicates creating an RRPP ring
                 3. destroy(6)     -indicates deleting an RRPP ring
                "
            ::= { hwRrppRingEntry 9 }

        hwRrppPortTable OBJECT-TYPE
            SYNTAX SEQUENCE OF HwRrppPortEntry
            MAX-ACCESS not-accessible
            STATUS current
            DESCRIPTION
                "Used to manage RRPP ports, query the information about RRPP ports.
                 The indexes of this table are hwRrppDomainID, hwRrppRingID and hwRrppPortID. 
                "
            ::= { hwRrppTable 3 }
        
        hwRrppPortEntry OBJECT-TYPE
            SYNTAX HwRrppPortEntry
            MAX-ACCESS not-accessible
            STATUS current
            DESCRIPTION
                "Used to manage RRPP ports, query the information about RRPP ports.
                 The indexes of this entry are hwRrppDomainID, hwRrppRingID and hwRrppPortID.
                "
            INDEX 
                { 
                hwRrppDomainID, 
                hwRrppRingID, 
                hwRrppPortID 
                }
            ::= { hwRrppPortTable 1 }
        
        HwRrppPortEntry ::=
            SEQUENCE { 
                hwRrppPortID
                    InterfaceIndex,
                hwRrppPortType
                    INTEGER,
                hwRrppPortRole
                    INTEGER,
                hwRrppPortState
                    INTEGER,
                hwRrppPortRXError
                    Counter32,
                hwRrppPortRXHello
                    Counter32,
                hwRrppPortRXLinkUp
                    Counter32,
                hwRrppPortRXLinkDown
                    Counter32,
                hwRrppPortRXCommonFlush
                    Counter32,
                hwRrppPortRXCompleteFlush
                    Counter32,
                hwRrppPortRXEdgeHello
                    Counter32,
                hwRrppPortRXMajorFault
                    Counter32,
                hwRrppPortTXError
                    Counter32,
                hwRrppPortTXHello
                    Counter32,
                hwRrppPortTXLinkUp
                    Counter32,
                hwRrppPortTXLinkDown
                    Counter32,
                hwRrppPortTXCommonFlush
                    Counter32,
                hwRrppPortTXCompleteFlush
                    Counter32,
                hwRrppPortTXEdgeHello
                    Counter32,
                hwRrppPortTXMajorFault
                    Counter32
             }

        hwRrppPortID OBJECT-TYPE
            SYNTAX InterfaceIndex 
            MAX-ACCESS not-accessible
            STATUS current
            DESCRIPTION
                "Indicates the ID of the port in the RRPP ring. 
                "
            ::= { hwRrppPortEntry 1 }
        
        hwRrppPortType OBJECT-TYPE
            SYNTAX INTEGER
                {
                fe(1),
                ge(2),
                ve(3),
                ethtrunk(4)
                }
            MAX-ACCESS read-only
            STATUS current
            DESCRIPTION
                "Indicates the type of the port in the RRPP ring.
                 Options: 
                 1. fe(1)       -indicates the type of the port in the RRPP ring is fe
                 2. ge(2)       -indicates the type of the port in the RRPP ring is ge
                 3. ve(3)       -indicates the type of the port in the RRPP ring is ve
                 4. ethtrunk(4) -indicates the type of the port in the RRPP ring is ethtrunk
                "
            ::= { hwRrppPortEntry 2 }

        hwRrppPortRole OBJECT-TYPE
            SYNTAX INTEGER
                {
                primary(1),
                secondary(2),
                common(3),
                edge(4)
                }
            MAX-ACCESS read-only
            STATUS current
            DESCRIPTION
                "Indicates the role of the port in the RRPP ring.
                 Options: 
                 1. primary(1)   -indicates the role of the port in the RRPP ring is primary
                 2. secondary(2) -indicates the role of the port in the RRPP ring is secondary
                 3. common(3)    -indicates the role of the port in the RRPP ring is common
                 4. edge(4)      -indicates the role of the port in the RRPP ring is edge                 
                "
            ::= { hwRrppPortEntry 3 }
        
        hwRrppPortState OBJECT-TYPE
            SYNTAX INTEGER
                {
                unknown(1),
                unblocked(2),
                blocked(3),
                down(4)
                }
            MAX-ACCESS read-only
            STATUS current
            DESCRIPTION
                "Indicates the status of the port in the RRPP ring.
                 Options: 
                 1. unknown(1)   -indicates the status of the port in the RRPP ring is unknown
                 2. unblocked(2) -indicates the status of the port in the RRPP ring is up
                 3. blocked(3)   -indicates the status of the port in the RRPP ring is blocked
                 4. down(4)      -indicates the status of the port in the RRPP ring is down
                "
            ::= { hwRrppPortEntry 4 }
        
        hwRrppPortRXError OBJECT-TYPE
            SYNTAX Counter32
            MAX-ACCESS read-only
            STATUS current
            DESCRIPTION
                "Indicates the number of invalid RRPP packets received by the port.
                "
            ::= { hwRrppPortEntry 5 }
        
        hwRrppPortRXHello OBJECT-TYPE
            SYNTAX Counter32
            MAX-ACCESS read-only
            STATUS current
            DESCRIPTION
                "Indicates the number of hello packets received by the port.
                "
            ::= { hwRrppPortEntry 6 }
        
        hwRrppPortRXLinkUp OBJECT-TYPE
            SYNTAX Counter32
            MAX-ACCESS read-only
            STATUS current
            DESCRIPTION
                "Indicates the number of linkup packets received by the port.
                "
            ::= { hwRrppPortEntry 7 }

        hwRrppPortRXLinkDown OBJECT-TYPE
            SYNTAX Counter32
            MAX-ACCESS read-only
            STATUS current
            DESCRIPTION
                "Indicates the number of linkdown packets received by the port.
                "
            ::= { hwRrppPortEntry 8 }

        hwRrppPortRXCommonFlush OBJECT-TYPE
            SYNTAX Counter32
            MAX-ACCESS read-only
            STATUS current
            DESCRIPTION
                "Indicates the number of commonflush packets received by the port.
                "
            ::= { hwRrppPortEntry 9 }

        hwRrppPortRXCompleteFlush OBJECT-TYPE
            SYNTAX Counter32
            MAX-ACCESS read-only
            STATUS current
            DESCRIPTION
                "Indicates the number of completeflush packets received by the port.
                "
            ::= { hwRrppPortEntry 10 }

        hwRrppPortRXEdgeHello OBJECT-TYPE
            SYNTAX Counter32
            MAX-ACCESS read-only
            STATUS current
            DESCRIPTION
                "The statistics of edge-hello packets received
                 from this port on specified ring.
                 Instruction
                 When edge-node sends edge-hello packets, 
                 assistantEdge-node will receive its own edge-hello
                 packets from the common link and the master ring.
                "
            ::= { hwRrppPortEntry 11 }

        hwRrppPortRXMajorFault OBJECT-TYPE
            SYNTAX Counter32
            MAX-ACCESS read-only
            STATUS current
            DESCRIPTION
                "Indicates the number of majorfault packets received by the port.
                "
            ::= { hwRrppPortEntry 12 }

        hwRrppPortTXError OBJECT-TYPE
            SYNTAX Counter32
            MAX-ACCESS read-only
            STATUS current
            DESCRIPTION
                "Indicates the number of invalid RRPP packets sent by the port.
                "
            ::= { hwRrppPortEntry 13 }

        hwRrppPortTXHello OBJECT-TYPE
            SYNTAX Counter32
            MAX-ACCESS read-only
            STATUS current
            DESCRIPTION
                "Indicates the number of hello packets sent by the port.
                "
            ::= { hwRrppPortEntry 14 }

        hwRrppPortTXLinkUp OBJECT-TYPE
            SYNTAX Counter32
            MAX-ACCESS read-only
            STATUS current
            DESCRIPTION
                "Indicates the number of linkup packets sent by the port.
                "
            ::= { hwRrppPortEntry 15 }

        hwRrppPortTXLinkDown OBJECT-TYPE
            SYNTAX Counter32
            MAX-ACCESS read-only
            STATUS current
            DESCRIPTION
                "Indicates the number of linkdown packets sent by the port.
                "
            ::= { hwRrppPortEntry 16 }

        hwRrppPortTXCommonFlush OBJECT-TYPE
            SYNTAX Counter32
            MAX-ACCESS read-only
            STATUS current
            DESCRIPTION
                "Indicates the number of commonflush packets sent by the port.
                "
            ::= { hwRrppPortEntry 17 }

        hwRrppPortTXCompleteFlush OBJECT-TYPE
            SYNTAX Counter32
            MAX-ACCESS read-only
            STATUS current
            DESCRIPTION
                "Indicates the number of completeflush packets sent by the port.
                "
            ::= { hwRrppPortEntry 18 }

        hwRrppPortTXEdgeHello OBJECT-TYPE
            SYNTAX Counter32
            MAX-ACCESS read-only
            STATUS current
            DESCRIPTION
                "The statistics of edge-hello packets sent
                 from this port on specified ring.
                "
            ::= { hwRrppPortEntry 19 }

        hwRrppPortTXMajorFault OBJECT-TYPE
            SYNTAX Counter32
            MAX-ACCESS read-only
            STATUS current
            DESCRIPTION
                "Indicates the number of majorfault packets sent by the port.
                "
            ::= { hwRrppPortEntry 20 }

        hwRrppNotifications OBJECT IDENTIFIER ::= { hwRrpp 3 }

        hwRrppRingRecover NOTIFICATION-TYPE
            OBJECTS 
                { 
                hwRrppDomainID, 
                hwRrppRingID 
                }
            STATUS current
            DESCRIPTION 
                "Trap message is generated by master-node on
                 the ring when the ring recovers from fault.
                "
            ::= { hwRrppNotifications 1 }

        hwRrppRingFail NOTIFICATION-TYPE
            OBJECTS { hwRrppDomainID, hwRrppRingID }
            STATUS current
            DESCRIPTION 
                "Trap message is generated by master-node on
                 the ring when the ring fails.
                "
            ::= { hwRrppNotifications 2 }

        hwRrppMultiMaster NOTIFICATION-TYPE
            OBJECTS 
                { 
                hwRrppDomainID, 
                hwRrppRingID 
                }
            STATUS current
            DESCRIPTION 
                "Trap message is generated by master-node when
                 it detects there are more than one master-node
                 on the ring.
                "
            ::= { hwRrppNotifications 3 }

        hwRrppMibGroup OBJECT IDENTIFIER ::= { hwRrpp 4 }

        hwRrppGlobalGroup OBJECT-GROUP
            OBJECTS 
                { 
                hwRrppEnableStatus 
                }
            STATUS current
            DESCRIPTION 
                "Indicates the RRPP global status.
                "
            ::= { hwRrppMibGroup 1 }

        hwRrppDomainGroup OBJECT-GROUP
            OBJECTS 
                { 
                hwRrppDomainID, 
                hwRrppDomainControlVlanID, 
                hwRrppDomainHelloTime, 
                hwRrppDomainFailTime, 
                hwRrppDomainRowStatus
                }
            STATUS current
            DESCRIPTION 
                " Collection of RRPP domain's basic information.
                "
            ::= { hwRrppMibGroup 2 }

        hwRrppRingGroup OBJECT-GROUP
            OBJECTS 
                { 
                hwRrppRingID, 
                hwRrppRingEnableStatus, 
                hwRrppRingActive, 
                hwRrppRingState, 
                hwRrppRingNodeMode, 
                hwRrppRingPrimaryPort, 
                hwRrppRingSecondaryPort, 
                hwRrppRingLevel, 
                hwRrppRingRowStatus 
                }
            STATUS current
            DESCRIPTION 
                "Collection of RRPP ring's basic information.
                "
            ::= { hwRrppMibGroup 3 }

        hwRrppPortGroup OBJECT-GROUP
            OBJECTS 
                { 
                hwRrppPortType, 
                hwRrppPortRole, 
                hwRrppPortState, 
                hwRrppPortRXError, 
                hwRrppPortRXHello, 
                hwRrppPortRXLinkUp, 
                hwRrppPortRXLinkDown, 
                hwRrppPortRXCommonFlush, 
                hwRrppPortRXCompleteFlush, 
                hwRrppPortRXEdgeHello, 
                hwRrppPortRXMajorFault, 
                hwRrppPortTXError, 
                hwRrppPortTXHello, 
                hwRrppPortTXLinkUp, 
                hwRrppPortTXLinkDown, 
                hwRrppPortTXCommonFlush, 
                hwRrppPortTXCompleteFlush, 
                hwRrppPortTXEdgeHello, 
                hwRrppPortTXMajorFault 
                }
            STATUS current
            DESCRIPTION 
                "Collection of RRPP port's basic information.
                "
            ::= { hwRrppMibGroup 4 }

        hwRrppNotificationGroup NOTIFICATION-GROUP
            NOTIFICATIONS 
                { 
                hwRrppRingRecover, 
                hwRrppRingFail, 
                hwRrppMultiMaster 
                }
            STATUS current
            DESCRIPTION 
                "Collection of RRPP notifications that will be generated when RRPP events occur.
                "
            ::= { hwRrppMibGroup 5 }

    END
