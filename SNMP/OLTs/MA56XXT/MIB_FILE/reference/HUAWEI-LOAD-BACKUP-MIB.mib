-- =========================================================================
-- Copyright (C) 2016 by HUAWEI TECHNOLOGIES. All rights reserved.
-- Description: This mib provides loading, backup and patch-related functions.
-- Reference:
-- Version: V4.21
-- ========================================================================
    HUAWEI-LOAD-BACKUP-MIB DEFINITIONS ::= BEGIN
        IMPORTS
            hwFrameIndex, hwSlotIndex
                FROM HUAWEI-DEVICE-MIB
            huaweiUtility
                FROM HUAWEI-MIB
            HWPCBType
                FROM HUAWEI-TC-MIB
            IpAddress, Integer32, Unsigned32, OBJECT-TYPE,
            MODULE-IDENTITY, NOTIFICATION-TYPE
                FROM SNMPv2-SMI
            RowStatus, DisplayString, DateAndTime
                FROM SNMPv2-TC
            InetAddressType, InetAddress
                FROM INET-ADDRESS-MIB;


        hwLoadBackup MODULE-IDENTITY
            LAST-UPDATED "201606140000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION
              "
              This mib provides loading, backup and patch-related functions.
              "

--  Revision history 
             REVISION    "201606140000Z"
             DESCRIPTION "V4.21,
                          Add enum values scriptWithResult(201) in hwLoadContent.
                          Add enum values vsCreate(12), vsDelete(13), vsAddPhysicalResource(14) and vsDeletePhysicalResource(15) in hwOperationReqType."

             REVISION    "201604120000Z"
             DESCRIPTION "V4.20,
                          Add the node hwAutoLoadBoardStartTrap of hwLoadBackupAlarmTrapsPrefix.
                          Add the node hwAutoLoadBoardCompleteTrap of hwLoadBackupAlarmTrapsPrefix.
                          Add the node hwAutoLoadBoardFailTrap of hwLoadBackupAlarmTrapsPrefix."

             REVISION    "201511240000Z"
             DESCRIPTION "V4.19,
                          Modify the size of hwLoadFileName from (0-127) to (0-128)."

             REVISION    "201507040000Z"
             DESCRIPTION "V4.18,
                          Add enum values rpscertfile(200) in hwLoadContent."

             REVISION    "201507010000Z"
             DESCRIPTION "V4.17,
                          Add the node hwLoadOperFlag of hwLoadBackupMon."

             REVISION    "201506160000Z"
             DESCRIPTION "V4.16,
                          Add enum values cmcperformance(14) in hwFileDataType.
                          Add several enums in the DESCRIPTION of hwBackupPeriodTable and hwBackupPeriodEntry.
                          Add several enums in the DESCRIPTION of hwBackupByHandTable and hwBackupByHandEntry."

             REVISION    "201505070000Z"
             DESCRIPTION "V4.15,
                          Add enum values opticalfile(149) in hwLoadContent."
                          
             REVISION    "201503130000Z"
             DESCRIPTION "V4.14,
                          Add enum values rootCAfile(108) in hwLoadContent.
                          Add enum values mfgCAfile(109) in hwLoadContent."

             REVISION    "201503050000Z"
             DESCRIPTION "V4.13,
                          Add enum values boardspectrum(150) in hwBackupContent."
                          
             REVISION    "201502100000Z"
             DESCRIPTION "V4.12,
                          Add enum values atiboardelabel(148) in hwLoadContent.
                          Add enum values atiboardelabel(141) in hwBackupContent."

             REVISION    "201501280000Z"
             DESCRIPTION "V4.11,
                          Delete enum values voice(78) in hwLoadContent."

             REVISION    "201501060000Z"
             DESCRIPTION "V4.10,
                          Add enum values sslcertfile(145) in hwLoadContent.
                          Add enum values sslkeyfile(146) in hwLoadContent.
                          Add enum values sslcrlfile(147) in hwLoadContent."

             REVISION    "201412160000Z"
             DESCRIPTION "V4.09,
                          Add the node hwDataReplaceResult of hwLoadPara."

             REVISION    "201412060000Z"
             DESCRIPTION "V4.08,
                          Add the node hwLoadInStandbyChannelTrap of hwLoadBackupAlmTrapsPrefix."

             REVISION    "201411060000Z"
             DESCRIPTION "V4.07,
                          Add the node hwLoadEncryptAlgorithm hwLoadEncryptKey and hwLoadEncryptIV for hwLoadParaTable."

             REVISION    "201410250000Z"
             DESCRIPTION "V4.06,
                          Add enum values rootfs(140)  in hwLoadContent.
                          Add enum values uimage(141)  in hwLoadContent.
                          Add enum values initrd(142)  in hwLoadContent.
                          Add enum values rootfs(138)  in hwBackupContent.
                          Add enum values uimage(139)  in hwBackupContent.
                          Add enum values initrd(140)  in hwBackupContent."

             REVISION    "201410230000Z"
             DESCRIPTION "V4.05,
                          Add enum values frameelabel(144)  in hwLoadContent.
                          Add enum values frameelabel(137)  in hwBackupContent."

             REVISION    "201410060000Z"
             DESCRIPTION "V4.04,
                          Add enum values boardinfo(9) in hwFileDataType.
                          Add several enums in the DESCRIPTION of hwBackupPeriodTable and hwBackupPeriodEntry.
                          Add several enums in the DESCRIPTION of hwBackupByHandTable and hwBackupByHandEntry."

             REVISION    "201409120000Z"
             DESCRIPTION "V4.03,
                          Modify the description of hwBackupParaTable"

             REVISION    "201409030000Z"
             DESCRIPTION "V4.02,
                          Modify the Revision history of V3.96 and V3.97"

             REVISION    "201408290000Z"
             DESCRIPTION "V4.01,
                          Modify the size of hwFilePathName from (0-64) to (0-128)."

             REVISION    "201408150000Z"
             DESCRIPTION "V4.00,
                          Add enum values xdsl-port-reset-info(136) in hwBackupContent."

             REVISION    "201407280000Z"
             DESCRIPTION "V3.99,
                          Modified the range of hwNewPatchName."

             REVISION    "201406300000Z"
             DESCRIPTION "V3.98,
                          1. removed all hyphens (-) from enumerated values of hwLoadContent.
                          2. removed all hyphens (-) from enumerated values of hwBackupContent"

             REVISION    "201405120000Z"
             DESCRIPTION "V3.97,
                          Add enum values udm(13) in hwFileDataType.
                          Add several enums in the DESCRIPTION of hwBackupPeriodTable and hwBackupPeriodEntry.
                          Add several enums in the DESCRIPTION of hwBackupByHandTable and hwBackupByHandEntry."

            REVISION    "201405300000Z"
            DESCRIPTION "V3.96,
                         Modified the description of hwBackupPeriodTable.
                         Modified the description of hwBackupPeriodEntry.
                         Modified the description of hwBackupByHandTable.
                         Modified the description of hwBackupByHandEntry."

             REVISION    "201404220000Z"
             DESCRIPTION "V3.95, Modified the index of hwPatchNewEntry."

             REVISION    "201402250000Z"
             DESCRIPTION "V3.94,
                          Modified the description of hwBackupMode.
                          Modified the description of hwLoadMode.
                          Modified the description of hwFileServerMode."

             REVISION    "201312240000Z"
             DESCRIPTION "V3.93,
                          Add enum values port(76) in hwBackupContent.
                          Add enum values vectoring(135) in hwBackupContent. "

             REVISION    "201312130000Z"
             DESCRIPTION "V3.92, Add the node hwOperationFileDigest for hwOperationInfoTable."

             REVISION    "201311200000Z"
             DESCRIPTION "V3.91, add enum values userfile(134) in hwBackupContent for the user common file."

             REVISION    "201311190000Z"
             DESCRIPTION "V3.90,Add enum values ont-interoperability-file(134) in hwLoadContent."

             REVISION    "201311110000Z"
             DESCRIPTION "V3.89,Modify access type of hwNewFileDataType."

             REVISION    "201309120000Z"
             DESCRIPTION "V3.88,Delte port(76) in the description of hwBackupContent."

             REVISION    "201307250000Z"
             DESCRIPTION "V3.87,
                          Modify the size of hwBackupFileName from (0-127) to (0-128).
                          Modify the size of hwBackupUserName from (0-31) to (0-40).
                          Modify the size of hwBackupPassword from (0-16) to (0-40)."

             REVISION    "201307160000Z"
             DESCRIPTION "V3.86, Add enum values ibmsFile(133) in hwBackupContent."

             REVISION    "201306040000Z"
             DESCRIPTION "V3.85, Add enum values crosstalk-coupling-matrix(131) in hwBackupContent.
                          Add enum values vdsl2-xlin(132)  in hwBackupContent.
                          Add hwBackupPrivatePara for hwBackupParaEntry."

             REVISION    "201304230000Z"
             DESCRIPTION "V3.84, Change the status of hwSDLoadResult from current to obsolete."

             REVISION    "201301150000Z"
             DESCRIPTION "V3.83, Delte enum values port(76) in hwBackupContent."

             REVISION    "201212130000Z"
             DESCRIPTION "V3.82, Add the status of Gpon protect group for the node hwStatusCollectMask.
                         Add the status of link aggregation for the node hwStatusCollectMask.
                         Add the status of ServiceProcessBoard protect group for the node hwStatusCollectMask."

             REVISION    "201212100000Z"
             DESCRIPTION "V3.81, Add enum values powerRunData(123) in hwBackupContent."

             REVISION    "201210220000Z"
             DESCRIPTION "V3.80, Add enum values deviceinfo(9) in hwFileDataType."

             REVISION    "201210300000Z"
             DESCRIPTION "V3.79, Add boardversion status for the node hwStatusCollectMask."

             REVISION    "201209250000Z"
             DESCRIPTION "V3.78, Add enum values deviceCapabilityFile(122) in hwBackupContent."

             REVISION    "201208270000Z"
             DESCRIPTION "V3.77, Add enum values cabinetelabel(120) in hwLoadContent.
                          Add enum values cabinetelabel(120) in hwBackupContent.
                          Add enum values batteryelabel(121) in hwBackupContent."

             REVISION    "201208250000Z"
             DESCRIPTION "V3.76,1. Modified the description of hwPatchNewTable.
                                2. Modified the description of hwPatchNewEntry.
                                3. Modified the description of hwNewPatchAdminStatus.
                                4. Modified the description of hwNewPatchRely.
                                5. Modified the description of hwNewPatchRequestID."

             REVISION    "201208140000Z"
             DESCRIPTION "V3.75, Modified the description of hwOperationProgress.
                         Add unit to hwOperationProgress."

             REVISION    "201208070000Z"
             DESCRIPTION "V3.74,1. Add enum values serviceboardloading(13) in hwOperationReqStatus. "

             REVISION    "201207230000Z"
             DESCRIPTION "V3.73, Modified the illegal comment symbol for FT."

             REVISION    "201207050000Z"
             DESCRIPTION "V3.72, Modified enum values ontfile(9) to ontfile(11) in hwFileDataType."

             REVISION    "201207040000Z"
             DESCRIPTION "V3.71, Add enum values ontfile(9) in hwFileDataType."

             REVISION    "201206050000Z"
             DESCRIPTION "V3.70, Add the node hwStatusCollectReady for hwStatusCollect."

             REVISION    "201202100000Z"
             DESCRIPTION "V3.69,1. Modified the description of hwLoadRequestId, hwBackupRequestID, hwBackupPositionPara. "

             REVISION    "201201050000Z"
             DESCRIPTION "V3.68, Add enum values device-cap-xml(84) in hwBackupContent for device capability information xml file."

             REVISION    "201112290000Z"
             DESCRIPTION "V3.67, modified a descripition of autobackup.
                         Add enum values bulkstat(8) in hwFileDataType.
                         Values patchactive(8), patchdeactive(9), patchdelete(10) and patchrun(11) are added for hwOperationReqType."

             REVISION    "201111200000Z"
             DESCRIPTION "V3.66, add enum values userfile(80) in hwLoadContent for the user common file.
                         Add enum values interruptedAutoUpgrade(7) in hwOperationReqType.
                         Add enum values ioupgrade(11) and systemreboot(12) in hwOperationReqStatus."

             REVISION    "201110180000Z"
             DESCRIPTION "V3.65, Add potsvoltage status for the node hwStatusCollectMask."

             REVISION    "201111090000Z"
             DESCRIPTION "V3.64, modified description in hwLoadBackupResult and hwOperationReqErrStatus.
                        And modified the description in hwLoadServerPort and hwBackupServerPort."

             REVISION    "201108220000Z"
             DESCRIPTION "V3.63, modified enum and description in hwPatchOperation."

             REVISION    "201107190000Z"
             DESCRIPTION "V3.62, Add the node hwStatusCollectResultSize for hwStatusCollect.
                         Add enum values hwStatusCollectInfo(83) in hwBackupContent for hm status information file.
                         Values h248mginterface(11), mgcpmginterface(12), tcu(13), uplinkporttraffic(14),
                         onustatus(15), xpontraffic(16) and mxusnmpinfo(17) are added for hwStatusCollectMask."

             REVISION    "201105020000Z"
             DESCRIPTION "V3.61, delete enum values interception(80) from hwLoadContent.
                         Add enum values resetRecord(82) in hwBackupContent for backup board debug information."

             REVISION    "201101200000Z"
             DESCRIPTION "V3.60, modified enum description interception(80) to lawful-interception(80) in hwLoadContent."

             REVISION    "201012290000Z"
             DESCRIPTION "V3.59, added hwProgramAndDataInfoTable for hwLoadBackupMon."

             REVISION    "201012200000Z"
             DESCRIPTION "V3.58, Add enum values interception(80) in hwLoadContent for the lawful interception.
                         Modified the description of hwLoadPositionPara and hwPatchResult."

             REVISION    "201012080000Z"
             DESCRIPTION "V3.57, modified the node hwOntIndex name ,from hwOntIndex to hwUpdateOntIndex."

             REVISION    "201011220000Z"
             DESCRIPTION "V3.56, Value ap (10) is added for hwStatusCollectMask."

             REVISION    "201011090000Z"
             DESCRIPTION "V3.55, The description of this MIB is modified according to the tool."

             REVISION    "201009190000Z"
             DESCRIPTION "V3.54, added hwLoadPacketSmart for hwLoadParaEntry.
                         Add eoc firmware type to hwLoadContent."

             REVISION    "201008300000Z"
             DESCRIPTION "V3.53, added hwSaveResult for standard trap.
                          Add enum values trace(8) in hwNewFileDataType."

             REVISION    "201008250000Z"
             DESCRIPTION "V3.52, modified the contact-info and the revision history. Modified the description of leaves.
                          Add enum values voice(78) in hwLoadContent for the syntax and semantics of simpletest."

             REVISION     "201008160000Z"
             DESCRIPTION  "V3.51, The system supports the definitions of a new standard trap node hwPatchNeedResetBoardTrap."

             REVISION     "201007190000Z"
             DESCRIPTION  "V3.50, 1. The description of the object is modified. The objects hwLoadAdminStatus, hwConfigChangedSequence,
                           hwServerIpAddrForTerminal, hwBackupGuageTrap, and all the objects in hwCfgOperTable and hwPatchStatTable are abandoned.
                           2. The object name is changed. For instance, the name of hwBackUpOperationStartTrap is changed to hwSaveStartTrap,
                           the name of hwBackUpOperationCompleteTrap is changed to hwSaveCompleteTrap,
                           the name of hwBackupFileLenth is changed to hwBackupFileLength,
                           the name of hwClodePatchInconsistentTrap is changed to hwColdPatchInconsistentTrap,
                           the name of hwPatActiveTrap is changed to hwPatchInActiveTrap,
                           the name of hwPatDeActiveTrap is changed to hwPatchInDeActiveTrap,
                           the name of hwPatRestorecoldTrap is changed to hwPatchRestoreTrap,
                           and the name of hwLoadBackupAlmTraps is changed to hwLoadBackupAlarmTraps.
                           3. The enum values of hwLoadBackObject are changed to the following enum values for DT requirements:
                           loadbackupobjectmasterboard(1),
                           loadbackupobjectmastersubboard(2),
                           loadbackupobjectslaveboard(3),
                           loadbackupobjectslavesubboard(4),
                           loadbackupobjectmasterslave(5),
                           loadbackupobjectserviceboard(6),
                           loadbackupobjectservicesubboard(7),
                           loadbackupobjectserviceport(8),
                           loadbackupobjectframeboard(9),
                           loadbackupobjectemmboard(10),
                           loadbackupobjectbackboard(11),
                           loadbackupobjectsystem(12)
                           4. Add objects hwNewFileDataType and hwAutoBackupResult for DT requirements.
                           5. Add object hwLoadExtServerInetAddressType in hwLoadParaTable to set IP type of load server.
                           Add object hwLoadExtServerIPAddress in hwLoadParaTable to set IP address of load server.
                           Add object hwBackupExtServerInetAddressType in hwBackupParaTable to set IP type of load server.
                           Add object hwBackupExtServerIPAddress in hwBackupParaTable to set IP address of load server.
                           6. Values frame-pnp(79),board-pnp(80),subboard-pnp(81) are added for hwBackupContent.
                           Add hwBackupResouce for hwBackupParaEntry to identify specified pnp data."

             REVISION     "201007090000Z"
             DESCRIPTION  "V3.49, Add voice type to hwBackupContent."

             REVISION     "201005170000Z"
             DESCRIPTION  "V3.48, Add enum (file:77) in hwLoadContent leaf node for the supporting general file type."

             REVISION     "201004020000Z"
             DESCRIPTION  "V3.47, The system supports the definitions of a new standard trap node and associated trapparameter nodes."

             REVISION     "201003030000Z"
             DESCRIPTION  "V3.46, DT requirements are implemented and the syntax and semantics of SIMPLETEST are changed."

             REVISION     "201001290000Z"
             DESCRIPTION  "V3.45, This MIB is modified according to DT requirements. Trap definitions of associated alarms are added."

             REVISION     "201001290000Z"
             DESCRIPTION  "V3.44, The system supports the definitions of standard trap nodes and associated trapparameter nodes."

             REVISION     "201001260000Z"
             DESCRIPTION  "V3.43, This MIB does not meet the requirements of SIMPLETEST.
                           Alarms and errors of MIB BROWSER are cleared.MIB description is added according to new requirements."

             REVISION     "200911230000Z"
             DESCRIPTION  "V3.42, Values syncstatus (7), esc (8), and lswport (9) are added for hwStatusCollectMask."

             REVISION     "200911170000Z"
             DESCRIPTION  "V3.41, MIB alarms and errors are cleared."

             REVISION     "200907080000Z"
             DESCRIPTION  "V3.40,  1. Add script type to hwLoadContent.
                           2. Add script type to hwBackupContent.
                           3. Add script type to hwUndoContent."

             REVISION     "200904150000Z"
             DESCRIPTION  "V3.37, Add the function of querying the result of loading
                           files by the host from the SD card when the SC card is used for project deployment."

             REVISION     "200904010000Z"
             DESCRIPTION  "V3.35, Add the function of upgrading the multicast function
                           of the MDU through the OLT (as an agent)."

             REVISION     "200902050000Z"
             DESCRIPTION  "V3.33, Add an object for cancellation of database loading and backup."

             REVISION     "200902030000Z"
             DESCRIPTION  "V3.32, Support the health diagnosis feature."

             REVISION     "200901040000Z"
             DESCRIPTION  "V3.31, Support the batch upgrade of ONTs through the OLT agent.
                           Modify MIB table hwLoadParaTable. Add leaves hwLoadOntType and hwLoadVersionFilter,
                           and MIB table hwAgentUpdateOntTable."

             REVISION     "200804180000Z"
             DESCRIPTION  "V3.29, Support the configuration for automatically loading
                           the file server information through the board software."

             REVISION     "200804110000Z"
             DESCRIPTION  "V3.27, Add enumeration for the loading and backup of the SIP digitmap file."

             REVISION     "200802130000Z"
             DESCRIPTION  "V3.26, Add enumeration of the electronical label(elabel) backup types."

             REVISION     "200801210000Z"
             DESCRIPTION  "V3.25, Add enumeration for the loading and backup of digitmap,
                           H.248 profile, and SIP profile."

             REVISION     "200801080000Z"
             DESCRIPTION  "V3.23, Add the Clone operation during the optimization of the NMS upgrade efficiency."

             REVISION     "200712170000Z"
             DESCRIPTION  "V3.21,Support the optimization of the efficency of SingTel's NMS upgrade."

             REVISION     "200705170000Z"
             DESCRIPTION  "V3.17, Support automatic in-service upgrade."

             REVISION     "200703010000Z"
             DESCRIPTION  "V3.12, Normalize MIB."

             REVISION     "200607310000Z"
             DESCRIPTION  "V3.08,  1. Support the automatic backup feature.
                          2. (SSMP) Support enhancement of the patch functions and support
                          the loading through the XML interface."

             REVISION     "200601040000Z"
             DESCRIPTION  "V3.06, Support the management of the RAD SHDSL terminal."

             REVISION     "200312280000Z"
             DESCRIPTION  "V3.02, Modify according to the requirements of the BWA project."

             REVISION     "200302280000Z"
             DESCRIPTION  "V2.01, Modify according to the MIB requirements of the Brazilian customer."

             REVISION     "200211290000Z"
             DESCRIPTION  "V2.00, Revise the MIB according to the latest fixed-line network
                          standard (backup and loading through the NMS)."

             REVISION    "200210180000Z"
             DESCRIPTION "V1.00, Complete the draft."

            ::= { huaweiUtility 6 }

        hwLoadBackupMon OBJECT IDENTIFIER ::= { hwLoadBackup 1 }

        hwLoadParaTable OBJECT-TYPE
            SYNTAX SEQUENCE OF HwLoadParaEntry
            MAX-ACCESS not-accessible
            STATUS current
            DESCRIPTION
                "
                Load parameter table, used to load various files to the host
                through the NMS. The indexes of this table are hwFrameIndex and hwSlotIndex of the board.
                For example, to load files to the board in slot 3 of frame 0, the index is 0.3.
                "
            ::= { hwLoadBackupMon 1 }

        hwLoadParaEntry OBJECT-TYPE
            SYNTAX HwLoadParaEntry
            MAX-ACCESS not-accessible
            STATUS current
            DESCRIPTION
                "
                Load parameter table, used to load various files to the host
                through the NMS. The indexes of this entry are hwFrameIndex and hwSlotIndex of the board.
                For example, to load files to the board in slot 3 of frame 0, the index is 0.3.
                "
            INDEX { hwFrameIndex, hwSlotIndex }
            ::= { hwLoadParaTable 1 }

        HwLoadParaEntry ::=
            SEQUENCE {
                hwLoadServerIpAddr
                    IpAddress,
                hwLoadMode
                    INTEGER,
                hwLoadFileName
                    OCTET STRING,
                hwLoadContent
                    INTEGER,
                hwLoadBoardType
                    HWPCBType,
                hwLoadPositionPara
                    Integer32,
                hwLoadProcess
                    Integer32,
                hwLoadUserName
                    OCTET STRING,
                hwLoadPassword
                    OCTET STRING,
                hwLoadAdminStatus
                    RowStatus,
                hwLoadOperStatus
                    INTEGER,
                hwLoadRequestId
                    Integer32,
                hwLoadServerPort
                    Unsigned32,
                hwBatchLoadOptions
                    INTEGER,
                hwLoadOntType
                    OCTET STRING,
                hwLoadVersionFilter
                    OCTET STRING,
                hwLoadExtServerInetAddressType
                    InetAddressType,
                hwLoadExtServerIPAddress
                    InetAddress,
                hwLoadPacketSmart
                    INTEGER,
                hwLoadEncryptAlgorithm
                    INTEGER,
                hwLoadEncryptKey
                    OCTET STRING,
                hwLoadEncryptIV
                    OCTET STRING
             }

        hwLoadServerIpAddr OBJECT-TYPE
            SYNTAX IpAddress
            MAX-ACCESS read-write
            STATUS current
            DESCRIPTION
                 "
                 The IP address of file server.
                 "
            ::= { hwLoadParaEntry 1 }

        hwLoadMode OBJECT-TYPE
            SYNTAX INTEGER
                {
                 tftp(1),
                 modem(2),
                 ftp(3),
                 smbLoadAnyBoards(4),
                 sftp(5),
                 other(255)
                }
            MAX-ACCESS read-write
            STATUS current
            DESCRIPTION
              "
              Load protocol.
              Options:
              1.tftp(1)   -indicates that the Trivial File Transfer Protocol (TFTP) is used to perform
                           the loading through the network port. Select tftp(1) when the transmission mode
                           of the server is configured to TFTP. When TFTP is used for the loading, you need
                           not enter the user name (hwLoadUserName) and password (hwLoadPassword).
              2.modem(2)  -indicates that the XMODEM protocol is used to perform the loading through
                           the serial port. When you use the HyperTerminal of the OS to perform serial
                           port configuration on the server, select modem(2). Loading through the serial port
                           does not require networking and maintenance through the command line interface
                           does not require NM software.
              3.ftp(3)    -indicates that the File Transfer Protocol (FTP) is used to perform loading
                           through the network port. When the transmission mode of the server is configured to FTP,
                           select ftp(3). When FTP is used for the loading, you need to enter the user name (hwLoadUserName)
                           and password (hwLoadPassword).
              4.smbLoadAnyBoards(4)-smbLoadAnyBoards.
              5.sftp(5)   -indicates that the Secure File Transfer Protocol (SFTP) is used to perform the loading through
                           the network port. Select sftp(5) when the transmission mode of the server is configured to SFTP.
                           When SFTP is used for the loading, you need to enter the user name (hwLoadUserName)
                           and password (hwLoadPassword). The instructions and data are encrypted during transmission.
              6.other(255)-other.
              The SFTP transmission mode is recommended.
              "
            ::= { hwLoadParaEntry 2 }

        hwLoadFileName OBJECT-TYPE
        SYNTAX OCTET STRING (SIZE (0..128))
        MAX-ACCESS read-write
        STATUS current
        DESCRIPTION
            "
            The name of the file to be loaded.
            "
        ::= { hwLoadParaEntry 3 }

        hwLoadContent OBJECT-TYPE
            SYNTAX INTEGER
                {
                 noloadcontent(-1),
                 program(1),        -- program file
                 database(2),   -- database file
                 patch(3),      -- patch file
                 shellMacro(4),  -- shell macro file
                 resLocal(5),       -- local resource file
                 resGeneral(6),  -- general resource file
                 cpeDrive(7),    -- cpe drive
                 programDatabase(8),    -- database file
                 programBios(9),        -- bios file
                 programApp(10),        -- application program
                 logicFpga(11),     -- fpga logic file
                 logicCpld(12),     -- Cpld  logic file
                 logicPci(13),      -- pci logic file
                 logicAfc(14),      -- afc logic file
                 programMicroCode(15),  -- micro code file
                 programFirmware(16),   -- application program of pinch board
                 programHelp(17),        -- program help file
                 programDataFlow(18),   -- flow file of card management point
                 programBootFile(19),   -- Boot program file of board
                 logciPa(20),       -- Boot program file of board start
                 webExp(21),        -- web exp file
                 webNev(22),        -- web nev file
                 webHelp(23),       -- web help file
                 programBsp(24),        -- bsp program file
                 verBinFile(25),     -- packet file
                 configurationFile(26), -- configuration file
                 configurationIni(40),  -- configuration file of ini formatini
                 configurationEfs(41),  -- configuration file with the header of efs
                 configurationCli(42),  -- configuration file of command line format
                 programCurrent(45),        -- the program being run
                 programOther(46),      -- the program that has not been run presently
                 license(49),             -- license file
                 programchipset(50),     -- AC5 chipset load
                 programExtendedBios(51), --extended bios file
                 programBaseBios(52),   --base bios file
                 logicCpld2(53),         -- cpld2 file
                 logicCpld3(54),         -- cpld3 file
                 extendedBootRom(55),    -- extended BootRom file
                 defaultCfg(56),         -- default configuration file
                 boardManuVersion(57),   -- board manufacture information
                 versionDescribe(58),     -- version description file
                 announcement(59),        --announcement file
                 voice(60),              --voice file
                 boardtemplatefile(61),  --board template file
                 frametemplatefile(62),   --frame template file
                 r2signalingfile(63),   -- r2 signaling file
                 declaration(65),        --declaration file
                 digitmap(66),           -- h248 Digitmap
                 elabel(67),            -- elabel file
                 emuprogram(68),        -- emu program file
                 emuelabel(69),         -- emu elabel file
                 emuproofelabel(70),        -- emu proof elabel file
                 backboardelabel(71),   --frame back board elabel file
                 ioPacketfile(72),      -- ioPacket file
                 h248Profile(73),       -- h248 Profile
                 sipProfile(74),        -- sip Profile
                 sipDigitmap(75),       -- sip Digitmap
                 script(76),             -- script configuration command file
                 file(77),               -- general file
                 eocfirmware(79),         -- eoc firmware file
                 userfile(80),            -- user common file
                 rootCAfile(108),         -- root CA certificate file
                 mfgCAfile(109),          -- CA certificate file
                 cabinetelabel(120),      -- cabinet elabel file
                 ontInteroperabilityfile(134),       -- ONT interoperability file
                 rootfs(140),                -- rootfs file
                 uimage(142),                -- uimage file
                 initrd(143),                -- initrd file
                 frameelabel(144),           -- frame elabel file
                 sslcertfile(145),           -- ssl certificate file
                 sslkeyfile(146),            -- ssl key file
                 sslcrlfile(147),            -- ssl CRL file
                 atiboardelabel(148),        -- ATI board elabel file
                 opticalfile(149),            -- Optical file
                 rpscertfile(200),            -- RPS cert file
                 scriptWithResult(201)       -- script configuration command file with result
                }
            MAX-ACCESS read-write
            STATUS current
            DESCRIPTION
                "
                Type of the loaded file.
                Options:
                1.noloadcontent(-1)               -no file.
                2.program(1)                      -program file.
                3.database(2)                     -database file.
                4.patch(3)                        -patch file.
                5.shellMacro(4)                   -shell macro file.
                6.resLocal(5)                     -local resource file.
                7.resGeneral(6)                   -general resource file.
                8.cpeDrive(7)                     -cpe drive.
                9.programDatabase(8)              -database file.
                10.programBios(9)                 -bios file.
                11.programApp(10)                 -application program.
                12.logicFpga(11)                  -fpga logic file.
                13.logicCpld(12)                  -Cpld logic file.
                14.logicPci(13)                   -pci logic file.
                15.logicAfc(14)                   -afc logic file.
                16.programMicroCode(15)           -micro code file.
                17.programFirmware(16)            -application program of pinch board.
                18.programHelp(17)                -program help file.
                19.programDataFlow(18)            -flow file of card management point.
                20.programBootFile(19)            -Boot program file of board.
                21.logciPa(20)                    -Boot program file of board start.
                22.webExp(21)                     -web exp file.
                23.webNev(22)                     -web nev file.
                24.webHelp(23)                    -web help file.
                25.programBsp(24)                 -bsp program file.
                26.verBinFile(25)                 -packet file.
                27.configurationFile(26)          -configuration file.
                28.configurationIni(40)           -configuration file of ini formatini.
                29.configurationEfs(41)           -configuration file with the header of efs.
                30.configurationCli(42)           -configuration file of command line format.
                31.programCurrent(45)             -the program being run.
                32.programOther(46)               -the program that has not been run presently.
                33.license(49)                    -license file.
                34.programchipset(50)             -AC5 chipset load.
                35.programExtendedBios(51)        -extended bios file.
                36.programBaseBios(52)            -base bios file.
                37.logicCpld2(53)                 -cpld2 file.
                38.logicCpld3(54)                 -cpld3 file.
                39.extendedBootRom(55)            -extended BootRom file.
                40.defaultCfg(56)                 -default configuration file.
                41.boardManuVersion(57)           -board manufacture information.
                42.versionDescribe(58)            -version description file.
                43.announcement(59)               -announcement file.
                44.voice(60)                      -voice file.
                45.boardtemplatefile(61)          -board template file.
                46.frametemplatefile(62)          -frame template file.
                47.r2signalingfile(63)            -r2 signaling file.
                48.declaration(65)                -declaration file.
                49.digitmap(66)                   -h248 Digitmap.
                50.elabel(67)                     -elabel file.
                51.emuprogram(68)                 -emu program file.
                52.emuelabel(69)                  -emu elabel file.
                53.emuproofelabel(70)             -emu proof elabel file.
                54.backboardelabel(71)            -frame back board elabel file.
                55.ioPacketfile(72)              -io-packet file.
                56.h248Profile(73)               -h248 Profile.
                57.sipProfile(74)                -sip Profile.
                58.sipDigitmap(75)               -sip Digitmap.
                59.script(76)                     -script configuration command file.
                60.file(77)                       -general file.
                61.eocfirmware(79)                -eoc firmware file.
                62.userfile(80)                   -user common file.
                63.rootCAfile(108)                -root CA certificate file.
                64.mfgCAfile(109)                 -CA certificate file.
                65.cabinetelabel(120)             -cabinet elabel file.
                66.ontInteroperabilityFile(134) -ONT interoperability file.
                67.rootfs(140)                 -- rootfs file
                68.uimage(142)                 -- uimage file
                69.initrd(143)                 -- initrd file
                70.frameelabel(144)            -- frame elabel file
                71.sslcertfile(145)            -- ssl cert file
                72.sslkeyfile(146)             -- ssl key file
                73.sslcrlfile(147)             -- ssl crl file
                74.atiboardelabel(148)         -- ATI board elabel file
                75.opticalfile(149)            -- Optical file
                76.rpscertfile(200)           -- RPS cert file
                77.scriptWithResult(201)    -script configuration command file with result
                "
            ::= { hwLoadParaEntry 4 }

        hwLoadBoardType OBJECT-TYPE
            SYNTAX HWPCBType
            MAX-ACCESS read-write
            STATUS current
            DESCRIPTION
                "
                The type of the board to be loaded, which is defined in HUAWEI-TC-MIB.mib.
                "
            ::= { hwLoadParaEntry 5 }

        hwLoadPositionPara OBJECT-TYPE
            SYNTAX Integer32
            MAX-ACCESS read-write
            STATUS current
            DESCRIPTION
                "
                Auxiliary parameters for locating a board to be loaded.
                When a file is loaded to an EMU, the value of this parameter is emuID.
                When a file is loaded to a modem or an ONT, the value of this parameter is portID.
                When a file is loaded to a daughter board, the value of this parameter is SubBoardID.
                This parameter is not required for loading the file to other components.
                -1 indicates that the parameter is meaningless.
                "
            ::= { hwLoadParaEntry 6 }

        hwLoadProcess OBJECT-TYPE
            SYNTAX Integer32 (0..100)
            MAX-ACCESS read-only
            STATUS current
            DESCRIPTION
                "
                Loading progress.
                Range: 0-100.
                "
            ::= { hwLoadParaEntry 7 }

        hwLoadUserName OBJECT-TYPE
            SYNTAX OCTET STRING (SIZE (0..31))
            MAX-ACCESS read-write
            STATUS current
            DESCRIPTION
                "
                The name of load user, which is required in FTP mode and SFTP mode
                but is not required in any other modes.
                "
            ::= { hwLoadParaEntry 8 }

        hwLoadPassword OBJECT-TYPE
            SYNTAX OCTET STRING (SIZE (0..16))
            MAX-ACCESS read-write
            STATUS current
            DESCRIPTION
                "
                The load user password, which is required in FTP mode and SFTP mode
                but is not required in any other modes.
                "
            ::= { hwLoadParaEntry 9 }

        hwLoadAdminStatus OBJECT-TYPE
            SYNTAX RowStatus
            MAX-ACCESS read-create
            STATUS obsolete
            DESCRIPTION
                "
                Load Adminstatus. The object is not supported at present.
                "
            ::= { hwLoadParaEntry 10 }

        hwLoadOperStatus OBJECT-TYPE
            SYNTAX INTEGER
                {
                 inition(1),  -- initial state
                 loading(2),  -- loading the file
                 flashing(3), -- saving the file to flash memory.
                 success(4),  -- operation success (include loading success, writing flash success and so on)
                 failure(5)   -- operation failure (include loading failure, writing flash failure and so on)
                }
            MAX-ACCESS read-only
            STATUS current
            DESCRIPTION
                "
                Operational Status. The object is not supported at present.
                Options:
                1.inition(1) -initial state.
                2.loading(2) -loading the file.
                3.flashing(3)-saving the file to flash memory.
                4.success(4) -operation success (include loading success, writing flash success and so on).
                5.failure(5) -operation failure (include loading failure, writing flash failure and so on).
                "
            ::= { hwLoadParaEntry 11 }

        hwLoadRequestId OBJECT-TYPE
            SYNTAX Integer32
            MAX-ACCESS read-write
            STATUS current
            DESCRIPTION
                "
                The loading request ID, which identifies the loading request delivered by the NMS.
                According to the ID, you can query hwOperationInfoTable to obtain the status and
                results of each loading operation.
                A request ID can be any integer in the range of 0-0xFFFFFFFF,
                but the IDs of different loading requests are not duplicate.
                This object cannot be set independently.
                The hwLoadRequestId value of -1 indicates there is no loading operation.
                "
            ::= { hwLoadParaEntry 12 }

        hwLoadServerPort OBJECT-TYPE
            SYNTAX Unsigned32 (0..65535)
            MAX-ACCESS read-write
            STATUS current
            DESCRIPTION
                "
                Monitoring port on the SFTP server.
                Range: 0-65535
                Default: 22
                The invalid value is 65535.
                "
            DEFVAL { 22 }
            ::= { hwLoadParaEntry 13 }

        hwBatchLoadOptions OBJECT-TYPE
            SYNTAX INTEGER
            {
             noloadActiveAndStandby(-1),
             loadActiveAndStandby(1)
            }
            MAX-ACCESS read-write
            STATUS current
            DESCRIPTION
                "
                Batch load options. This object is used to determine whether the slot number
                of the active control board or the standby control board is selected.
                Options:
                1.noloadActiveAndStandby(-1) -indicates that the active and standby control boards
                                              are not loaded at the same time.
                2.loadActiveAndStandby(1)    -indicates that the active and standby control boards
                                              are loaded at the same time.
                "
            ::= { hwLoadParaEntry 14 }

        hwLoadOntType OBJECT-TYPE
            SYNTAX OCTET STRING (SIZE (0..16))
            MAX-ACCESS read-write
            STATUS current
            DESCRIPTION
                "
                It indicates the ONT type.
                This object is used to specify the type of the ONTs that are upgraded in batches through the OLT.
                ONT type:
                MA5610, MA5616, MA5620G, MA5620E, MA5626G, MA5626E, MA5651, MA5651G and MA5652.
                "
            ::= { hwLoadParaEntry 15 }

        hwLoadVersionFilter OBJECT-TYPE
            SYNTAX OCTET STRING (SIZE (0..320))
            MAX-ACCESS read-write
            STATUS current
            DESCRIPTION
                "
                ONT version list.
                It indicates version list of the ONTs that are upgraded in batched through the OLT.
                This leaf is used to specify the ONT versions that need upgrade or the ONT versions
                that need no upgrade.If this field is null, it indicates that no limitation about
                version is set on the upgrade and all ONTs of the specified type should be upgraded.
                If this field is not null, this leaf can be used to specifyeither the versions that
                need upgrade or the versions that need no upgrade. The character '+' marks the versions
                that need upgrade and the character '-' marks the versions that need no upgrade.
                Note that the versions that need upgrade and the versions that need no upgrade are
                exclusive in this leaf; therefore only one type of them can be specified at the same time.
                When the versions that need upgrade are specified, only the specified versions are upgraded;
                when the versions that need no upgrade are specified, all versionsother than the specified
                ones are upgraded. To specify multiple versions at the same time, use the character '-' to
                separate different versions.
                "
            ::= { hwLoadParaEntry 16 }

        hwLoadExtServerInetAddressType OBJECT-TYPE
            SYNTAX InetAddressType
            MAX-ACCESS read-write
            STATUS current
            DESCRIPTION
                "
                The type of address in hwLoadExtServerIPAddress.
                "
            ::= { hwLoadParaEntry 17 }

        hwLoadExtServerIPAddress OBJECT-TYPE
            SYNTAX InetAddress
            MAX-ACCESS read-write
            STATUS current
            DESCRIPTION
                "
                The IPv4, IPv6 or DNS address of LOAD Server. Note that,
                since this is an index to the table, the DNS name must be
                short enough to fit into the maximum length of indices allowed
                by the management protocol in use.
                "
            REFERENCE
                "RFC 2748 section 2.3
                "
            ::= { hwLoadParaEntry 18 }

        hwLoadPacketSmart OBJECT-TYPE
            SYNTAX INTEGER
            {
             normal(1),
             smart(2)
            }
            MAX-ACCESS read-write
            STATUS current
            DESCRIPTION
                "
                This object is used to identify the loading mode of the package file.
                Options:
                1.normal(1)    -indicates that the entire package file is loaded into the system.
                2.smart(2)     -indicates that part of the package file is loaded into the system
                                according to the hardware configuration of the device.
                Default { normal }
                "
            ::= { hwLoadParaEntry 19 }

        hwLoadEncryptAlgorithm OBJECT-TYPE
            SYNTAX INTEGER
            {
             none(1),
             aes256cbc(2)
            }
            MAX-ACCESS read-write
            STATUS current
            DESCRIPTION
                "
                This object is used to identify the encrypt algorithm of the load file.
                Options:
                1.none(1)    -indicates that the load file is not encrypt.
                2.aes256cbc(2)     -indicates that the script file encrypt algorithm is AES256-CBC.
                "
            ::= { hwLoadParaEntry 20 }

        hwLoadEncryptKey OBJECT-TYPE
            SYNTAX OCTET STRING (SIZE (0..32))
            MAX-ACCESS read-write
            STATUS current
            DESCRIPTION
                "
                This object is used to identify the encrypt key.
                "
            ::= { hwLoadParaEntry 21 }

        hwLoadEncryptIV OBJECT-TYPE
            SYNTAX OCTET STRING (SIZE (0..16))
            MAX-ACCESS read-write
            STATUS current
            DESCRIPTION
                "
                This object is used to identify the initialization vector of the encrypt file.
                "
            ::= { hwLoadParaEntry 22 }

        hwBackupParaTable OBJECT-TYPE
            SYNTAX SEQUENCE OF HwBackupParaEntry
            MAX-ACCESS not-accessible
            STATUS current
            DESCRIPTION
                "
                Backup parameter table, used to back up various files of the host through the NMS.
                This table is used to back up important system data. Therefore, configure a high
                access permission for this table.
                The indexes of this table are hwFrameIndex and hwSlotIndex of the board.
                For example, to back up the files of the board in slot 3 of frame 0, the index is 0.3.
                "
            ::= { hwLoadBackupMon 2 }

        hwBackupParaEntry OBJECT-TYPE
            SYNTAX HwBackupParaEntry
            MAX-ACCESS not-accessible
            STATUS current
            DESCRIPTION
                "
                Backup parameter table, used to back up various files of the host through the NMS.
                The indexes of this entry are hwFrameIndex and hwSlotIndex of the board.
                For example, to back up the files of the board in slot 3 of frame 0, the index is 0.3.
                "
            INDEX { hwFrameIndex, hwSlotIndex }
            ::= { hwBackupParaTable 1 }

        HwBackupParaEntry ::=
            SEQUENCE
                {
                 hwBackupServerIpAddr
                     IpAddress,
                 hwBackupMode
                     INTEGER,
                 hwBackupFileName
                     OCTET STRING,
                 hwBackupContent
                     INTEGER,
                 hwBackupProcess
                     Integer32,
                 hwBackupUserName
                     OCTET STRING,
                 hwBackupPassword
                     OCTET STRING,
                 hwBackupBoardType
                     HWPCBType,
                 hwBackupRequestID
                     Integer32,
                 hwBackupServerPort
                     Unsigned32,
                 hwBackupPositionPara
                     Integer32,
                 hwBackupExtServerInetAddressType
                     InetAddressType,
                 hwBackupExtServerIPAddress
                     InetAddress,
                 hwBackupResouce
                     OCTET STRING,
                 hwBackupPrivatePara
                     OCTET STRING
                }

        hwBackupServerIpAddr OBJECT-TYPE
            SYNTAX IpAddress
            MAX-ACCESS read-write
            STATUS current
            DESCRIPTION
             "The IP address of file server.
             "
            ::= { hwBackupParaEntry 1 }

        hwBackupMode OBJECT-TYPE
            SYNTAX INTEGER
                {
                 tftp(1),
                 modem(2),
                 ftp(3),
                 sftp(5),
                 other(6)
                }
            MAX-ACCESS read-write
            STATUS current
            DESCRIPTION
              "
              Load protocol.
              Options:
              1.tftp(1)  -indicates that the backup is performed by using TFTP through the
                          network port. Select tftp(1) when the transmission mode of the server is
                          configured to TFTP.When TFTP is used in the backup, you need not enter the
                          user name and password.
              2.modem(2) -indicates that the backup is performed by using the Xmodem serial
                          port protocol through the serial port. When you use the HyperTerminal of
                          the OS to configure the serial port on the server, select modem(2).
                          Loading through the serial port does not require networking and maintenance
                          through the command line interface does not require NM software.
              3.ftp(3)   -indicates that the backup is performed by using FTP through the network
                          port. Select ftp when the transmission mode of the server is configured to FTP.
                          When FTP is used for file backup, you need to enter the user name and password.
              4.sftp(5)  -indicates that the backup is performed by using SFTP through the network port.
                          Select sftp(5) when the transmission mode of the server is configured to SFTP.
                          When SFTP is used for file backup, the instructions and data are encrypted
                          during transmission.
              5.other(6) -other.
              The SFTP transmission mode is recommended.
             "
            ::= { hwBackupParaEntry 2 }

        hwBackupFileName OBJECT-TYPE
            SYNTAX OCTET STRING (SIZE (0..128))
            MAX-ACCESS read-write
            STATUS current
            DESCRIPTION
                "
                The name of backup file.
                "
            ::= { hwBackupParaEntry 3 }

        hwBackupContent OBJECT-TYPE
            SYNTAX INTEGER
                {
                 nobackupcontent(-1),
                 database(1),   -- database file
                 shellMacro(2),  --shell macro file
                 log(3),            -- log file
                 bill(4),    -- bill file
                 alarm(5),      -- alarm file
                 configurationFile(14), -- configuration file
                 program(15),       -- program file
                 reslocal(16),   --local resource file
                 resgeneral(17), --general resource file
                 patch(18),     -- patch file
                 programDatabase(19),   -- database file
                 programBios(20),   -- bios file
                 programApp(21),        -- application file
                 logicFpga(22),     -- fpga logic file
                 logicCpld(23),     -- Cpld logic file
                 logicPci(24),      -- pci logic file
                 logicAfc(25),      -- afc logic file
                 programMicroCode(26),  -- micro-code file
                 programFireware(27),   -- application program of pinch board
                 programDataFlow(28),   -- flow file of card management point
                 programBootFile(29),   -- boot program file of the board start
                 logciPa(30),       -- fpga logic file of the pinch board
                 webExp(31),        -- web exp file
                 webNev(32),        -- web nev file
                 webHelp(33),       -- web help file
                 programBsp(34),        -- bsp program file
                 configurationIni(40), -- not supported
                 configurationEfs(41), -- not supported
                 configurationCli(42), -- not supported
                 programCurrent(45),   -- not supported
                 programOther(46),     -- not supported
                 bcdcInfo(47),           -- bcdc description system in ini file
                 license(49),            -- license file
                 programExtendedBios(51),  --extended bios file
                 boardinfo(60),          -- board information
                 extendedBootRom(61), -- extended BootRom file
                 defaultCfg(62), -- default configuration file
                 exception(63), -- exception file
                 versionDescribe(64), -- version description file
                 emuelabel(65),         -- emu elabel file
                 emuproofelabel(66),        -- emu proof elabel file
                 backboardelabel(67),       --frame back board elabel file
                 nmscollectinfo(68),        --nms collect information file
                 trapsyninfo(69),             --trap synchronization information file
                 digitmap(70),           -- h248 Digitmap
                 h248Profile(71),       -- h248 profile
                 sipProfile(72),        -- sip profile
                 elabel(73),             -- elabel file
                 sipDigitmap(74),        -- sip Digitmap
                 iop(75),            -- iop file
                 port(76),            -- Port status information
                 script(77),        -- script command result
                 voice(78),         -- voice file
                 framePnp(79),       -- frame pnp
                 boardPnp(80),       -- board pnp
                 subboardPnp(81),       -- subboard pnp
                 resetRecord(82),        -- debug information of board
                 hwStatusCollectInfo(83),   -- hm status information file
                 deviceCapXml(84),        -- device capability information xml file
                 cabinetelabel(120),        -- cabinet elabel file
                 batteryelabel(121),        -- battery elabel file
                 deviceCapabilityFile(122), -- device capability decoupling file
                 powerRunData(123),         -- the running data
                 crosstalkCouplingMatrix(131),    -- crosstalk coupling matrix file
                 vdsl2Xlin(132),                     -- vdsl2 xlin file
                 ibmsFile(133),              --Installed Base Management System(IBMS) file type
		 userfile(134),               -- user common file
		 vectoring(135),             --Vectoring run info
                xdslPortResetInfo(136),     -- xdsl port auto reset info
                frameelabel(137),         -- frame elabel file
                rootfs(138),              -- rootfs file
                uimage(139),              -- uimage file
                initrd(140),              -- initrd file
                atiboardelabel(141),      -- ATI board elabel file
                boardspectrum(150)        -- Board Spectrum
                }
            MAX-ACCESS read-write
            STATUS current
            DESCRIPTION
                "
                Type of the backup file.
                Options:
                1.nobackupcontent(-1)             -no file.
                2.database(1)                     -database file.
                3.shellMacro(2)                   -shell macro file.
                4.log(3)                          -log file.
                5.bill(4)                         -bill file.
                6.alarm(5)                        -alarm file.
                7.configurationFile(14)           -configuration file.
                8.program(15)                     -program file.
                9.reslocal(16)                    -local resource file.
                10.resgeneral(17)                 -general resource file.
                11.patch(18)                      -patch file.
                12.programDatabase(19)            -database file.
                13.programBios(20)                -bios file.
                14.programApp(21)                 -application file.
                15.logicFpga(22)                  -fpga logic file.
                16.logicCpld(23)                  -Cpld logic file.
                17.logicPci(24)                   -pci logic file.
                18.logicAfc(25)                   -afc logic file.
                19.programMicroCode(26)           -micro-code file.
                20.programFireware(27)            -application program of pinch board.
                21.programDataFlow(28)            -flow file of card management point.
                22.programBootFile(29)            -boot program file of the board start.
                23.logciPa(30)                    -fpga logic file of the pinch board.
                24.webExp(31)                     -web exp file.
                25.webNev(32)                     -web nev file.
                26.webHelp(33)                    -web help file.
                27.programBsp(34)                 -bsp program file.
                28.configurationIni(40)           -not supported.
                29.configurationEfs(41)           -not supported.
                30.configurationCli(42)           -not supported.
                31.programCurrent(45)             -not supported.
                32.programOther(46)               -not supported.
                33.bcdcInfo(47)                   -bcdc description system in ini file.
                34.license(49)                    -license file.
                35.programExtendedBios(51)        -extended bios file.
                36.boardinfo(60)                  -board information.
                37.extendedBootRom(61)            -extended BootRom file.
                38.defaultCfg(62)                 -default configuration file.
                39.exception(63)                  -exception file.
                40.versionDescribe(64)            -version description file.
                41.emuelabel(65)                  -emu elabel file.
                42.emuproofelabel(66)             -emu proof elabel file.
                43.backboardelabel(67)            -frame back board elabel file.
                44.nmscollectinfo(68)             -nms collect information file.
                45.trapsyninfo(69)                -trap synchronization information file.
                46.digitmap(70)                   -h248 Digitmap.
                47.h248Profile(71)               -h248 profile.
                48.sipProfile(72)                -sip profile.
                49.elabel(73)                     -elabel file.
                50.sipDigitmap(74)               -sip Digitmap.
                51.iop(75)                        -iop file.
                52.port(76)                       - Port status information
                53.script(77)                     -script command result.
                54.voice(78)                      -voice file.
                55.framePnp(79)                  -frame pnp.
                56.boardPnp(80)                  -board pnp.
                57.subboardpnp(81)               -subboard pnp.
                58.resetRecord(82)                -debug information of board.
                59.hwStatusCollectInfo(83)        -hm status information file.
                60.deviceCapXml(84)             -device capability information xml file.
                61.cabinetelabel(120)             -cabinet elabel file.
                62.batteryelabel(121)             -battery elabel file.
                63.deviceCapabilityFile(122)      -device capability decoupling file
                64.powerRunData(123)              -the running data
                65.crosstalkCouplingMatrix(131) -crosstalk coupling matrix file
                66.vdsl2Xlin(132)                -vdsl2 xlin file
                67.ibmsFile(133)                  -Installed Base Management System(IBMS) file type
		68.userfile(134)                  - user common file
                69.vectoring(135)                 -Vectoring run info
                70.xdslPortResetInfo(136)      -xdsl port auto reset info
                71.frameelabel(137)         -- frame elabel file
                72.rootfs(138)              -- rootfs file
                73.uimage(139)              -- uimage file
                73.initrd(140)              -- initrd file
                74.atiboardelabel(141)      -- ATI board elabel file
                75.boardspectrum(150)       -- Board Spectrum
                "
            ::= { hwBackupParaEntry 4 }

        hwBackupProcess OBJECT-TYPE
            SYNTAX Integer32 (0..100)
            MAX-ACCESS read-only
            STATUS current
            DESCRIPTION
                "
                Backup progress.
                "
            ::= { hwBackupParaEntry 5 }

        hwBackupUserName OBJECT-TYPE
            SYNTAX OCTET STRING (SIZE (0..40))
            MAX-ACCESS read-write
            STATUS current
            DESCRIPTION
                "
                The backup user name, which is required in FTP mode and SFTP mode
                but is not required in TFTP mode.
                "
            ::= { hwBackupParaEntry 6 }

        hwBackupPassword OBJECT-TYPE
            SYNTAX OCTET STRING (SIZE (0..40))
            MAX-ACCESS read-write
            STATUS current
            DESCRIPTION
                "
                The backup user password, which is required in FTP mode and SFTP mode
                but is not required in TFTP mode.
                "
            ::= { hwBackupParaEntry 7 }

        hwBackupBoardType OBJECT-TYPE
            SYNTAX HWPCBType
            MAX-ACCESS read-write
            STATUS current
            DESCRIPTION
                "
                The type of the board to be backed up, which is defined in HUAWEI-TC-MIB.mib.
                "
            ::= { hwBackupParaEntry 8 }

        hwBackupRequestID OBJECT-TYPE
            SYNTAX Integer32
            MAX-ACCESS read-write
            STATUS current
            DESCRIPTION
                "
                The backup request ID, which identifies a backup request delivered by the NMS.
                According to the ID, you can query hwOperationInfoTable to obtain
                the status and results of each backup operation.
                An backup request ID can be any integer in the range of 0-0xFFFFFFFF.
                But, the IDs of different backup requests cannot duplicate.
                This object cannot be set independently.
                The hwBackupRequestID value of -1 indicates there is no backup operation.
                "
            ::= { hwBackupParaEntry 9 }

        hwBackupServerPort OBJECT-TYPE
            SYNTAX Unsigned32 (0..65535)
            MAX-ACCESS read-write
            STATUS current
            DESCRIPTION
                "
                SFTP server listen port.
                Range: 0-65535
                Default: 22
                The invalid value is 65535.
                "
            DEFVAL { 22 }
            ::= { hwBackupParaEntry 10 }

        hwBackupPositionPara OBJECT-TYPE
            SYNTAX Integer32
            MAX-ACCESS read-write
            STATUS current
            DESCRIPTION
                "
                Auxiliary parameters for locating a board to be backed up.
                When a file is backed up to the EMU, the value of this parameter is emuID.
                When a file is backed up to a modem or an ONT, the value of this parameter is portID.
                When a file is backed up to a daughter board, the value of this parameter is SubBoardID.
                This parameter is not required for backing up the file to other components.
                The hwBackupPositionPara value of -1 indicates auxiliary parameters for locating is not exist.
                "
            ::= { hwBackupParaEntry 11 }

        hwBackupExtServerInetAddressType OBJECT-TYPE
            SYNTAX InetAddressType
            MAX-ACCESS read-write
            STATUS current
            DESCRIPTION
                 "
                 The type of address in hwBackupExtServerIPAddress.
                 "
            ::= { hwBackupParaEntry 12 }

        hwBackupExtServerIPAddress OBJECT-TYPE
            SYNTAX InetAddress
            MAX-ACCESS read-write
            STATUS current
            DESCRIPTION
                "
                The IPv4, IPv6 or DNS address of BACKUP Server. Note that,
                since this is an index to the table, the DNS name must be
                short enough to fit into the maximum length of indices allowed
                by the management protocol in use.
                "
            REFERENCE
                 "
                 RFC 2748 section 2.3
                 "
            ::= { hwBackupParaEntry 13 }

        hwBackupResouce OBJECT-TYPE
            SYNTAX OCTET STRING
            MAX-ACCESS read-write
            STATUS current
            DESCRIPTION
                "
                The backup resource.
                "
            ::= { hwBackupParaEntry 14 }

        hwBackupPrivatePara OBJECT-TYPE
            SYNTAX OCTET STRING (SIZE (0..4096))
            MAX-ACCESS read-write
            STATUS current
            DESCRIPTION
                "
                Proprietary parameter carried during file backup. The parameter is related to the contents of the backup file.
                The backup file is Vdsl2 xlin. The proprietary parameter is the victim or disturb port list. The maximum length of the parameter is 4096 bytes.
                1.The collection parameter that contains only a victim port list collects coefficient of crosstalk generated by all the disturb ports to a specified victim port.
                   Parameter description:
                     1.The parameter contains the parameter length and port list.
                     2.The parameter type of a port list is victim.
                     3.The information about a port list contains the MAC address, frame ID, slot ID, and port ID.
                |Parameter length (4 bytes)  |Parameter type (4 bytes)  |Parameter length (4 bytes)   |MAC address (6 bytes) |Reserved bytes   |Frame (1 byte)    |Slot (1 byte)  |Port ID (1 byte) |...|
                +----------------------------+--------------------------+-----------------------------+----------------------+-----------------+------------------+---------------+-----------------+...+
                |<--Parameter length-------->|<-----------------------------------Victim port list------------------------------------------------------------------------------------------------> |
                The MAC address is reserved and is filled with 0s in BLV and SLV scenarios. The omitted contents are repeat of |MAC address (6 bytes) |Reserved bytes   |Frame (1 byte)    |Slot (1 byte)  |Port ID (1 byte) |.

                2.The collection parameter that contains only a disturb port list collects coefficient of crosstalk generated by a specified disturb ports to all victim ports.
                   Parameter description:
                     1.The parameter contains the parameter length and port list.
                     2.The parameter type of a port list is disturb.
                     3.The information about a port list contains the MAC address, frame ID, slot ID, and port ID.
                |Parameter length (4 bytes)  |Parameter type (4 bytes)  |Parameter length (4 bytes)   |MAC address (6 bytes) |Reserved bytes   |Frame (1 byte)    |Slot (1 byte)  |Port ID (1 byte) |...|
                +-----------------------------+--------------------------+-----------------------------+----------------------+-----------------+------------------+---------------+-----------------+...+
                |<--Parameter length-------->|<-----------------------------------disturb port list-----------------------------------------------------------------------------------------------> |
                The MAC address is reserved and is filled with 0s in BLV and SLV scenarios. The omitted contents are repeat of |MAC address (6 bytes) |Reserved bytes   |Frame (1 byte)    |Slot (1 byte)  |Port ID (1 byte) |.

                3.The collection parameter that contains victim and disturb port lists collects coefficient of crosstalk generated by specified disturb ports to specified victim ports.
                   Parameter description:
                     1.The parameter contains the parameter length, victim port list, and disturb port list.
                |Parameter length (4 bytes)  |Parameter type (4 bytes)  |Parameter length (4 length)  |Port information |Parameter type (4 bytes) |Parameter length (4 bytes) |Port information |
                +----------------------------+--------------------------+-----------------------------+-----------------+-------------------------+---------------------------+-----------------+
                |<--Parameter length-------->|<-------------------------------------victim port list------------------->|<-----------------------disturb port list----------------------------> |
                "
            ::= { hwBackupParaEntry 15 }

        hwBackupAndRestoreConfig OBJECT IDENTIFIER ::= { hwLoadBackupMon 4 }

        hwBackupAndRestore OBJECT-TYPE
            SYNTAX INTEGER
                {
                 copyMemToFlash(1),
                 copyFlashToMemory(2),
                 copyMemToHardDisk(3),
                 copyHardDiskToMem(4)
                }
            MAX-ACCESS read-write
            STATUS current
            DESCRIPTION
                "
                The running configuration in the system has been backed-up to flash or disk,
                or restored. The object is not supported at present.
                Options:
                1. copyMemToFlash(1)    -back up the configuration file for the host memory to the flash memory.
                2. copyFlashToMemory(2) -back up the configuration file for the host memory to the disk.
                3. copyMemToHardDisk(3) -copy the configuration file for the flash memory to the host memory for running.
                4. copyHardDiskToMem(4) -copy the configuration file for the disk to the host memory for running.
                "
            ::= { hwBackupAndRestoreConfig 1 }


        hwConfigChangedSequence OBJECT-TYPE
            SYNTAX Integer32
            MAX-ACCESS read-only
            STATUS obsolete
            DESCRIPTION
                "
                The sequence of system configuration changed.
                The object is not supported at present.
                "
            ::= { hwBackupAndRestoreConfig 2 }

--  Activating rollback operation table
        -- 1.3.6.1.4.1.2011.6.6.1.5
        hwCfgOperTable OBJECT-TYPE
            SYNTAX SEQUENCE OF HwCfgOperEntry
            MAX-ACCESS not-accessible
            STATUS obsolete
            DESCRIPTION
                "
                New MIB node added by BWA production. Activating rollback operation table,
                used to activate rollback operation.
                The indexes of this table are hwFrameIndex and hwSlotIndex.
                The object is not supported at present.
                "
            ::= { hwLoadBackupMon 5 }

-- Activating rollback operation entry
        -- 1.3.6.1.4.1.2011.6.6.1.5.1
        hwCfgOperEntry OBJECT-TYPE
            SYNTAX HwCfgOperEntry
            MAX-ACCESS not-accessible
            STATUS obsolete
            DESCRIPTION
                "
                New MIB node added by BWA production. Activating rollback operation table,
                used to activate rollback operation.
                The indexes of this entry are hwFrameIndex and hwSlotIndex.
                The object is not supported at present.
                "
            INDEX { hwFrameIndex, hwSlotIndex }
            ::= { hwCfgOperTable 1 }

        HwCfgOperEntry ::=
            SEQUENCE
                {
                    hwConfigAdminStatus
                        INTEGER,
                    hwConfigOperTimeLine
                        Integer32,
                    hwConfigOperProgress
                        Integer32,
                    hwConfigOperStatus
                        INTEGER
                 }

-- 0: activate default configuration 1: activate backed up software
-- 2: rollback begin (standby configuration will cover active configuration)
-- 3: rollback cancel (active configuration will cover standby configuration)
        -- 1.3.6.1.4.1.2011.6.6.1.5.1.1
        hwConfigAdminStatus OBJECT-TYPE
            SYNTAX INTEGER
                {
                 activeDefaultCfg(0),
                 activeBackupSw(1),
                 beginRollback(2),
                 cancelRollback(3)
                }
            MAX-ACCESS read-write
            STATUS obsolete
            DESCRIPTION
                "
                configuration administration status.
                Options:
                1.activeDefaultCfg(0) -activate default configuration.
                2.activeBackupSw(1)   -activate the backed up software.
                3.beginRollback(2)    -rollback begin (standby configuration will cover active configuration).
                4.cancelRollback(3)   -rollback cancel (active configuration will cover standby configuration).
                "
            ::= { hwCfgOperEntry 1 }

        -- 1.3.6.1.4.1.2011.6.6.1.5.1.2
        hwConfigOperTimeLine OBJECT-TYPE
            SYNTAX Integer32 (0..7)
            MAX-ACCESS read-write
            STATUS obsolete
            DESCRIPTION
                "
                Time limit of canceling rollback operation, unit is day,
                0 means canceling rollback immediately.
                This node is just used for the rollback canceling operation.
                "
            ::= { hwCfgOperEntry 2 }

--  Progress indication 0-100

        -- 1.3.6.1.4.1.2011.6.6.1.5.1.3
        hwConfigOperProgress OBJECT-TYPE
            SYNTAX Integer32 (0..100)
            MAX-ACCESS read-only
            STATUS obsolete
            DESCRIPTION
                "
                Progress indication. The object is not supported at present.
                "
            ::= { hwCfgOperEntry 3 }

-- 1 can be rollbacked
-- 2 can not be rollbacked
        -- 1.3.6.1.4.1.2011.6.6.1.5.1.4
        hwConfigOperStatus OBJECT-TYPE
            SYNTAX INTEGER
                {
                 enableRollback(1),
                 disableRollback(2)
                }
            MAX-ACCESS read-only
            STATUS obsolete
            DESCRIPTION
                "
                Flag of whether the file can be rollbacked.
                Options:
                1.enableRollback(1)  -the file can be rollbacked.
                2.disableRollback(2) -the file can not be rollbacked.
                The object is not supported at present.
                "
            ::= { hwCfgOperEntry 4 }

        hwCpeLoadPara OBJECT IDENTIFIER ::= { hwLoadBackupMon 6 }

        hwServerIpAddrForTerminal OBJECT-TYPE
            SYNTAX IpAddress
            MAX-ACCESS read-write
            STATUS obsolete
            DESCRIPTION
                "
                This object indicates the IP address of TFTP server and it is used for
                the loading to the terminal. The object is not supported at present.
                "
            ::= { hwCpeLoadPara 1 }

        --Operation Information Tabel
        hwOperationInfo OBJECT IDENTIFIER ::= { hwLoadBackup 4 }

        hwOperationInfoTable OBJECT-TYPE
            SYNTAX SEQUENCE OF HwOperationInfoEntry
            MAX-ACCESS not-accessible
            STATUS current
            DESCRIPTION
                "
                Operation information table. Through this table,
                you can query the status and results of data saving, loading,
                backup, upgrading without service interruption, patch rollback,
                and cloning operations on the NMS. The index of this table is hwOperationReqID.
                hwOperationReqID is an operation request ID.
                "
            ::= { hwOperationInfo 1 }

        hwOperationInfoEntry OBJECT-TYPE
            SYNTAX HwOperationInfoEntry
            MAX-ACCESS not-accessible
            STATUS current
            DESCRIPTION
                "
                Operation information table. Through this table,
                you can query the status and results of data saving, loading,
                backup, upgrading without service interruption, patch rollback,
                and cloning operations on the NMS. The index of this entry is hwOperationReqID.
                hwOperationReqID is an operation request ID.
                "
            INDEX { hwOperationReqID }
            ::= { hwOperationInfoTable 1 }

        HwOperationInfoEntry ::=
            SEQUENCE
                {
                 hwOperationReqID
                     Integer32,
                 hwOperationReqType
                     INTEGER,
                 hwOperationReqStatus
                     INTEGER,
                 hwOperationProgress
                     Integer32,
                 hwOperationReqErrStatus
                     Integer32,
                 hwOperationReqStartTime
                     DateAndTime,
                 hwOperationReqEndTime
                     DateAndTime,
                 hwOperationFileDigest
                     OCTET STRING
                }

        hwOperationReqID OBJECT-TYPE
            SYNTAX Integer32
            MAX-ACCESS read-only
            STATUS current
            DESCRIPTION
                "
                The requestID of this operation. This object together with hwOperationReqType,
                identifies different operations of different types.
                "
            ::= { hwOperationInfoEntry 1 }

        hwOperationReqType OBJECT-TYPE
            SYNTAX INTEGER
                {
                 dataSave(1),
                 load(2),
                 backup(3),
                 uninterruptedAutoUpgrade(4),
                 patchrollback(5),
                 clone(6),
                 interruptedAutoUpgrade(7),
                 patchactive(8),
                 patchdeactive(9),
                 patchdelete(10),
                 patchrun(11),
                 vsCreate(12),
                 vsDelete(13),
                 vsAddPhysicalResource(14),
                 vsDeletePhysicalResource(15)
                }
            MAX-ACCESS read-only
            STATUS current
            DESCRIPTION
                "
                Operation type.
                Options:
                1. dataSave(1)                 -indicates the data saving operation through the NMS.
                2. load(2)                     -indicates the loading operation through the NMS.
                3. backup(3)                   -indicates the backup operation through the NMS.
                4. uninterruptedAutoUpgrade(4) -indicates automatic upgrade without service interruption.
                5. patchrollback(5)            -indicates patch rollback.
                6. clone(6)                    -clone(6) is not in use at present.
                7.interruptedAutoUpgrade(7)    -indicates automatic upgrade with service interruption.
                8.patchactive(8)               -indicates patch active.
                9.patchdeactive(9)             -indicates patch deactive.
                10.patchdelete(10)             -indicates patch delete.
                11.patchrun(11)                -indicates patch run.
                12.vsCreate(12)                -indicates create virtual system.
                13.vsDelete(13)                -indicates delete virtual system.
                14.vsAddPhysicalResource(14)   -indicates add physical resource.
                15.vsDeletePhysicalResource(15) -indicates delete physical resource.
                "
            ::= { hwOperationInfoEntry 2 }

        hwOperationReqStatus OBJECT-TYPE
            SYNTAX INTEGER
                {
                 initial(1),
                 datascanning(2),
                 transferring(3),
                 saving(4),
                 success(5),
                 fail(6),
                 uninterruptedAutoUpgradeResetStandby(7),
                 uninterruptedAutoUpgradeBatchHotBackupFirst(8),
                 uninterruptedAutoUpgradeSwitchOver(9),
                 uninterruptedAutoUpgradeBatchHotBackupSecond(10),
                 ioupgrade(11),
                 systemreboot(12),
                 serviceboardloading(13)
                }
            MAX-ACCESS read-only
            STATUS current
            DESCRIPTION
                "
                Current status of an operation request.
                Options:
                1.initial(1)     -indicates that the operation is in the preparation phase.
                2.datascanning(2)-indicates that the operation is in the data collection phase.
                3.transferring(3)-indicates that the operation is in the data transmission phase.
                4.saving(4)      -indicates that the operation is in the data saving phase.
                5.success(5)     -indicates that the operation is successful.
                6.fail(6)        -indicates that the operation fails.
                7.uninterruptedAutoUpgradeResetStandby(7)
                 -indicates that automatic upgrade without service interruption is in the following state:
                  the standby control board is being started after reset.
                8.uninterruptedAutoUpgradeBatchHotBackupFirst(8)
                 -indicates that automatic upgrade without service interruption is in the following state:
                  the standby control board is restarted and hot backup on the host is under way.
                9.uninterruptedAutoUpgradeSwitchOver(9)
                 -indicates that automatic upgrade without service interruption is in the following state:
                  the active control board switches to the standby one and is being restarted.
               10.uninterruptedAutoUpgradeBatchHotBackupSecond(10)
                 -indicates that automatic upgrade without service interruption is in the following state:
                  the current standby control board is already restarted and hot backup on the host is being performed.
               11.ioupgrade(11)   -indicates that automatic upgrade is in the following state:
                  the upgrade of the service board.
               12.systemreboot(12)-indicates that automatic upgrade with service interruption is in the following state:
                  the system is rebooting.
               13.serviceboardloading(13)--indicates that automatic upgrade is in the following state:
                  the service board is loading.
               "
            ::= { hwOperationInfoEntry 3 }

        hwOperationProgress OBJECT-TYPE
            SYNTAX Integer32 (0..100)
            UNITS "percentage"
            MAX-ACCESS read-only
            STATUS current
            DESCRIPTION
                "
                The progress of the operation.
                Range: 0-100.
                "
            ::= { hwOperationInfoEntry 4 }

        hwOperationReqErrStatus OBJECT-TYPE
            SYNTAX Integer32
            MAX-ACCESS read-only
            STATUS current
            DESCRIPTION
                "
                The error code of this operation. The returned error code is an NMS error code.
                The value 0 means 'No error';
                The value 6561510 means 'Failed to transfer the file';
                The value 6561553 means 'Username or password error';
                The value 6561620 means 'The server is unreachable';
                The value 6561623 means 'Failed to operate the remote file';
                The value 6561625 means 'The SSH key is incorrect';
                The value 6561626 means 'The path does not exist';
                The value 6561627 means 'The file does not exist'.
                "
            ::= { hwOperationInfoEntry 5 }

        hwOperationReqStartTime OBJECT-TYPE
            SYNTAX DateAndTime
            MAX-ACCESS read-only
            STATUS current
            DESCRIPTION
                "
                Time when the operation starts.
                "
            ::= { hwOperationInfoEntry 6 }

        hwOperationReqEndTime OBJECT-TYPE
            SYNTAX DateAndTime
            MAX-ACCESS read-only
            STATUS current
            DESCRIPTION
                "
                Time when the operation ends.
                "
            ::= { hwOperationInfoEntry 7 }

        hwOperationFileDigest OBJECT-TYPE
            SYNTAX OCTET STRING(SIZE (0..16))
            MAX-ACCESS read-only
            STATUS current
            DESCRIPTION
                "
                Digest value of the operating file, such as 0x13AC06A62E47FD51F95D2BA243CD0346,
                0 means invalid value.
                "
            ::= { hwOperationInfoEntry 8 }

        hwPatch OBJECT IDENTIFIER ::= { hwLoadBackup 2 }

        hwPatchTable OBJECT-TYPE
            SYNTAX SEQUENCE OF HwPatchEntry
            MAX-ACCESS not-accessible
            STATUS obsolete
            DESCRIPTION
                "
                Do operations on single patch. The table is not supported at present.
                The indexes of this table are hwFrameIndex, hwSlotIndex and hwPatchId.
                "
            ::= { hwPatch 1 }

        hwPatchEntry OBJECT-TYPE
            SYNTAX HwPatchEntry
            MAX-ACCESS not-accessible
            STATUS obsolete
            DESCRIPTION
                "
                Do operations on single patch. The table is not supported at present.
                The indexes of this entry are hwFrameIndex, hwSlotIndex and hwPatchId.
                "
            INDEX { hwFrameIndex, hwSlotIndex, hwPatchId }
            ::= { hwPatchTable 1 }

        HwPatchEntry ::=
            SEQUENCE
            {
                hwPatchId
                    Unsigned32,
                hwPatchDescription
                    OCTET STRING,
                hwPatchFuncNum
                    Integer32,
                hwPatchTextLen
                    Integer32,
                hwPatchDataLen
                    Integer32,
                hwPatchType
                    INTEGER,
                hwPatchAdminStatus
                    INTEGER,
                hwPatchOperState
                    INTEGER
             }

        hwPatchId OBJECT-TYPE
            SYNTAX Unsigned32
            MAX-ACCESS not-accessible
            STATUS obsolete
            DESCRIPTION
                "
                Patch ID. The object is not supported at present.
                "
            ::= { hwPatchEntry 1 }

        hwPatchDescription OBJECT-TYPE
            SYNTAX OCTET STRING (SIZE (0..64))
            MAX-ACCESS read-only
            STATUS obsolete
            DESCRIPTION
                "
                Patch Description.
                "
            ::= { hwPatchEntry 2 }

        hwPatchFuncNum OBJECT-TYPE
            SYNTAX Integer32
            MAX-ACCESS read-only
            STATUS obsolete
            DESCRIPTION
                "
                Function number included in patch. The object is not supported at present.
                "
            ::= { hwPatchEntry 3 }

        hwPatchTextLen OBJECT-TYPE
            SYNTAX Integer32
            MAX-ACCESS read-only
            STATUS obsolete
            DESCRIPTION
                "
                Patch text length.
                "
            ::= { hwPatchEntry 4 }

        hwPatchDataLen OBJECT-TYPE
            SYNTAX Integer32
            MAX-ACCESS read-only
            STATUS obsolete
            DESCRIPTION
                "
                Patch data length. The object is not supported at present.
                "
            ::= { hwPatchEntry 5 }

        hwPatchType OBJECT-TYPE
            SYNTAX INTEGER
                {
                 common(1),
                 temporary(2)
                }
            MAX-ACCESS read-only
            STATUS obsolete
            DESCRIPTION
                "
                Patch type. The object is not supported at present.
                Options:
                1.common(1)    -Patch type is common.
                2.temporary(2) -Patch type is temporary.
                "
            ::= { hwPatchEntry 6 }

        hwPatchAdminStatus OBJECT-TYPE
            SYNTAX INTEGER
                {
                 active(1),
                 deactive(2),
                 delete(3),
                 run(4),
                 withdraw(5)
                }
            MAX-ACCESS read-write
            STATUS obsolete
            DESCRIPTION
                "
                Patch administrative status. The object is not supported at present.
                Options:
                1.active(1)  -indicates patch administrative status is active.
                2.deactive(2)-indicates patch administrative status is deactive.
                3.delete(3)  -indicates patch administrative status is delete.
                4.run(4)     -indicates patch administrative status is running.
                5.withdraw(5)-indicates patch administrative status is withdraw.
                "
            ::= { hwPatchEntry 7 }

        hwPatchOperState OBJECT-TYPE
            SYNTAX INTEGER
                {
                 patchActive(1),
                 patchDeActive(2),
                 patchRunning(4)
                }
            MAX-ACCESS read-only
            STATUS obsolete
            DESCRIPTION
                "
                Patch operative state. The object is not supported at present.
                Options:
                1.patchActive(1)  -Patch operative state is active.
                2.patchDeActive(2)-Patch operative state is deactive.
                3.patchRunning(4) -Patch operative state is running.
                "
            ::= { hwPatchEntry 8 }

        hwPatchStatTable OBJECT-TYPE
            SYNTAX SEQUENCE OF HwPatchStatEntry
            MAX-ACCESS not-accessible
            STATUS obsolete
            DESCRIPTION
                "
                Information of patch statistics. The table is not supported at present.
                The indexes of this table are hwFrameIndex and hwSlotIndex.
                "
            ::= { hwPatch 2 }

        hwPatchStatEntry OBJECT-TYPE
            SYNTAX HwPatchStatEntry
            MAX-ACCESS not-accessible
            STATUS obsolete
            DESCRIPTION
                "
                Information of patch statistics. The table is not supported at present.
                The indexes of this entry are hwFrameIndex and hwSlotIndex.
                "
            INDEX { hwFrameIndex, hwSlotIndex }
            ::= { hwPatchStatTable 1 }

        HwPatchStatEntry ::=
            SEQUENCE
            {
                hwPatchStatNumMax
                    Integer32,
                hwPatchStatTextMax
                    Integer32,
                hwPatchStatDataMax
                    Integer32,
                hwPatchStatTextUsed
                    Integer32,
                hwPatchStatDataUsed
                    Integer32
             }

        hwPatchStatNumMax OBJECT-TYPE
            SYNTAX Integer32
            MAX-ACCESS read-only
            STATUS obsolete
            DESCRIPTION
                "
                The maximum number of patches can be supported in system.
                The object is not supported at present.
                "
            ::= { hwPatchStatEntry 1 }

        hwPatchStatTextMax OBJECT-TYPE
            SYNTAX Integer32
            MAX-ACCESS read-only
            STATUS obsolete
            DESCRIPTION
                "
                Size of patch code area. The object is not supported at present.
                "
            ::= { hwPatchStatEntry 2 }

        hwPatchStatDataMax OBJECT-TYPE
            SYNTAX Integer32
            MAX-ACCESS read-only
            STATUS obsolete
            DESCRIPTION
                "
                Size of patch data area. The object is not supported at present.
                "
            ::= { hwPatchStatEntry 3 }

        hwPatchStatTextUsed OBJECT-TYPE
            SYNTAX Integer32
            MAX-ACCESS read-only
            STATUS obsolete
            DESCRIPTION
                "
                Patch code area used. The object is not supported at present.
                "
            ::= { hwPatchStatEntry 4 }

        hwPatchStatDataUsed OBJECT-TYPE
            SYNTAX Integer32
            MAX-ACCESS read-only
            STATUS obsolete
            DESCRIPTION
             "Patch data area used. The object is not supported at present.
             "
            ::= { hwPatchStatEntry 5 }


        hwPatchNewTable OBJECT-TYPE
            SYNTAX SEQUENCE OF HwPatchNewEntry
            MAX-ACCESS not-accessible
            STATUS current
            DESCRIPTION
                "
                The patch information description table, which describes the information
                about the patches in the system, including the running status of the patches.
                At the same time, it allows you to activate, deactivate, delete, run,
                and roll back a single patch.The indexes of this table are hwFrameIndex,
                hwSlotIndex and hwNewPatchName.
                "
            ::= { hwPatch 3 }

        hwPatchNewEntry  OBJECT-TYPE
            SYNTAX HwPatchNewEntry
            MAX-ACCESS not-accessible
            STATUS current
            DESCRIPTION
                "
                The patch information description table, which describes the information
                about the patches in the system, including the running status of the patches.
                At the same time, it allows you to activate, deactivate, delete, run,
                and roll back a single patch.The indexes of this entry are hwFrameIndex,
                hwSlotIndex and hwNewPatchName.
                "
            INDEX { hwFrameIndex, hwSlotIndex, IMPLIED hwNewPatchName }
            ::= { hwPatchNewTable 1 }

        HwPatchNewEntry  ::=
            SEQUENCE {
                hwNewPatchName
                    OCTET STRING,
                hwNewPatchDescription
                    OCTET STRING,
                hwNewPatchType
                    INTEGER,
                hwNewPatchAdminStatus
                    INTEGER,
                hwNewPatchOperState
                    INTEGER,
                hwNewPatchRely
                    OCTET STRING,
                hwNewPatchRelied
                    OCTET STRING,
                hwNewPatchRequestID
                    Integer32
             }

        hwNewPatchName OBJECT-TYPE
            SYNTAX OCTET STRING (SIZE (1|6|7))
            MAX-ACCESS not-accessible
            STATUS current
            DESCRIPTION
                "
                The patch name and the table index. For example, the ASCII code of patch name
                SPH001 after conversion is 83.80.72.48.48.49.
                "
            ::= { hwPatchNewEntry  1 }

        hwNewPatchDescription OBJECT-TYPE
            SYNTAX OCTET STRING (SIZE (0..64))
            MAX-ACCESS read-only
            STATUS current
            DESCRIPTION
             "The description about the patch.
             "
            ::= { hwPatchNewEntry  2 }

        hwNewPatchType OBJECT-TYPE
            SYNTAX INTEGER
                {
                 hotcommon(1),
                 hottemporary(2),
                 coldcommon(3),
                 coldtemporary(4)
                }
            MAX-ACCESS read-only
            STATUS current
            DESCRIPTION
                "
                The type of the patch.
                Options:
                1.hotcommon(1)      -indicates the released hot patch.
                2.hottemporary(2)   -indicates the temporary hot patch.
                3.coldcommon(3)     -indicates the released cold patch.
                4.coldtemporary(4)  -indicates the temporary cold patch.
                "
            ::= { hwPatchNewEntry  3 }

        hwNewPatchAdminStatus OBJECT-TYPE
            SYNTAX INTEGER
                {
                 nooperation(-1),
                 active(1),
                 deactive(2),
                 delete(3),
                 run(4),
                 rollback(6),
                 patchbatchconfirm(7)
                }
            MAX-ACCESS read-write
            STATUS current
            DESCRIPTION
                "
                Patch management operations.
                Options:
                1.nooperation(-1)     -the state of start.
                2.active(1)           -activate a patch.
                3.deactive(2)         -deactivate a patch.
                4.delete(3)           -delete a patch.
                5.run(4)              -run a patch.
                6.rollback(6)         -roll back patch.
                7.patchbatchconfirm(7)-activate patches in batch.
                This function is no longer supported.
                "
            ::= { hwPatchNewEntry  4 }

        hwNewPatchOperState OBJECT-TYPE
            SYNTAX INTEGER
                {
                 patchActive(1),
                 patchDeActive(2),
                 patchRunning(4),
                 patchWaitActive(5),
                 patchWaitRunning(6),
                 patchWaitDelete(7)
                }
            MAX-ACCESS read-only
            STATUS current
            DESCRIPTION
                "
                The current state of the patch.
                Options:
                1.patchActive(1)      -indicates that a patch is in the activated state.
                2.patchDeActive(2)    -indicates that a patch is in the deactivated state.
                3.patchRunning(4)     -indicates that a patch is in the running state.
                4.patchWaitActive(5)  -indicates that a patch is in the to be activated state.
                5.patchWaitRunning(6) -indicates that a patch is in the state of waiting to be run.
                6.patchWaitDelete(7)  -indicates that a patch is in the state of waiting to be deleted.
                "
            ::= { hwPatchNewEntry  5 }

        hwNewPatchRely OBJECT-TYPE
            SYNTAX OCTET STRING (SIZE (0..255))
            MAX-ACCESS read-only
            STATUS current
            DESCRIPTION
                "
                The name of the patch on which the current patch is dependent.
                If the current patch has a dependent patch, the name of the dependent patch is displayed.
                If the current patch has more than one dependent patch,
                the names of the dependent patches are separated by '\'.
                For example, if patch HP0003 is dependent on patches HP0001 and HP0002,
                HP0001\HP0002 is displayed.
                "
            ::= { hwPatchNewEntry  6 }

        hwNewPatchRelied OBJECT-TYPE
            SYNTAX OCTET STRING (SIZE (0..255))
            MAX-ACCESS read-only
            STATUS current
            DESCRIPTION
                "
                The name of the patch that is dependent on the current patch.
                If a patch is dependent on the current patch, the name of the patch is displayed.
                If multiple patches are dependent on the current patch,
                the names of the patches are separated by '\'.
                For example, if HP0003 and HP0004 are dependent on HP0002, HP0003\HP0004 is displayed.
                "
            ::= { hwPatchNewEntry  7 }

        hwNewPatchRequestID OBJECT-TYPE
            SYNTAX Integer32
            MAX-ACCESS read-write
            STATUS current
            DESCRIPTION
                "
                Indicates the requestid of a patch asynchronous operation.
                To perform such an operation, use this parameter.
                Query object hwOperationInfoTable to obtain the operation result.
                The value of requestid can be any integer in the range of 0-0xFFFFFFFF.
                The requestid of an operation must be unique.
                "
            ::= { hwPatchNewEntry 8 }

        hwBackupDataToServer OBJECT IDENTIFIER ::= { hwLoadBackup 3 }

        hwFileServerTable   OBJECT-TYPE
            SYNTAX SEQUENCE OF HwFileServerEntry
            MAX-ACCESS not-accessible
            STATUS current
            DESCRIPTION
                "
                The parameter table for configuring a server for the device.
                The indexes of this table are hwFileServerType, hwFileDataType and hwFileServerPriority.
                "
            ::= { hwBackupDataToServer 1 }

        hwFileServerEntry OBJECT-TYPE
            SYNTAX HwFileServerEntry
            MAX-ACCESS not-accessible
            STATUS current
            DESCRIPTION
                "
                The parameter table for configuring a server for the device.
                The indexes of this entry are hwFileServerType, hwFileDataType and hwFileServerPriority.
                "
            INDEX { hwFileServerType, hwFileDataType, hwFileServerPriority }
            ::= { hwFileServerTable 1 }

        HwFileServerEntry ::=
            SEQUENCE {
                hwFileServerType
                    INTEGER,
                hwFileDataType
                    INTEGER,
                hwFileServerPriority
                    INTEGER,
                hwFileServerIpAddress
                    IpAddress,
                hwFileServerMode
                    INTEGER,
                hwFileUser
                    OCTET STRING,
                hwFileUserPassword
                    OCTET STRING,
                hwFilePathName
                    OCTET STRING,
                hwFilePort
                    Unsigned32,
                hwFileServerState
                    INTEGER,
                hwFileServerRowStatus
                    RowStatus
             }

        hwFileServerType OBJECT-TYPE
            SYNTAX INTEGER
                {
                 autobackup(1),
                 autoload(2)
                }
            MAX-ACCESS not-accessible
            STATUS current
            DESCRIPTION
                "
                The server type.
                Options:
                1.autobackup(1) -indicates the server for automatic backup.
                2.autoload(2)   -indicates the server for automatic loading.
                "
            ::= { hwFileServerEntry 1 }

        hwFileDataType OBJECT-TYPE
            SYNTAX INTEGER
                {
                 database(1),
                 configurationfile(2),
                 alarm(3),
                 log(4),
                 lastword(5),
                 cdr(6),
                 program(7),
                 bulkstat(8),
                 boardinfo(9),
                 ontfile(11),
                 deviceinfo(12),
                 udm(13),
                 cmcperformance(14)
                }
            MAX-ACCESS not-accessible
            STATUS current
            DESCRIPTION
                "
                The data type of a file.
                Options:
                1.database(1)              -indicates that the backup file type is database file.
                2.configurationfile(2)     -indicates that the backup file type is configuration file.
                3.alarm(3)                 -indicates that the backup file type is alarm file.
                4.log(4)                   -indicates that the backup file type is log file.
                5.lastword(5)              -indicates that the backup file type is last word.
                6.cdr(6)                   -indicates that the backup file type is multicast CDR file.
                7.program(7)               -indicates that the automatic loading file type is program.
                8.bulkstat(8)              -indicates that the backup file type is bulk statistic file.
                9.boardinfo(9)             -indicates that the backup file type is board info file.
                10.ontfile(11)             -indicates that the automatic loading file type is ont file.
                11.deviceinfo(12)          -indicates that the backup file type is expanded device info file.
                12.udm(13)                 -indicates that the backup file type is user data management file.
                13.cmcperformance(14)      -indicates that the backup file type is cmc performance file.
                "
            ::= { hwFileServerEntry 2 }

        hwFileServerPriority OBJECT-TYPE
            SYNTAX INTEGER
                {
                 primaryserver(1),
                 secondaryserver(2)
                }
            MAX-ACCESS not-accessible
            STATUS current
            DESCRIPTION
                "
                The type (active/standby) of the server.
                The system can be configured with a maximum of two servers.
                One as the active server and the other as the standby server.
                When the active server fails or is unreachable, the standby server starts to function.
                Options:
                1. primaryserver(1)   -indicates the active server.
                2. secondaryserver(2) -indicates the standby server.
                "
            ::= { hwFileServerEntry 3 }

        hwFileServerIpAddress OBJECT-TYPE
            SYNTAX IpAddress
            MAX-ACCESS read-create
            STATUS current
            DESCRIPTION
                "
                The IP address of the server.
                "
            ::= { hwFileServerEntry 4 }

        hwFileServerMode OBJECT-TYPE
            SYNTAX INTEGER
                {
                 tftp(1),
                 ftp(2),
                 sftp(3)
                }
            MAX-ACCESS read-create
            STATUS current
            DESCRIPTION
                "
                Protocal be used to transfer the file.
                Options:
                1.tftp(1)-indicates that TFTP is used to perform the backup through the network port.
                          When the transmission mode of the server is configured to TFTP, select tftp(1).
                          When TFTP is used for backup, you need not enter the user name (hwFileUser)
                          and the password (hwFileUserPassword).
                2.ftp(2) -indicates that FTP is used to perform the backup through the network port.
                          When the transmission mode of the server is configured to FTP, select ftp(2).
                          When FTP is used for the backup, you need to enter the user name (hwFileUser)
                          and the password (hwFileUserPassword).
                3.sftp(3)-indicates that SFTP is used to perform the backup through the network port.
                          Select sftp(3) when the transmission mode of the server is configured to SFTP.
                          When SFTP is used for backup, you need to enter the user name (hwFileUser)
                          and the password (hwFileUserPassword).
                          The instructions and data are encrypted during transmission.
                The SFTP transmission mode is recommended.
                "
            ::= { hwFileServerEntry 5 }

        hwFileUser OBJECT-TYPE
            SYNTAX OCTET STRING (SIZE (0..40))
            MAX-ACCESS read-create
            STATUS current
            DESCRIPTION
                "
                The backup user name, which is required in FTP mode and SFTP mode
                but is not required in TFTP mode.
                "
            ::= { hwFileServerEntry 6 }

        hwFileUserPassword OBJECT-TYPE
            SYNTAX OCTET STRING (SIZE (0..40))
            MAX-ACCESS read-create
            STATUS current
            DESCRIPTION
                "
                The backup password, which is required in FTP mode and SFTP mode
                but is not required in TFTP mode.
                "
            ::= { hwFileServerEntry 7 }

        hwFilePathName OBJECT-TYPE
            SYNTAX OCTET STRING (SIZE (0..128))
            MAX-ACCESS read-create
            STATUS current
            DESCRIPTION
                "
                The path to the backup file, which is not required in FTP mode, SFTP mode and TFTP mode.
                "
            ::= { hwFileServerEntry 8 }

        hwFilePort OBJECT-TYPE
            SYNTAX Unsigned32 (0..65535)
            MAX-ACCESS read-create
            STATUS current
            DESCRIPTION
                "
                Port number. It is only used by SFTP.
                Default: 22
                "
            ::= { hwFileServerEntry 9 }

        hwFileServerState OBJECT-TYPE
            SYNTAX INTEGER
                {
                 currentserver(1),
                 notcurrentserver(2)
                }
            MAX-ACCESS read-only
            STATUS current
            DESCRIPTION
                "
                Describe whether the server is current server.
                Options:
                1.currentserver(1)    -indicates that the server is the current server.
                2.notcurrentserver(2) -indicates that the server is not the current server.
                "
            ::= { hwFileServerEntry 10 }

        hwFileServerRowStatus OBJECT-TYPE
            SYNTAX RowStatus
            MAX-ACCESS read-create
            STATUS current
            DESCRIPTION
                "
                Operation status of NMS station, the NMS station can be createAndGo(4) and deleted(6).
                createAndGo(4) is supplied to create a new instance of a conceptual row.
                destroy(6) is supplied to delete the instances associated with an existing conceptual row.
                "
            ::= { hwFileServerEntry 11 }


        hwBackupPeriodTable OBJECT-TYPE
            SYNTAX SEQUENCE OF HwBackupPeriodEntry
            MAX-ACCESS not-accessible
            STATUS current
            DESCRIPTION
                "
                The periodic backup table of the device data.The index of this table is hwFileDataType.
                hwFileDataType is the file data type.
                The index value is in the range of 1-9 and 11-13.
                Options:
                1.database(1)              -indicates that the backup file type is database file.
                2.configurationfile(2)     -indicates that the backup file type is configuration file.
                3.alarm(3)                 -indicates that the backup file type is alarm file.
                4.log(4)                   -indicates that the backup file type is log file.
                5.lastword(5)              -indicates that the backup file type is last word.
                6.cdr(6)                   -indicates that the backup file type is multicast CDR file.
                7.program(7)               -indicates that the automatic loading file type is program.
                8.bulkstat(8)              -indicates that the backup file type is bulk statistic file.
                9.boardinfo(9)             -indicates that the backup file type is board info file.
                10.ontfile(11)             -indicates that the automatic loading file type is ont file.
                11.deviceinfo(12)          -indicates that the backup file type is expanded device info file.
                12.udm(13)                 -indicates that the backup file type is user data management file.
                13.cmcperformance(14)      -indicates that the backup file type is cmc performance file.
                "
            ::= { hwBackupDataToServer 2 }

        hwBackupPeriodEntry OBJECT-TYPE
            SYNTAX HwBackupPeriodEntry
            MAX-ACCESS not-accessible
            STATUS current
            DESCRIPTION
                "
                The periodic backup table of the device data.The index of this entry is hwFileDataType.
                hwFileDataType is the file data type.
                The index value is in the range of 1-9 and 11-13.
                Options:
                1.database(1)              -indicates that the backup file type is database file.
                2.configurationfile(2)     -indicates that the backup file type is configuration file.
                3.alarm(3)                 -indicates that the backup file type is alarm file.
                4.log(4)                   -indicates that the backup file type is log file.
                5.lastword(5)              -indicates that the backup file type is last word.
                6.cdr(6)                   -indicates that the backup file type is multicast CDR file.
                7.program(7)               -indicates that the automatic loading file type is program.
                8.bulkstat(8)              -indicates that the backup file type is bulk statistic file.
                9.boardinfo(9)             -indicates that the backup file type is board info file.
                10.ontfile(11)             -indicates that the automatic loading file type is ont file.
                11.deviceinfo(12)          -indicates that the backup file type is expanded device info file.
                12.udm(13)                 -indicates that the backup file type is user data management file.
                13.cmcperformance(14)      -indicates that the backup file type is cmc performance file.
                "
            INDEX { hwFileDataType }
            ::= { hwBackupPeriodTable 1 }

        HwBackupPeriodEntry ::=
            SEQUENCE
            {
                hwBackupInterval
                    Integer32,
                hwBackupTime
                    OCTET STRING,
                hwBackupPeriodSwitch
                    INTEGER
             }

        hwBackupInterval OBJECT-TYPE
            SYNTAX Integer32 (1..10)
            UNITS "day"
            MAX-ACCESS read-write
            STATUS current
            DESCRIPTION
                "
                The time interval of periodic backup.The interval is in the unit of day.
                Range: 1-10
                Default: 1
                Unit: day
                "
            DEFVAL { 1 }
            ::= { hwBackupPeriodEntry 1 }

        hwBackupTime OBJECT-TYPE
            SYNTAX OCTET STRING (SIZE (5))
            MAX-ACCESS read-write
            STATUS current
            DESCRIPTION
                "
                The time point of the periodic backup. It is in the format of <hh:mm>.
                Data's default backup time is 00:00,
                configuration's default backup time is 01:00,
                alarm's default backup time is 02:00,
                log's default backup time is 03:00,
                lastword's backup time is 04:00.
                "
            ::= { hwBackupPeriodEntry 2 }

        hwBackupPeriodSwitch OBJECT-TYPE
            SYNTAX INTEGER
                {
                 on(1),
                 off(2)
                }
            MAX-ACCESS read-write
            STATUS current
            DESCRIPTION
                "
                Period backup switch.
                Options:
                1.on(1)  -indicates that periodic backup is configured.
                2.off(2) -indicates that periodic backup is not configured.
                The default value is off(2).
                "
            DEFVAL { off }
            ::= { hwBackupPeriodEntry 3 }

        hwBackupCondition OBJECT IDENTIFIER ::= { hwBackupDataToServer 3 }

        hwBackupAlarmCondition OBJECT-TYPE
            SYNTAX Integer32 (500..1000)
            MAX-ACCESS read-write
            STATUS current
            DESCRIPTION
                "
                Setting and querying the condition of backing up the alarm.
                Range: 500-1000, indicating that the latest 500-1000 alarms of the current system can be backed up.
                Default { 500 }
                "
            ::= { hwBackupCondition 2 }

        hwBackupLogCondition OBJECT-TYPE
            SYNTAX Integer32 (100..250)
            MAX-ACCESS read-write
            STATUS current
            DESCRIPTION
                "
                Setting and querying the condition of backing up the log.
                Range: 100-250, indicating that the latest 100-250 logs of the current system can be backed up.
                Default { 100 }
                "
            ::= { hwBackupCondition 3 }

        hwBackupLastwordCondition OBJECT-TYPE
            SYNTAX Integer32 (200..300)
            MAX-ACCESS read-write
            STATUS current
            DESCRIPTION
                "
                Setting and querying the condition of backing up the last word.
                Range: 200-300, indicating that the latest 200-300 last words of the current system can be backed up.
                Default { 200 }
                "
            ::= { hwBackupCondition 4 }

        hwBackupAlarmConditionSwitch OBJECT-TYPE
            SYNTAX INTEGER
                {
                 on(1),
                 off(2)
                }
            MAX-ACCESS read-write
            STATUS current
            DESCRIPTION
                "
                Configuring the function of backing up the alarm.
                Options:
                1.on(1)  -indicates that the alarm information is backed up according to the configured conditions.
                2.off(2) -indicates that the alarm information is not backed up.
                Default { off }
                "
            ::= { hwBackupCondition 5 }

        hwBackupLogConditionSwitch OBJECT-TYPE
            SYNTAX INTEGER
                {
                 on(1),
                 off(2)
                }
            MAX-ACCESS read-write
            STATUS current
            DESCRIPTION
                "
                Configuring the function of backing up the log.
                Options:
                1.on(1)  -indicates that the log information is backed up according to the configured conditions.
                2.off(2) -indicates that the log information is not backed up.
                Default { off }
                "
            ::= { hwBackupCondition 6 }

        hwBackupLastwordConditionSwitch OBJECT-TYPE
            SYNTAX INTEGER
                {
                 on(1),
                 off(2)
                }
            MAX-ACCESS read-write
            STATUS current
            DESCRIPTION
                "
                Configuring the function of backing up the last word.
                Options:
                1.on(1)  -indicates that the last word information is backed up according to the configured conditions.
                2.off(2) -indicates that the last word information is not backed up.
                Default { off }
                "
            ::= { hwBackupCondition 7 }

        hwBackupByHandTable OBJECT-TYPE
            SYNTAX SEQUENCE OF HwBackupByHandEntry
            MAX-ACCESS not-accessible
            STATUS current
            DESCRIPTION
                "
                The manual data backup table. The index of this table is hwFileDataType.
                hwFileDataType is the file data type. The index value is in the range of 1-9 and 11-13.
                Options:
                1.database(1)              -indicates that the backup file type is database file.
                2.configurationfile(2)     -indicates that the backup file type is configuration file.
                3.alarm(3)                 -indicates that the backup file type is alarm file.
                4.log(4)                   -indicates that the backup file type is log file.
                5.lastword(5)              -indicates that the backup file type is last word.
                6.cdr(6)                   -indicates that the backup file type is multicast CDR file.
                7.program(7)               -indicates that the automatic loading file type is program.
                8.bulkstat(8)              -indicates that the backup file type is bulk statistic file.
                9.boardinfo(9)             -indicates that the backup file type is board info file.
                10.ontfile(11)             -indicates that the automatic loading file type is ont file.
                11.deviceinfo(12)          -indicates that the backup file type is expanded device info file.
                12.udm(13)                 -indicates that the backup file type is user data management file.
                13.cmcperformance(14)      -indicates that the backup file type is cmc performance file.
                "
            ::= { hwBackupDataToServer 4 }

        hwBackupByHandEntry OBJECT-TYPE
            SYNTAX HwBackupByHandEntry
            MAX-ACCESS not-accessible
            STATUS current
            DESCRIPTION
                "
                The manual data backup table. The index of this entry is hwFileDataType.
                hwFileDataType is the file data type. The index value is in the range of 1-9 and 11-13.
                Options:
                1.database(1)              -indicates that the backup file type is database file.
                2.configurationfile(2)     -indicates that the backup file type is configuration file.
                3.alarm(3)                 -indicates that the backup file type is alarm file.
                4.log(4)                   -indicates that the backup file type is log file.
                5.lastword(5)              -indicates that the backup file type is last word.
                6.cdr(6)                   -indicates that the backup file type is multicast CDR file.
                7.program(7)               -indicates that the automatic loading file type is program.
                8.bulkstat(8)              -indicates that the backup file type is bulk statistic file.
                9.boardinfo(9)             -indicates that the backup file type is board info file.
                10.ontfile(11)             -indicates that the automatic loading file type is ont file.
                11.deviceinfo(12)          -indicates that the backup file type is expanded device info file.
                12.udm(13)                 -indicates that the backup file type is user data management file.
                13.cmcperformance(14)      -indicates that the backup file type is cmc performance file.
                "
            INDEX { hwFileDataType }
            ::= { hwBackupByHandTable 1 }

        HwBackupByHandEntry ::=
            SEQUENCE
            {
                hwBackupByHand
                    Integer32
            }

            hwBackupByHand OBJECT-TYPE
            SYNTAX Integer32 (1)
            MAX-ACCESS read-write
            STATUS current
            DESCRIPTION
                "
                Whether the backup is performed manually. The value of hwBackupByHand can only be set to 1.
                When the value is set to 1, the data backup is triggered.
                "
            ::= { hwBackupByHandEntry 1 }

-- 1.3.6.1.4.1.2011.6.6.1.7
        hwAgentUpdateOntTable OBJECT-TYPE
            SYNTAX SEQUENCE OF HwAgentUpdateOntEntry
            MAX-ACCESS not-accessible
            STATUS current
            DESCRIPTION
                "
                The optical network unit (ONT) batch upgrade management table.
                When ONT batch upgrade through OLT agent is started on the NMS,
                you can query the upgrade status, upgrade progress and error
                code information about each ONT through this table.
                The indexes of this table are hwOntFrameIndex, hwOntSlotIndex, hwOntPortIndex
                and hwUpdateOntIndex of the ONT to be queried.Note that the index parameters
                hwFrameIndex, hwSlotIndex, hwUpdateOntIndex,and hwPortIndex are optional
                (To indicate that a parameter is optional, set the parameter to -1).
                For example, to return the information about
                all the ONTs connected to a specified port, set hwUpdateOntIndex to -1.
                Then the information about all the ONTs of a port is returned.
                To return the status of all the ONTs connected to all ports in a specified
                slot of a frame, set both hwUpdateOntIndex and hwPortIndex to -1.
                "
            ::= { hwLoadBackupMon 7 }

        -- 1.3.6.1.4.1.2011.6.6.1.7.1
        hwAgentUpdateOntEntry OBJECT-TYPE
            SYNTAX HwAgentUpdateOntEntry
            MAX-ACCESS not-accessible
            STATUS current
            DESCRIPTION
                "
                The optical network unit (ONT) batch upgrade management table.
                When ONT batch upgrade through OLT agent is started on the NMS,
                you can query the upgrade status, upgrade progress and error
                code information about each ONT through this table.
                The indexes of this entry are hwOntFrameIndex, hwOntSlotIndex, hwOntPortIndex
                and hwUpdateOntIndex of the ONT to be queried.Note that the index parameters
                hwFrameIndex, hwSlotIndex, hwUpdateOntIndex,and hwPortIndex are optional
                (To indicate that a parameter is optional, set the parameter to -1).
                For example, to return the information about
                all the ONTs connected to a specified port, set hwUpdateOntIndex to -1.
                Then the information about all the ONTs of a port is returned.
                To return the status of all the ONTs connected to all ports in a specified
                slot of a frame, set both hwUpdateOntIndex and hwPortIndex to -1.
                "
            INDEX { hwOntFrameIndex, hwOntSlotIndex, hwOntPortIndex, hwUpdateOntIndex }
            ::= { hwAgentUpdateOntTable 1 }

        HwAgentUpdateOntEntry ::=
            SEQUENCE
            {
                hwOntFrameIndex
                    Integer32,
                hwOntSlotIndex
                    Integer32,
                hwOntPortIndex
                    Integer32,
                hwUpdateOntIndex
                    Integer32,
                hwOntUpdateState
                    DisplayString,
                hwOntUpdateStateAndProgress
                    DisplayString
             }

    -- 1.3.6.1.4.1.2011.6.6.1.7.1.1
        hwOntFrameIndex OBJECT-TYPE
            SYNTAX Integer32 (0..1024)
            MAX-ACCESS read-only
            STATUS current
            DESCRIPTION
                "
                The number of the frame in the device.
                "
            ::= { hwAgentUpdateOntEntry 1 }

    -- 1.3.6.1.4.1.2011.6.6.1.7.1.2
        hwOntSlotIndex OBJECT-TYPE
            SYNTAX Integer32 (0..255)
            MAX-ACCESS read-only
            STATUS current
            DESCRIPTION
                "
                The number of the slot. The present slot index is determined by its
                physical position in the board.
                "
            ::= { hwAgentUpdateOntEntry 2 }

    -- 1.3.6.1.4.1.2011.6.6.1.7.1.3
        hwOntPortIndex OBJECT-TYPE
            SYNTAX Integer32 (0..255)
            MAX-ACCESS read-only
            STATUS current
            DESCRIPTION
                "
                The number of the port.
                "
            ::= { hwAgentUpdateOntEntry 3 }

    -- 1.3.6.1.4.1.2011.6.6.1.7.1.4
        hwUpdateOntIndex OBJECT-TYPE
            SYNTAX Integer32 (0..127)
            MAX-ACCESS   read-only
            STATUS      current
            DESCRIPTION
                "
                ONT ID.
                "
              ::= { hwAgentUpdateOntEntry 4}

    -- 1.3.6.1.4.1.2011.6.6.1.7.1.5
        hwOntUpdateState OBJECT-TYPE
            SYNTAX DisplayString
            MAX-ACCESS read-only
            STATUS current
            DESCRIPTION
                "
                ONT update state.
                data structure: ONT IP + ONT update state
                ----------------------------------------------------------------------
                |  ONT NUM |  ONT IP  | ONT update  |  ONT IP  | ONT update | _  _   |
                |   (2B)   |   (4B)   |  state (1B) |   (2B)   |  state(1B) |        |
                ----------------------------------------------------------------------
                state enum:
                Loading is successful(1): The ont-packetfile is loaded to the ONT successfully.
                Loading fails(2): Loading the ont-packetfile to the ONT failed.
                Not upgrade(3): Upgrading the ONT does not start.
                Loading(4): The ONT is being loaded with ont-packetfile.
                Resetting(5): The ONT is being reset.
                Upgrade fails(6): Upgrading the ONT fails.
                Upgrade is successful(7): Upgrading the ONT is successful.

                Because of the restrictions on the SNMP packet, the packet of up to 8 KB can be transmitted.
                When the size of the packet to be reported exceeds 8 KB, the packet must be compressed.
                The compress format of the packet is shown in the following figure.
                -----------------------------------------------------------------------
                | DATA-LENGTH | FLAG  |  TLV-NUM  |  TYPE  |  LEN  |  CRC  |          |
                ------------------------------------------------------------          |
                |                                                                     |
                |                                                                     |
                |                                                                     |
                -----------------------------------------------------------------------
                In the compressed packet:
                DATA-LENGTH occupies four bytes to store the whole length of the file, including the header structure.
                FLAG occupies two bytes to store the flag, which indicates the format of the file contents.
                In this compressed packet, the flag indicates that the format of the file contents is compressed.
                0xFEFE indicates compress and 0 indicates non-compress.
                TLV-NUM indicates the number of TLVs that the file carries. In this compressed packet, TLV-NUM is 1,
                indicating the CRC value of the compressed content. The following continuous bytes TYPE, LEN, and CRC
                are data in the TLV format. Each of TYPE, LEN, and CRC occupies two bytes. In this compressed packet,
                TYPE, LEN, and CRC record the CRC value of the compressed content. TYPE indicates the CRC type.
                LEN indicates the number of bytes that the CRC occupies and the actual value is 2.
                CRC stores the CRC value of the compressed content.
                The actual returned content is compressed in the .zip format and stored in the final field of compressed
                content.
                "
            ::= { hwAgentUpdateOntEntry 5 }

    -- 1.3.6.1.4.1.2011.6.6.1.7.1.6
        hwOntUpdateStateAndProgress OBJECT-TYPE
            SYNTAX DisplayString
            MAX-ACCESS read-only
            STATUS current
            DESCRIPTION
                "
                ONT update state and load progress or load error num.
                data structure: ONT IP + ONT update state + load progress/error num
                ---------------------------------------------------------------------------------------------------------
                |  ONT NUM |  ONT IP  | ONT update  |  load progress  |  ONT IP  | ONT update  |  load progress  |  _   |
                |   (2B)   |   (4B)   |  state (1B) |   /error num(4B |   (4B)   |  state (1B) |   /error num(4B |      |
                ---------------------------------------------------------------------------------------------------------
                load progress: percent, such as 20%
                error num:
                Loading of the OLT fails(1): Loading the ont-packetfile from the DC to the OLT failed.
                Loading of the ONT fails(2): Loading the ont-packetfile from the OLT to the ONT failed.
                ONT version does not match(3): After the ONT reset, the ONT version does not match the target ONT version.
                If the ONT loading is successful, the loading progress is displayed as 100%.
                If the ONT loading fails, the related error code is returned to indicate the reason.
                "
            ::= { hwAgentUpdateOntEntry 6 }

-- 1.3.6.1.4.1.2011.6.6.1.8
        hwUndoLoadBackup OBJECT IDENTIFIER ::= { hwLoadBackupMon 8 }
--   1.3.6.1.4.1.2011.6.6.1.8.1
        hwUndoOperType OBJECT-TYPE
            SYNTAX INTEGER
            {
                nooperation(-1),
                load(1),
                backup(2)
            }
            MAX-ACCESS read-write
            STATUS current
            DESCRIPTION
                "
                Cancel the operation of this type.
                You can cancel the operations of loading and backing up the database through
                this node when you incorrectly perform the operations.
                Options:
                1.nooperation(-1) -indicates that no operation is performed in the system currently.
                2.load(1)         -indicates that the loading operation is to be cancelled.
                3.backup(2)       -indicates that the backup operation is to be cancelled.
                "
            ::= { hwUndoLoadBackup 1 }


--   1.3.6.1.4.1.2011.6.6.1.8.2
        hwUndoContent OBJECT-TYPE
            SYNTAX INTEGER
            {
                nothing(-1),
                data(1),
                script(2)
            }
            MAX-ACCESS read-write
            STATUS current
            DESCRIPTION
                "
                Cancel the contents of the operation.
                You can cancel the operations of loading and backing up the database
                through this node when you incorrectly perform the operations.
                Options:
                1.nothing(-1) -indicates that no operation is performed in the system currently.
                2.data(1)     -indicates the operation on a database is to be cancelled.
                               Both the loading and backup of a database can be cancelled.
                3.script(2)   -indicates that the operation on a script is to be cancelled.
                               Only the loading of a script can be cancelled. The backup of a script cannot be cancelled.
                "
            ::= { hwUndoLoadBackup 2 }

        hwLoadOperFlag OBJECT-TYPE
            SYNTAX INTEGER
            {
                 enableLoad(1),  -- enable load operator 
                 disableLoad(2)  -- disable load operator
            }
            MAX-ACCESS read-only
            STATUS current
            DESCRIPTION
                "
                The object is used to identify whether the current system  can load software.
                Options:
                1.enableLoad(1) -The current system can load software. 
                2.disableLoad(2) -The current system can not load software.
                "
            ::= { hwLoadBackupMon 9 }

        hwStatusCollect OBJECT IDENTIFIER ::= { hwLoadBackup 5 }

        hwStatusInfoTable OBJECT-TYPE
            SYNTAX SEQUENCE OF HwStatusInfoEntry
            MAX-ACCESS not-accessible
            STATUS current
            DESCRIPTION
             "The table contains all collectable status information in the system.
              The index of this table is hwStatusID. The index value is the status ID.
              The table can only be queried. It cannot be configured.
             "
            ::= { hwStatusCollect 1 }

        hwStatusInfoEntry OBJECT-TYPE
            SYNTAX HwStatusInfoEntry
            MAX-ACCESS not-accessible
            STATUS current
            DESCRIPTION
             "The table contains all collectable status information in the system.
              The index of this entry is hwStatusID. The index value is the status ID.
              The table can only be queried. It cannot be configured.
             "
            INDEX { hwStatusID }
            ::= { hwStatusInfoTable 1 }

        HwStatusInfoEntry ::=
            SEQUENCE
            {
                hwStatusID
                    Integer32,
                hwStatusDescription
                    OCTET STRING
            }

            hwStatusID OBJECT-TYPE
            SYNTAX Integer32
            MAX-ACCESS not-accessible
            STATUS current
            DESCRIPTION
                "
                Status ID.Be consistent with the status parameters in the hwStatusCollectMask.
                "
            ::= { hwStatusInfoEntry 1 }

        hwStatusDescription OBJECT-TYPE
            SYNTAX OCTET STRING (SIZE (1..512))
            MAX-ACCESS read-only
            STATUS current
            DESCRIPTION
                "
                Status description.
                -----------------------------------------------------
                statusID               | description
                -----------------------------------------------------
                cpu(0)                 | CPU usage of the control board
                board(1)               | running status of the board
                frame(2)               | running status of the shelf
                temperature(3)         | environmental temperature
                power(4)               | status of the power supply
                fan(5)                 | status of the fan monitoring objects
                upstreamport(6)        | status of the uplink port
                syncstatus(7)          | sync status
                esc(8)                 | Esc state
                lswport(9)             | Lsw ports status
                ap(10)                 | status of the fault ap, return 100 logs at most
                h248mginterface(11)    | H248 MG interface status(OLT/MXU)
                mgcpmginterface(12)    | MGCP MG interface status(OLT/MXU)
                tcu(13)                | Tcu state
                uplinkporttraffic(14)  | traffic on the uplink port(OLT/MXU)
                onustatus(15)          | status of the ONU(OLT)
                xpontraffic(16)        | traffic on the xPON port(OLT)
                mxusnmpinfo(17)        | SNMP information about the MxU(OLT)
                potsvoltage(18)        | voltage status of the pots board
                boardversion(19)       | version of the board
                gponProtectGroup(20)   | status of Gpon protect group
                linkAggregation(21)    | status of link aggregation
                serviceProcessBoardProtectGroup(22)     | status of ServiceProcessBoard protect group
                "
            ::= { hwStatusInfoEntry 2 }

        hwStatusCollectIndicate OBJECT-TYPE
            SYNTAX INTEGER
                {
                 start(1),
                 stop(2)
                }
            MAX-ACCESS read-write
            STATUS current
            DESCRIPTION
                "
                Start to collect status or stop collecting status.
                Options:
                1. start(1) -Collecting status starts.
                2. stop(2)  -Collecting status stops.
                "
            ::= { hwStatusCollect 2 }

        hwStatusCollectMask OBJECT-TYPE
            SYNTAX BITS
                {
                 cpu(0),
                 board(1),
                 frame(2),
                 temperature(3),
                 power(4),
                 fan(5),
                 upstreamport(6),
                 syncstatus(7),
                 esc(8),
                 lswport(9),
                 ap(10),
                 h248mginterface(11),
                 mgcpmginterface(12),
                 tcu(13),
                 uplinkporttraffic(14),
                 onustatus(15),
                 xpontraffic(16),
                 mxusnmpinfo(17),
                 potsvoltage(18),
                 boardversion(19),
                 gponProtectGroup(20),
                 linkAggregation(21),
                 serviceProcessBoardProtectGroup(22)
                }
            MAX-ACCESS read-write
            STATUS current
            DESCRIPTION
                "
                Collecting status mask.
                Options:
                1.cpu(0)                 -indicates that the CPU usage of the control board.
                2.board(1)               -indicates that the running status of the board.
                3.frame(2)               -indicates that the running status of the shelf.
                4.temperature(3)         -indicates that the environmental temperature.
                5.power(4)               -indicates that the status of the power supply.
                6.fan(5)                 -indicates that the status of the fan monitoring objects.
                7.upstreamport(6)        -indicates the status of the uplink port.
                8.syncstatus(7)          -indicates the sync status.
                9.esc(8)                 -indicates the Esc state.
                10.lswport(9)            -indicates the Lsw ports status.
                11.ap(10)                -indicates the the running status of the fault ap, return 100 logs at most.
                12.h248mginterface(11)   -indicates the H248 MG interface status.
                13.mgcpmginterface(12)   -indicates the MGCP MG interface status.
                14.tcu(13)               -indicates the Tcu state.
                15.uplinkporttraffic(14) -indicates the traffic on the uplink port.
                16.onustatus(15)         -indicates the status of the ONU.
                17.xpontraffic(16)       -indicates the traffic on the xPON port.
                18.mxusnmpinfo(17)       -indicates the SNMP information about the MxU.
                19.potsvoltage(18)       -indicates the voltage status of the pots board.
                20.boardversion(19)      -indicates the version of the board.
                21.gponProtectGroup(20)  -indicates the status of Gpon protect group.
                22.linkAggregation(21)   -indicates the status of link aggregation.
                23.serviceProcessBoardProtectGroup(22)    -indicates the status of ServiceProcessBoard protect group.
                From left to right, each bit indicates a status parameter.
                If the bit is set to 1, it indicates collecting the corresponding status parameter.
                If the bit is set to 0, it indicates ignoring the corresponding status parameter.
                The value of the status parameter is the serial number of the bit.
                For example, if only status parameters cpu, board, and fan need to be collected,
                the mask value is 11000100 (binary), that is, 0xC4.
                "
            ::= { hwStatusCollect 3 }

        hwStatusCollectType OBJECT-TYPE
            SYNTAX INTEGER
                {
                 fault(1),
                 all(2)
                }
            MAX-ACCESS read-write
            STATUS current
            DESCRIPTION
                "
                Collecting type.
                Options:
                1.fault(1) -Collecting system fault status information.
                2.all(2)   -Collecting all the system information.
                When the collection start command is sent, the port is an optional object. If the port is not issued,
                only the fault status information is collected by default.
                Default { fault }
                "
            ::= { hwStatusCollect 4 }

        hwStatusCollectProgress OBJECT-TYPE
            SYNTAX Integer32 (0..100)
            MAX-ACCESS read-only
            STATUS current
            DESCRIPTION
                "
                The progress of collecting the device status information about the object can be queried
                at the specified time.
                If the health diagnosis has not started, the displayed collection progress is 0.
                If the health diagnosis has started but is not yet complete, the displayed collection progress
                is the current collection progress.
                If the health diagnosis has stopped (including the stop after the diagnosis is complete,
                the stop when an error occurs, and the stop after a collection stop command is issued),
                the displayed collection progress is 100.
                "
            ::= { hwStatusCollect 5 }


        hwStatusCollectResult OBJECT-TYPE
            SYNTAX OCTET STRING (SIZE (0..8192))
            MAX-ACCESS read-only
            STATUS current
            DESCRIPTION
                "
                After the collection of the status information about an object is complete, the collection result can be queried.
                If the health diagnosis has not started, or the health diagnosis has started but is not yet complete,
                the displayed collection result is a blank character string.
                If the health diagnosis has stopped, the displayed collection result is the actual data in the latest collection.
                That is, after a collection is complete, the collection data is retained until the next collection starts.
                1. The result returned by hwStatusCollectResult is displayed in the following format:
                ----------------------------------------------------------------------
                     |  DATA-LENGTH (4byte)         | FLAG (2byte)  | TLV_NUM(2byte) |
                     |---------------------------------------------------------------
                     | TYPE1(2byte) | LEN1(2byte)   |  VALUE1                        | -->CRC
                     |---------------------------------------------------------------
                     | TYPE2(2byte) | LEN2(2byte)   |  VALUE2                        | -->TIME_INFO
                ----------------------------------------------------------------------
                     |                                                               |
                     |        the content of Collected status                        |
                     |                                                               |
                ----------------------------------------------------------------------
                 DATA-LENGTH: It is used to save the length of a file.
                 FLAG: It is used to save the flag of a file, which represents the format of the file content.
                 Currently, the file content uses the non-compressing format, corresponding to flag 0.
                 TLV_NUM: It indicates the number of TLVs following a file. Currently, the number is 2,
                 indicating two TLVs, namely the CRC value and the time information.
                 The CRC value is used to record the compressed collection result. Currently, the CRC value is 0,
                 an invalid value, because the collection result is not compressed.
                 The data is reserved (type value 0) for the future performance expansion.
                 The time information indicates the time when the collection is complete. It is standard time on
                 the device and is recorded in a character string.
                 The format is <YYYY-MM-DD HH:MM:SS GMT{+/-}HH:MM> and the type value is 1.

                2. The content of the status information is as follows (taking the board running status
                and the CPU usage status information as an example):
                  -----------------------------------------------------------------------------------------
                  |hwStatusID|hwStatusDescription|instance   |result of diagnoses|         state           |
                  -----------------------------------------------------------------------------------------
                  | 0        | CPU occupancy     |NULL       | 0/1(ok/false)     |0-100(%)                 |
                  ------------------------------------------------------------------------------------------
                  | 1        | Board state       |frame/slot | 0/1(ok/false)     |0-4(0:null;1:autofind;   |
                  |          |                   |           |                   |2:fail;3:config;4:active)|
                  ------------------------------------------------------------------------------------------
                In the preceding content, each status index indicates a fault diagnosis point, and instance
                indicates the minimum unit of data collection for the fault diagnosis point.
                Each instance represents a piece of record in the diagnosis result. When the diagnosis point
                corresponds to only one instance, the displayed instance value is NULL.
                The data indicates the actual collection data about the instance of a fault diagnosis point.

                3. The format of the reported status information is as follows:
                The diagnosis item index and the instance determine a record. Each record contains the following
                information:
                The diagnosis item index, instance, diagnosis result, and status data. The information in each
                record is separated by ~ and two records are separated by +.
                For example, when the CPU usage (no instance) reaches 98%, the format of the reported information
                is 0~~1~98%. When board 0/2 is in the faulty state whereas board 0/3 is in the normal state,
                the format of the reported information is 1~0/2~1~fail+1~0/3~0~active.
                If a status information collection fails, the format of the reported information contains only
                the status item index and the diagnosis result (1).
                For example, when the collection of the board running information fails,
                the format of the reported information is 1~~1~.
                "
            ::= { hwStatusCollect 6 }

        hwStatusCollectResultSize OBJECT-TYPE
            SYNTAX Integer32
            MAX-ACCESS read-only
            STATUS current
            DESCRIPTION
                "
                The size of the Collecting result, unit is byte.
                "
            ::= { hwStatusCollect 7 }

        hwStatusCollectReady OBJECT-TYPE
            SYNTAX INTEGER
                {
                 ready(1),
                 notReady(2)
                }
            MAX-ACCESS read-only
            STATUS current
            DESCRIPTION
                "
                Ready status for health diagnosis.
                Options:
                1.ready(1)    -The device is ready and health diagnosis can start.
                2.notReady(2) -The device is not ready and health diagnosis cannot start.
                "
            ::= { hwStatusCollect 8 }

        hwLoadPara OBJECT IDENTIFIER ::= { hwLoadBackup 6 }

        hwSysMultiCastLoad OBJECT-TYPE
            SYNTAX INTEGER
                {
                 enabled(1),
                 disabled(2)
                }
            MAX-ACCESS read-write
            STATUS current
            DESCRIPTION
                "
                Configuring the function of the MDU upgrade through OLT agent.
                Options:
                1.enabled(1)  -indicates that the upgrade is enabled.
                2.disabled(2) -indicates that the upgrade is disabled.
                Default:disabled(2)
                "
            ::= { hwLoadPara 1 }

        hwSDLoadResult OBJECT-TYPE
            SYNTAX OCTET STRING (SIZE (1..5000))
            MAX-ACCESS read-only
            STATUS obsolete
            DESCRIPTION
                "
                The results of file loading from the SD card by the host during
                the query of the SD card office deployment.
                The host assembles the result of SD card loading to a string
                and submits the string to the NMS for resolution.
                The maximum length of a string is 5 KB.The format of loading
                result is:filename-1|result-1/filename-2|result-2/filename-3|result-3.
                For example, program.efs|0/cpld.efs|0/load-io.efs|6561502.
                "
            ::= { hwLoadPara 2 }

        hwDataReplaceResult OBJECT-TYPE
        SYNTAX INTEGER
            {
             success(1),
             failure(2),
             invalid(3)
            }
        MAX-ACCESS read-only
        STATUS current
        DESCRIPTION
         "The result of load database and start up.
          Options:
          1. Success(1)        -device load database start up successfull.
          2. Failure(2)        -device load database start up failure.
          3. Invalid(3)        -invalid result.
        Default { Invalid }         "
        ::= { hwLoadPara 3 }

        hwPatchTrapsVbOids      OBJECT IDENTIFIER ::= { hwPatch  4 }

        hwPatchResult  OBJECT-TYPE
            SYNTAX Integer32
            MAX-ACCESS accessible-for-notify
            STATUS current
            DESCRIPTION
                "
                The result of patch rollback.
                0 indicates that patch rollback is successful.
                Nonzero digits are error code indicating that patch rollback failed.
                For the meaning of error code, see error code list.
                "
            ::= { hwPatchTrapsVbOids 1 }

        hwPatchOperation  OBJECT-TYPE
            SYNTAX INTEGER
                {
                 patchnull(0),
                 patchload(1),
                 patchactive(2),
                 patchdeactive(3),
                 patchrun(4),
                 patchdelete(5),
                 patchrollback(6),
                 patchshow(7),
                 patchrestore(8),
                 patchbatchrun(9)
                }
            MAX-ACCESS accessible-for-notify
            STATUS current
            DESCRIPTION
                "
                The operation of patching file.
                Options:
                1.patchnull(0)     -patchnull.
                2.patchload(1)     -Load the Patch.
                3.patchactive(2)   -Active the Patch.
                4.patchdeactive(3) -Deavtive the Patch.
                5.patchrun(4)      -Run the Patch.
                6.patchdelete(5)   -Delete the Patch.
                7.patchrollback(6) -RollBack the Patch.
                8.patchshow(7)     -Query the Patch.
                9.patchrestore(8)  -Restore the Patch.
                10.patchbatchrun(9)-Batch run the Patch.
                "
            ::= { hwPatchTrapsVbOids 2}


        hwPatchTraps            OBJECT IDENTIFIER ::= { hwPatch  5 }

        hwPatchCommonTraps      OBJECT IDENTIFIER ::= { hwPatchTraps  1 }
        hwPatchCommonTrapsPrefix OBJECT IDENTIFIER ::= { hwPatchCommonTraps 0 }

        hwPatRollBackOkTrap   NOTIFICATION-TYPE
            OBJECTS
            {
                hwFrameIndex,
                hwSlotIndex,
                hwPatchOperation,
                hwPatchResult
            }
            STATUS current
            DESCRIPTION
                "
                This trap message is reported when the patch rollback is successful.
                "
            ::= { hwPatchCommonTrapsPrefix 1 }


        hwPatRollBackFailTrap   NOTIFICATION-TYPE
            OBJECTS
            {
                hwFrameIndex,
                hwSlotIndex,
                hwPatchOperation,
                hwPatchResult
            }
            STATUS current
            DESCRIPTION
                "
                This trap message is reported when the patch rollback fails.
                "
            ::= { hwPatchCommonTrapsPrefix 2 }


        hwPatColdPatDiffTrap   NOTIFICATION-TYPE
            STATUS current
            DESCRIPTION
                "
                This trap message is reported when the states of cold patches on the active and
                standby control boards are inconsistent.
                "
            ::= { hwPatchCommonTrapsPrefix 3 }

        hwPatchInActiveTrap   NOTIFICATION-TYPE
            STATUS current
            DESCRIPTION
                "
                This trap message is reported when a patch stays in the activated state for 24 hours
                for the first time. 24 hours later, if the patch is still in the activated state, this trap
                message is reported every 6 hours.
                "
            ::= { hwPatchCommonTrapsPrefix 4 }

        hwPatchInDeActiveTrap   NOTIFICATION-TYPE
            STATUS current
            DESCRIPTION
                "
                This trap message is reported when a patch stays in the deactivated state for 24 hours
                for the first time. 24 hours later, if the patch is still in the deactivated state, this trap
                message is reported every 6 hours.
                "
            ::= { hwPatchCommonTrapsPrefix 5}

        hwPatchRestoreTrap   NOTIFICATION-TYPE
            STATUS current
            DESCRIPTION
                "
                This trap message is reported when the standby control board is reset because the patch
                statuses on the active and standby control boards are different.
                "
            ::= { hwPatchCommonTrapsPrefix 6 }


        hwPatchAlarmTraps       OBJECT IDENTIFIER ::= { hwPatchTraps  2 }
        hwPatchAlarmTrapsPrefix OBJECT IDENTIFIER ::= { hwPatchAlarmTraps 0 }

        hwPatchInActiveStateTrap   NOTIFICATION-TYPE
            STATUS current
            DESCRIPTION
                "
                This trap message is reported when a patch stays in the activated state for 24 hours for
                the first time. 24 hours later, if the patch is still in the activated state, this trap message
                is reported every 6 hours.
                "
            ::= { hwPatchAlarmTrapsPrefix 1 }

        hwPatchInDeactiveStateTrap NOTIFICATION-TYPE
            STATUS current
            DESCRIPTION
                "
                This trap message is reported when a patch stays in the deactivated state for 24 hours for the
                first time. 24 hours later, if the patch is still in the deactivated state, this trap message is
                reported every 6 hours.
                "
            ::= { hwPatchAlarmTrapsPrefix 2 }

        hwColdPatchInconsistentTrap NOTIFICATION-TYPE
            STATUS current
            DESCRIPTION
                "
                This trap message is reported when the states of cold patches on the active and
                standby control boards are inconsistent.
                "
            ::= { hwPatchAlarmTrapsPrefix 3 }

         hwPatchNeedResetBoardTrap NOTIFICATION-TYPE
            STATUS current
            DESCRIPTION
                "
                After the patch is activated or deleted, the operation takes effect in certain
                cases only after board or system reset. In such cases, if the board or system
                is not reset 24 hours after the patch is activated or deleted, this trap message
                is sent. If the board or system has not reset all the time, this trap message
                is sent once every 24 hours.
                "
            ::= { hwPatchAlarmTrapsPrefix 4 }

--Trapsparama

        hwLoadBackupTrapsVbOids      OBJECT IDENTIFIER ::= { hwLoadBackup  7 }

        hwLoadBackupResult OBJECT-TYPE
            SYNTAX Integer32
            MAX-ACCESS accessible-for-notify
            STATUS current
            DESCRIPTION
                "
                The result of load/backup.
                The value 0 means 'No error';
                The value 6561510 means 'Failed to transfer the file';
                The value 6561553 means 'Username or password error';
                The value 6561620 means 'The server is unreachable';
                The value 6561623 means 'Failed to operate the remote file';
                The value 6561625 means 'The SSH key is incorrect';
                The value 6561626 means 'The path does not exist';
                The value 6561627 means 'The file does not exist'.
                "
            ::= { hwLoadBackupTrapsVbOids 1 }


        hwLoadBackupGuage   OBJECT-TYPE
            SYNTAX Integer32
            MAX-ACCESS accessible-for-notify
            STATUS current
            DESCRIPTION
                "
                The gauge of load/backup.
                "
            ::= { hwLoadBackupTrapsVbOids 2 }


        hwRollResult OBJECT-TYPE
            SYNTAX INTEGER
            {
                rollOk(1),
                rollFailed(2),
                rollError(3)
            }
            MAX-ACCESS accessible-for-notify
            STATUS current
            DESCRIPTION
                "
                Result of the rollback operation.
                Options:
                1. rollOk(1)     -The rollback is successful.
                2. rollFailed(2) -The rollback fails.
                3. rollError(3)  -An abnormality occurs during rollback.
                "
            ::= { hwLoadBackupTrapsVbOids 3}


        hwLoadBackObject OBJECT-TYPE
            SYNTAX INTEGER
            {
                loadbackupobjectmasterboard(1),
                loadbackupobjectmastersubboard(2),
                loadbackupobjectslaveboard(3),
                loadbackupobjectslavesubboard(4),
                loadbackupobjectmasterslave(5),
                loadbackupobjectserviceboard(6),
                loadbackupobjectservicesubboard(7),
                loadbackupobjectserviceport(8),
                loadbackupobjectframeboard(9),
                loadbackupobjectemmboard(10),
                loadbackupobjectbackboard(11),
                loadbackupobjectsystem(12)
            }
            MAX-ACCESS accessible-for-notify
            STATUS current
            DESCRIPTION
                "
                Load/backup object.
                Options:
                1.loadbackupobjectmasterboard(1)     -Load the object of master board.
                2.loadbackupobjectmastersubboard(2)  -Load the object of master subboard.
                3.loadbackupobjectslaveboard(3)      -Load the object of slave board.
                4.loadbackupobjectslavesubboard(4)   -Load the object of slave subboard.
                5.loadbackupobjectmasterslave(5)     -Load the object of master slave.
                6.loadbackupobjectserviceboard(6)    -Load the object of service board.
                7.loadbackupobjectservicesubboard(7) -Load the object of service subboard.
                8.loadbackupobjectserviceport(8)     -Load the object of service port.
                9.loadbackupobjectframeboard(9)      -Load the object of frame board.
                10.loadbackupobjectemmboard(10)      -Load the object of emm board.
                11.loadbackupobjectbackboard(11)     -Load the object of back board.
                12.loadbackupobjectsystem(12)        -Load the object of system.
                "
            ::= { hwLoadBackupTrapsVbOids 4 }

        hwBackupContentLocation OBJECT-TYPE
            SYNTAX OCTET STRING (SIZE (0..64))
            MAX-ACCESS accessible-for-notify
            STATUS current
            DESCRIPTION
                "
                Backup content location, main board or standby board.
                "
            ::= { hwLoadBackupTrapsVbOids 5 }

        hwBackupFileLength  OBJECT-TYPE
            SYNTAX  Integer32
            MAX-ACCESS accessible-for-notify
            STATUS current
            DESCRIPTION
                "
                The length of backup file.
                "
            ::= { hwLoadBackupTrapsVbOids 6 }

        hwNewFileDataType OBJECT-TYPE
            SYNTAX INTEGER
                {
                lastword(1),
                cdr(2),
                database(3),
                configurationfile(4),
                alarm(5),
                log(6),
                program(7),
                trace(8)
                }
            MAX-ACCESS accessible-for-notify
            STATUS current
            DESCRIPTION
                "
                The data type of a file.
                Options:
                1.lastword(1)          -indicates that the backup file type is last word.
                2.cdr(2)               -indicates that the backup file type is multicast CDR file.
                3.database(3)          -indicates that the backup file type is database file.
                4.configurationfile(4) -indicates that the backup file type is configuration file.
                5.alarm(5)             -indicates that the backup file type is alarm file.
                6.log(6)               -indicates that the backup file type is log file.
                7.program(7)           -indicates that the automatic loading file type is program.
                8.trace(8)             -indicates that the backup file type is running log file.
                "
            ::= { hwLoadBackupTrapsVbOids 7 }

        hwAutoBackupResult  OBJECT-TYPE
            SYNTAX  Integer32
            MAX-ACCESS accessible-for-notify
            STATUS current
            DESCRIPTION
                "
                AutoBackup result.
                0. -indicates that the backup is successful.
                1. -indicates that the backup fails.
                2. -indicates that the server is not configured.
                3. -indicates that the loading(backuping,rollbacking,duplicating,...)command being executed.
                4. -indicates that the username or password is wrong.
                5. -indicates that the file transmission error.
                6. -indicates that the uploaded file is 0 in size.
                7. -indicates that the type of data has been backed up.
                8. -indicates that the loading (backup, rollback, duplication...) command is being run when the data is backed up automatically.
                "
            ::= { hwLoadBackupTrapsVbOids 8 }

        hwSaveResult OBJECT-TYPE
            SYNTAX INTEGER
            {
                succeeded(0),
                failed(1)
            }
            MAX-ACCESS accessible-for-notify
            STATUS current
            DESCRIPTION
                "
                The result of save.
                Options:
                1. succeeded(0)     -indicates that the operation is successful.
                2. failed(1)        -indicates that the operation fails.
                "
            ::= { hwLoadBackupTrapsVbOids 9 }



hwLoadBackupTraps        OBJECT IDENTIFIER ::= { hwLoadBackup  8 }

--Common traps
        hwLoadBackupCommonTraps      OBJECT IDENTIFIER ::= { hwLoadBackupTraps  1 }
        hwLoadBackupCommonTrapsPrefix OBJECT IDENTIFIER ::= { hwLoadBackupCommonTraps 0 }


        hwNoNeedSaveTrap   NOTIFICATION-TYPE
            OBJECTS
            {
                hwFrameIndex,
                hwSlotIndex
            }
            STATUS current
            DESCRIPTION
                "
                There is no need to save the database.
                After the database is saved, this trap message is reported when the database is saved again
                while no change is made on the database.
                "
            ::= { hwLoadBackupCommonTrapsPrefix 1 }

        hwBackupGuageTrap   NOTIFICATION-TYPE
            OBJECTS
            {
                hwFrameIndex,
                hwSlotIndex,
                hwLoadBackupGuage
            }
            STATUS obsolete
            DESCRIPTION
                "
                This trap message is reported when a backup operation starts and it tells us the guage of backup.
                "
        ::= { hwLoadBackupCommonTrapsPrefix 2 }

        hwNoRollBackStartTrap   NOTIFICATION-TYPE
            OBJECTS
            {
                hwFrameIndex,
                hwSlotIndex
            }
            STATUS current
            DESCRIPTION
                "
                This trap message is reported when duplicating files starts from the master area
                to the slave area in the board.
                "
        ::= { hwLoadBackupCommonTrapsPrefix 3 }

        hwNoRollBackResultTrap   NOTIFICATION-TYPE
            OBJECTS
            {
                hwFrameIndex,
                hwSlotIndex,
                hwRollResult
            }
            STATUS current
            DESCRIPTION
                "
                This trap message is reported when the duplication of a file from the active area to the
                standby area is complete.
                "
        ::= { hwLoadBackupCommonTrapsPrefix 4 }

        hwSaveStartTrap   NOTIFICATION-TYPE
            STATUS current
            DESCRIPTION
                "
                This trap message is reported when the data saving starts.
                "
            ::= { hwLoadBackupCommonTrapsPrefix 5 }

        hwLoadTransferFileTrap   NOTIFICATION-TYPE
        STATUS current
        DESCRIPTION
            "
            This trap message is reported when the file transfer during loading is complete.
            "
        ::= { hwLoadBackupCommonTrapsPrefix 6 }

        hwSaveCompleteTrap   NOTIFICATION-TYPE
            OBJECTS { hwSaveResult}
            STATUS current
            DESCRIPTION
                "
                This trap message is reported when the data saving is complete.
                "
            ::= { hwLoadBackupCommonTrapsPrefix 7 }


--Alarm traps

        hwLoadBackupAlarmTraps        OBJECT IDENTIFIER ::= { hwLoadBackupTraps  2 }

        hwLoadBackupAlarmTrapsPrefix OBJECT IDENTIFIER ::= { hwLoadBackupAlarmTraps 0 }

        hwDuplicatingFileStartTrap   NOTIFICATION-TYPE
            OBJECTS
            {
                hwFrameIndex,
                hwSlotIndex
            }
            STATUS current
            DESCRIPTION
                "
                This trap message is reported when duplicating files starts from the master area
                to the slave area in the board.
                "
            ::= { hwLoadBackupAlarmTrapsPrefix 1 }

        hwDuplicatingFileSuccessTrap NOTIFICATION-TYPE
            OBJECTS
            {
                hwFrameIndex,
                hwSlotIndex
            }
            STATUS current
            DESCRIPTION
                "
                This trap message is reported when duplicating files succeeded from the master area
                to the slave area in the board.
                "
        ::= { hwLoadBackupAlarmTrapsPrefix 2 }

        hwDuplicatingFileFailTrap NOTIFICATION-TYPE
            OBJECTS
            {
                hwFrameIndex,
                hwSlotIndex
            }
            STATUS current
            DESCRIPTION
                "
                This trap message is reported when duplicating files failed from the master area
                to the slave area in the board.
                "
            ::= { hwLoadBackupAlarmTrapsPrefix 3 }

        hwLoadStartTrap NOTIFICATION-TYPE
            OBJECTS
            {
                hwFrameIndex,
                hwSlotIndex,
                hwLoadPositionPara,
                hwLoadContent,
                hwLoadBackObject
            }
            STATUS current
            DESCRIPTION
                "
                This trap message is reported when the loading operation starts.
                "
            ::= { hwLoadBackupAlarmTrapsPrefix 4 }

        hwLoadSuccessTrap   NOTIFICATION-TYPE
            OBJECTS
            {
                hwFrameIndex,
                hwSlotIndex,
                hwLoadPositionPara,
                hwLoadContent,
                hwLoadBackObject
            }
            STATUS current
            DESCRIPTION
                "
                This trap message is reported when the loading is successful.
                "
            ::= { hwLoadBackupAlarmTrapsPrefix 5 }

        hwLoadFailTrap NOTIFICATION-TYPE
            OBJECTS
            {
                hwFrameIndex,
                hwSlotIndex,
                hwLoadPositionPara,
                hwLoadContent,
                hwLoadBackObject,
                hwLoadBackupResult
            }
            STATUS current
            DESCRIPTION
                "
                This trap message is reported when the loading fails.
                "
            ::= { hwLoadBackupAlarmTrapsPrefix 6 }

        hwBackupStartTrap NOTIFICATION-TYPE
            OBJECTS
            {
                hwFrameIndex,
                hwSlotIndex,
                hwBackupPositionPara,
                hwBackupContent,
                hwLoadBackObject
            }
            STATUS current
            DESCRIPTION
                "
                This trap message is reported when the backup starts.
                "
            ::= { hwLoadBackupAlarmTrapsPrefix 7 }

        hwBackupSuccessTrap NOTIFICATION-TYPE
            OBJECTS
            {
                hwFrameIndex,
                hwSlotIndex,
                hwBackupPositionPara,
                hwBackupContent,
                hwLoadBackObject
            }
            STATUS current
            DESCRIPTION
                "
                This trap message is reported when the backup is successful.
                "
            ::= { hwLoadBackupAlarmTrapsPrefix 8 }

        hwBackupFailTrap NOTIFICATION-TYPE
            OBJECTS
            {
                hwFrameIndex,
                hwSlotIndex,
                hwBackupPositionPara,
                hwBackupContent,
                hwLoadBackObject,
                hwLoadBackupResult
            }
            STATUS current
            DESCRIPTION
                "
                This trap message is reported when the backup fails.
                "
            ::= { hwLoadBackupAlarmTrapsPrefix 9 }


        hwAutoBackupFailTrap NOTIFICATION-TYPE
            OBJECTS
            {
                hwNewFileDataType,
                hwBackupContentLocation,
                hwAutoBackupResult
            }
            STATUS current
            DESCRIPTION
                "
                This trap message is reported when the automatic backup fails.
                "
            ::= { hwLoadBackupAlarmTrapsPrefix 10 }


        --1.3.6.1.4.1.2011.6.8.2.0.11
        hwAutoLoadStartTrap NOTIFICATION-TYPE
            OBJECTS
            {
                hwFrameIndex,
                hwSlotIndex,
                hwLoadPositionPara,
                hwLoadContent,
                hwLoadBackObject
            }
            STATUS current
            DESCRIPTION
                "
                During the start of the board, if the board software version is different from the
                board software version configured in the system, the system upgrades the board program automatically.
                This trap message is reported when the automatic upgrade starts.
                "
            ::= { hwLoadBackupAlarmTrapsPrefix 11 }

        --1.3.6.1.4.1.2011.6.8.2.0.12
        hwAutoLoadCompleteTrap NOTIFICATION-TYPE
            OBJECTS
            {
                hwFrameIndex,
                hwSlotIndex,
                hwLoadPositionPara,
                hwLoadContent,
                hwLoadBackObject
            }
            STATUS current
            DESCRIPTION
                "
                During the start of the board, if the board software version is different from the board software
                version configured in the system, the system upgrades the board program automatically.
                This trap message is reported when the automatic upgrade is complete.
                "
            ::= { hwLoadBackupAlarmTrapsPrefix 12 }

        --1.3.6.1.4.1.2011.6.8.2.0.13
        hwAutoLoadFailTrap NOTIFICATION-TYPE
            OBJECTS
            {
                hwFrameIndex,
                hwSlotIndex,
                hwLoadPositionPara,
                hwLoadContent,
                hwLoadBackObject,
                hwLoadBackupResult
            }
            STATUS current
            DESCRIPTION
                "
                During the start of the board, if the board software version is different from the board software version
                configured in the system, the system upgrades the board program automatically. This trap message is reported
                when the automatic upgrade fails.
                "
            ::= { hwLoadBackupAlarmTrapsPrefix 13 }

        --1.3.6.1.4.1.2011.6.8.2.0.14
        hwAutoBackupSuccessTrap NOTIFICATION-TYPE
            OBJECTS
            {
                hwFrameIndex,
                hwSlotIndex,
                hwNewFileDataType,
                hwBackupFileLength,
                hwBackupServerIpAddr
            }
            STATUS current
            DESCRIPTION
             "
             This trap is reported when a log or an alarm is automatically uploaded successfully.
             "
            ::= { hwLoadBackupAlarmTrapsPrefix 14 }

           --1.3.6.1.4.1.2011.6.8.2.0.15
        hwLoadInStandbyChannelTrap NOTIFICATION-TYPE
            OBJECTS
            {
                hwFrameIndex,
                hwSlotIndex,
                hwLoadPositionPara,
                hwLoadContent,
                hwLoadBackObject
            }
            STATUS current
            DESCRIPTION
             "
             This trap is reported the main channel of loading is invalid, load in standby channel.
             "
            ::= { hwLoadBackupAlarmTrapsPrefix 15 }
            
        --1.3.6.1.4.1.2011.6.8.2.0.16
        hwAutoLoadBoardStartTrap NOTIFICATION-TYPE
            OBJECTS
            {
                hwFrameIndex,
                hwSlotIndex,
                hwLoadBoardType,
                hwLoadContent
            }
            STATUS current
            DESCRIPTION
             "
             During the start of the board, if the board software version is different from the
             board software version configured in the system, the system upgrades the board program automatically.
             This trap message is reported when the automatic upgrade starts.
             "
            ::= { hwLoadBackupAlarmTrapsPrefix 16 }
            
        --1.3.6.1.4.1.2011.6.8.2.0.17
        hwAutoLoadBoardCompleteTrap NOTIFICATION-TYPE
            OBJECTS
            {
                hwFrameIndex,
                hwSlotIndex,
                hwLoadBoardType,
                hwLoadContent
            }
            STATUS current
            DESCRIPTION
             "
             During the start of the board, if the board software version is different from the board software
             version configured in the system, the system upgrades the board program automatically.
             This trap message is reported when the automatic upgrade is complete.
             "
            ::= { hwLoadBackupAlarmTrapsPrefix 17 }
            
        --1.3.6.1.4.1.2011.6.8.2.0.18
        hwAutoLoadBoardFailTrap NOTIFICATION-TYPE
            OBJECTS
            {
                hwFrameIndex,
                hwSlotIndex,
                hwLoadBoardType,
                hwLoadContent
            }
            STATUS current
            DESCRIPTION
             "
             During the start of the board, if the board software version is different from the board software version
             configured in the system, the system upgrades the board program automatically. This trap message is reported
             when the automatic upgrade fails.
             "
            ::= { hwLoadBackupAlarmTrapsPrefix 18 }

       hwProgramAndDataInfoTable OBJECT-TYPE
            SYNTAX SEQUENCE OF HwProgramAndDataInfoEntry
            MAX-ACCESS not-accessible
            STATUS current
            DESCRIPTION
             "
             Program and data information table. Through this table,
             you can query the status and version of program and data in active board or standby board .
             The index of this table is hwMainboardID.
             hwMainboardID is an mainboard ID.
             "
            ::= { hwLoadBackup 9 }

        hwProgramAndDataInfoEntry OBJECT-TYPE
            SYNTAX HwProgramAndDataInfoEntry
            MAX-ACCESS not-accessible
            STATUS current
            DESCRIPTION
             "
             Program and data information table. Through this table,
             you can query the status and version of program and data in active board or standby board .
             The index of this entry is hwMainboardID.
             hwMainboardID is an mainboard ID.
             "
            INDEX { hwMainboardID }
            ::= { hwProgramAndDataInfoTable 1 }

       HwProgramAndDataInfoEntry ::=
            SEQUENCE
            {
                hwMainboardID
                    INTEGER,
                hwProagramActiveArea
                     INTEGER,
                hwDataActiveArea
                     INTEGER,
                hwProagramAreaAVersion
                     OCTET STRING,
                hwProagramAreaBVersion
                     OCTET STRING,
                hwDataAreaAVersion
                     OCTET STRING,
                hwDataAreaBVersion
                     OCTET STRING
            }

        hwMainboardID OBJECT-TYPE
            SYNTAX INTEGER
                {
                 active(1),
                 standby(2)
                }
            MAX-ACCESS not-accessible
            STATUS current
            DESCRIPTION
                "
                Operation type.
                Options:
                1.active(1)      -indicates the active board.
                2.standby(2)     -indicates the standby board.
                "
            ::= { hwProgramAndDataInfoEntry 1 }
        hwProagramActiveArea OBJECT-TYPE
            SYNTAX INTEGER
                {
                 areaA(1),
                 areaB(2)
                }
            MAX-ACCESS read-only
            STATUS current
            DESCRIPTION
                "
                Current infomation of the board program running.
                Options:
                1.areaA(1)     -indicates that the program is running on area A.
                2.areaB(2)     -indicates that the program is running on area B.
                "
            ::= { hwProgramAndDataInfoEntry 2 }

        hwDataActiveArea OBJECT-TYPE
            SYNTAX INTEGER
                {
                 areaA(1),
                 areaB(2)
                }
            MAX-ACCESS read-only
            STATUS current
            DESCRIPTION
                "
                Current infomation of the board data running.
                Options:
                1.areaA(1)     -indicates that the data is running on area A.
                2.areaB(2)     -indicates that the data is running on area B.
                "
            ::= { hwProgramAndDataInfoEntry 3 }

        hwProagramAreaAVersion OBJECT-TYPE
            SYNTAX OCTET STRING (SIZE (0..32))
            MAX-ACCESS read-only
            STATUS current
            DESCRIPTION
                "
                Current version of the program area A.
                "
            ::= { hwProgramAndDataInfoEntry 4 }

        hwProagramAreaBVersion OBJECT-TYPE
            SYNTAX OCTET STRING (SIZE (0..32))
            MAX-ACCESS read-only
            STATUS current
            DESCRIPTION
                "
                Current version of the program area B.
                "
            ::= { hwProgramAndDataInfoEntry 5 }

        hwDataAreaAVersion OBJECT-TYPE
            SYNTAX OCTET STRING (SIZE (0..32))
            MAX-ACCESS read-only
            STATUS current
            DESCRIPTION
                "
                Current version of the data area A.
                "
            ::= { hwProgramAndDataInfoEntry 6 }

        hwDataAreaBVersion OBJECT-TYPE
            SYNTAX OCTET STRING (SIZE (0..32))
            MAX-ACCESS read-only
            STATUS current
            DESCRIPTION
                "
                Current version of the data area B.
                "
            ::= { hwProgramAndDataInfoEntry 7 }

    END
