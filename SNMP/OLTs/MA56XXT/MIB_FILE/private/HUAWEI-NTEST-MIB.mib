-- ============================================================================
-- Copyright (C) 2014 by  HUAWEI TECHNOLOGIES. All rights reserved.
-- Description: This mib is used for defining the voip test MIB objects.
-- Reference:  
-- Version: V3.26
-- ============================================================================
HUAWEI-NTEST-MIB DEFINITIONS ::= BEGIN
IMPORTS
        MODULE-IDENTITY, OBJECT-TYPE, NOTIFICATION-TYPE
            FROM SNMPv2-SMI
        huaweiUtility
            FROM HUAWEI-MIB
        ifIndex
            FROM IF-MIB
        hwFrameIndex
            FROM HUAWEI-DEVICE-MIB
        hwTestGroupNo
            FROM HUAWEI-COMMTEST-MIB
        RowStatus
            FROM SNMPv2-TC
        Integer32
            FROM SNMPv2-SMI 
        Unsigned32
            FROM SNMPv2-SMI             
        IpAddress
            FROM SNMPv2-SMI 
;

hwTest OBJECT IDENTIFIER ::= { huaweiUtility 21 }

hwNTest MODULE-IDENTITY
        LAST-UPDATED "201406041040Z"
        ORGANIZATION "Huawei Technologies Co.,Ltd."
        CONTACT-INFO                                    
                     "Huawei Industrial Base            
                      Bantian, Longgang                 
                      Shenzhen 518129                   
                      People's Republic of China        
                      Website: http://www.huawei.com    
                      Email: support@huawei.com         
                     "                                  
        DESCRIPTION "This mib is used for defining the voip test MIB objects."

--  Revision history  
        REVISION     "201406041040Z"            
        DESCRIPTION  "V3.26, Modified the syntax for OMSYS"
                     
        REVISION     "201109010000Z"            
        DESCRIPTION  "V3.25, change in this revision:
                     - Added the following leaf into hwPstnCallerEmulateOprTable:
                        hwPstnCallerEmulateTestFailReason 
                        
                     - Added the following leaf into hwPstnCalledEmulateOprTable:
                        hwPstnCalledEmulateTestFailReason
        
                     - Added the following leaves into hwPstnCallEmulateOprTable:
                        hwPstnCallEmulateTestCallerFailReason
                        hwPstnCallEmulateTestCalledFailReason
                     "
                     
        REVISION     "201105042000Z"              
        DESCRIPTION  "V3.24, change in this revision:  
                      - Added the following leaf into hwPstnSignalToneTestOprTable
                         hwPstnSignalToneTestDTStop
                      
                      - Added the following trap node into hwPstnSignalToneTestOperatorTrap:
                         hwPstnSignalToneTestDTStop  
                      
                      - Added the following enum into leaf hwPstnSignalToneTestMode:     
                        invalidValue(-1)   
                      
                      - Modified the description of the following enums of leaf hwPstnSignalToneTestOprType:    
                        invalidValue(-1) 
                       
                      - Modified the value range of the following leaves,including:
                        hwPstnSignalToneActualDeferTime
                        hwPotsSelfCircuitTestDeferredTime
                      
                      - Modified the max access of the following leaf,including:
                        hwFrameLooplineAdjustBusyFlag
                      "

        REVISION     "201102152000Z"              
        DESCRIPTION  "V3.23, change in this revision:
                     - Added the following leaves into hwPotsSelfCircuitTestOprTable
                        hwPotsSelfCircuitTestOnHookDetectResult 
                        hwPotsSelfCircuitTestOffHookDetectResult
                        hwPotsSelfCircuitTestStopRingResult     
                        hwPotsSelfCircuitTestVPoleResult        
                        hwPotsSelfCircuitTestVBATLValue         
                        hwPotsSelfCircuitTestVBATHValue         
                        hwPotsSelfCircuitTestVBATRValue         
                        hwPotsSelfCircuitTestRingFValue         
                        hwPotsSelfCircuitTestVAGValue           
                        hwPotsSelfCircuitTestVBGValue           
                        hwPotsSelfCircuitTestVABPoleValue       
                        hwPotsSelfCircuitTestABLCurrentValue    
                        hwPotsSelfCircuitTestSLICTempValue

                     - Modified the following leaves in hwPotsSelfCircuitTestOprTable: 
                        hwPotsSelfCircuitTestVDDResult
                        hwPotsSelfCircuitTestVBATLResult
                        hwPotsSelfCircuitTestVBATHResult
                        hwPotsSelfCircuitTestVBATRResult
                        hwPotsSelfCircuitTestLoopCurrentResult
                        hwPotsSelfCircuitTestFeedVResult
                        hwPotsSelfCircuitTestRingVResult
                        hwPotsSelfCircuitTestRingFResult
                        hwPotsSelfCircuitTestVAGResult
                        hwPotsSelfCircuitTestVBGResult 
                        hwPotsSelfCircuitTestFeedVValue   
                        hwPotsSelfCircuitTestRingVValue  
                        hwPotsSelfCircuitTestLoopCurrentValue

                     - Added the following leaves into hwPstnSignalToneTestOprTable:
                        hwPstnSignalToneTestMode 
                        hwPstnSignalToneTestRequestID   
                        
                     - Added the following enums into leaf hwPstnSignalToneTestOprType:     
                        ringbacktone(5)     
                        busytone(6)
                        
                     - Modified the description of the following enums of leaf hwPstnSignalToneTestOprType:    
                        invalidValue(-1) 
                     
                     - Modified the description of the following enums of leaf hwPstnSignalToneTestBusyFlag:
                        invalidValue(-1) 
                     
                     - Modified the value range of the leaves,including:
                        hwPstnSignalToneTestDTDelayTime
                        hwPstnSignalTonePlayTime   
                     
                     - Added the following leaf into hwFrameLooplineAdjustOprTable:
                        hwFrameLooplineAdjustBusyFlag   
                        
                     - Modified the note of the table hwPotsLooplineThresholdTable
                     
                     - Modified the following leaves in the hwPotsLooplineThresholdTable:
                        hwTouchThePowerVolThreshold  
                        hwLoopLineMixedVolThreshold  
                        hwOffHookLoopMaxThreshold

                     - Added the following leaves into hwPotsLooplineThresholdTable:
                        hwLoopParamsCab
                        hwLoopParamsCagbg
                        hwLoopParamsRab        
                        hwLrcThMaxsc   
                        hwLrcThMaxLg 
                        hwHdcvL 
                        hwFacvL 
                        hwMinetsiSc   
                        hwMaxetsiSc 
                        hwMinetsiPr   
                        hwMaxetsiPr
                        hwMinZenerZv 
                        hwMaxRcrTr  
                        hwMinRcrTr 
                        hwCpeCab  
                        hwMinhrTr 
                        hwFvcLim
                        hwMinOffhookR 
                        hwLepPar  
                        hwLooplineThresholdOprType    

                     - Modified the definition of the trap node,including:
                        hwPstnSignalToneTestOperatorTrap                    
                        hwPotsSelfCircuitTestTrap   
                        
                     - Added the following leaves into hwPstnCallerEmulateOprTable:
                        hwPstnCallerEmulateTestRequestID 
                        
                     - Added the following leaves into hwPstnCalledEmulateOprTable:
                        hwPstnCalledEmulateTestRequestID
                        
                     - Added the following trap node into hwPstnCallerEmulateOperatorTrap:
                        hwPstnCallerEmulateTestRequestID
                        hwPstnCallerEmulateTestResult
                        ifIndex      
                        
                     - Added the following trap node into hwPstnCalledEmulateOperatorTrap:
                        hwPstnCalledEmulateTestRequestID
                        hwPstnCalledEmulateTestResult
                        ifIndex  
                        
                     - Added the following trap node into hwPstnCallEmulateOperatorTrap:
                        hwPstnCallEmulateTestResult
                             
                     - Created tables, include:
                        hwLineTestParaTable
                        hwMonitorTestOprTable  
                     "

        REVISION     "201012061240Z"            
        DESCRIPTION  "V3.22, change in this revision:
                     -Modified the definition of the leaves,including:
                     hwPstnSignalTonePlayTime
                     hwPstnSignalToneActualDeferTime
                     "

        REVISION     "201011172040Z"            
        DESCRIPTION  "V3.21, change in this revision:
                     -Modified the description
                     "
                     
        REVISION     "201008200000Z"            
        DESCRIPTION  "V3.20, change in this revision:
                     - Modified the description of all tables 
                     "

        REVISION     "201008200000Z"            
        DESCRIPTION  "V3.19, change in this revision:
                     - Modified the definition of the leaves,including:
                     hwPstnCallerEmulateTestStatus
                     hwPstnCalledEmulateTestStatus
                     "
                     
        REVISION     "201008100000Z"        
        DESCRIPTION  "V3.18, change in this revision:
                     - Modified the definition of the leaves,including:
                     hwPstnCallEmulateTestSendDTMFPeriod
                     hhwPstnCallEmulateTestSendDTMFList
                     "
                     
        REVISION     "201007300000Z"        
        DESCRIPTION  "V3.17, change in this revision:
                     - Created tables, include:
                     hwPstnCallEmulateConfigTable
                     hwPstnCalledEmulateOprTable
                     hwPstnCallEmulateOprTable 
                     "

        REVISION     "201007230000Z"        
        DESCRIPTION  "V3.16, change in this revision:
                     - Modified the description of all tables 
                     "

        REVISION    "201003240000Z"
        DESCRIPTION "V3.15, change in this revision:
                     - Corrected the SYNTAX
                     - Modified the definition of the trap node,including:
                        hw112IsdnDiagnoseTrap    
                        hw112IsdnDiagnoseTrap     
                        hwPotsSelfCircuitTestTrap
                        hwPstnCallEmulateOperatorTrap
                    
                     - Added the definition of the trap node,include:
                        hwISDNDiagnoseTestTrap
                        hwPstnLoopTestTrap   
                          
                     - Added the following leaves into hw112IsdnDiagnoseTestOprTable:
                        hw112IsdnDiagnoseTestIfIndex   
                        hw112IsdnDiagnoseTestRequestID
                        
                     - Added the following leaves into hwFrameLooplineAdjustOprTable:
                        hwFrameLooplineAdjustFrameIndex   
                        hwFrameLooplineAdjustRequestID

                     - Added the following leaves into hwPotsSelfCircuitTestOprTable:
                        hwPotsSelfCircuitTestLoopIfIndex   
                        hwPotsSelfCircuitTestLoopRequestID

                     - Added the following leaves into hwISDNDiagnoseTestTable:
                        hwISDNDiagnoseTestRequestID   

                     - Added the following leaves into hwPstnCallEmulateOprTable:
                        hwPstnCallEmulateTestRequestID
        
                     - Added the following leaves into hwPstnLoopTestOprTable:
                        hwPstnLoopTestRequestID
                    "
                    
        ::= { hwTest 2 }

hwNTestMib OBJECT IDENTIFIER ::= { hwNTest 1 }

hwNTestMIBObjects OBJECT IDENTIFIER ::= { hwNTestMib 1 }

hwNTestTraps OBJECT IDENTIFIER ::= { hwNTest 2 }

hwNTestTrapVbOids OBJECT IDENTIFIER ::= { hwNTestTraps 1 }

hwNTestVbOidsReason OBJECT IDENTIFIER ::= { hwNTestTrapVbOids 2 }

hwNTestGeneralTraps OBJECT IDENTIFIER ::= { hwNTestTraps 3 }
hwNTestGeneralTrapsOIDs OBJECT IDENTIFIER ::= { hwNTestGeneralTraps 0 }


  hwPstnCircuitTestOprTable OBJECT-TYPE
    SYNTAX      SEQUENCE OF HwPstnCircuitTestOprEntry
    MAX-ACCESS  not-accessible
    STATUS      current
    DESCRIPTION
      "Operation table for the PSTN subscriber circuit test:
      It realizes the function of the circuit test for analog subscribers in the system. The circuit test helps you to ensure that the service board can provide the functions such as ringing, feeder, and dial tone. The circuit test also helps you to ensure that the parameters such as the feeder voltage and ringing current voltage are normal.
      This function facilitates the maintenance of the subscriber circuits, especially the internal circuits of the service boards.
      The index of this table is ifIndex."
    ::= { hwNTestMIBObjects 1 }

  hwPstnCircuitTestOprEntry OBJECT-TYPE
    SYNTAX      HwPstnCircuitTestOprEntry
    MAX-ACCESS  not-accessible
    STATUS      current
    DESCRIPTION
      "Operation table for the PSTN subscriber circuit test:
      It realizes the function of the circuit test for analog subscribers in the system. The circuit test helps you to ensure that the service board can provide the functions such as ringing, feeder, and dial tone. The circuit test also helps you to ensure that the parameters such as the feeder voltage and ringing current voltage are normal.
      This function facilitates the maintenance of the subscriber circuits, especially the internal circuits of the service boards.
      The index of this entry is ifIndex."
    INDEX    {  
              ifIndex
             }
    ::= { hwPstnCircuitTestOprTable 1 }

  HwPstnCircuitTestOprEntry ::=
    SEQUENCE
    {
    hwPstnCircuitTestOprType          INTEGER,
    hwPstnCircuitTestOffHook          INTEGER,
    hwPstnCircuitTestOffHookCount     Integer32,
    hwPstnCircuitTestDialTone         INTEGER,
    hwPstnCircuitTestReceivePulse     INTEGER,
    hwPstnCircuitTestReceiveDTMF      INTEGER,
    hwPstnCircuitTestRingBackTone     INTEGER,
    hwPstnCircuitTestBusyTone         INTEGER,
    hwPstnCircuitTestBatteryFeed      INTEGER,
    hwPstnCircuitTestPoleDetect       INTEGER,
    hwPstnCircuitTestOnHook           INTEGER,
    hwPstnCircuitTestRing             INTEGER,
    hwPstnCircuitTestStopRing         INTEGER,
    hwPstnCircuitTestFeedV            INTEGER,
    hwPstnCircuitTestRingV            INTEGER,
    hwPstnCircuitTestBusyProcFlag     INTEGER,
    hwPstnCircuitTestStatus           INTEGER,
    hwPstnCircuitTestOffHookResult    INTEGER,
    hwPstnCircuitTestDialToneResult   INTEGER,
    hwPstnCircuitTestReceivePulseResult       INTEGER,
    hwPstnCircuitTestReceiveDTMFResult        INTEGER,
    hwPstnCircuitTestRingBackResult           INTEGER,
    hwPstnCircuitTestBusyToneResult           INTEGER,
    hwPstnCircuitTestBatteryFeedResult        INTEGER,
    hwPstnCircuitTestPoleDetectResult         INTEGER,
    hwPstnCircuitTestOnHookResult             INTEGER,
    hwPstnCircuitTestRingResult               INTEGER,
    hwPstnCircuitTestStopRingResult           INTEGER,
    hwPstnCircuitTestFeedVValue               Integer32,
    hwPstnCircuitTestFeedVResult              INTEGER,
    hwPstnCircuitTestRingVValue               Integer32,
    hwPstnCircuitTestRingVResult              INTEGER,
    hwPstnCircuitTestLoopCurrentValue         Integer32,
    hwPstnCircuitTestLoopCurrentResult        INTEGER
    }

  hwPstnCircuitTestOprType OBJECT-TYPE
    SYNTAX      INTEGER{stop(1),start(2)}
    MAX-ACCESS  read-create
    STATUS      current
    DESCRIPTION
        "Describes the Circuit test-Operation Type.
         Options: 
            1. stop(1)  -stop the test
            2. start(2) -start the test 
        "
    ::= { hwPstnCircuitTestOprEntry 1 }

  hwPstnCircuitTestOffHook OBJECT-TYPE
    SYNTAX      INTEGER{notest(1),test(2)}
    MAX-ACCESS  read-create
    STATUS      current
    DESCRIPTION
        "Describes the Circuit test-Off hook.
         Options: 
            1. notest(1) -no test is applied
            2. test(2)   -a test is applied   
        "
    ::= { hwPstnCircuitTestOprEntry 2 }

  hwPstnCircuitTestOffHookCount OBJECT-TYPE
    SYNTAX      Integer32(1..255)
    MAX-ACCESS  read-create
    STATUS      current
    DESCRIPTION
        "Circuit test-Off hook count"
    ::= { hwPstnCircuitTestOprEntry 3 }

  hwPstnCircuitTestDialTone OBJECT-TYPE
    SYNTAX      INTEGER{notest(1),test(2)}
    MAX-ACCESS  read-create
    STATUS      current
    DESCRIPTION
        "Describes the Circuit test-Dial tone.
         Options: 
            1. notest(1) -no test is applied
            2. test(2)   -a test is applied  
        "
    ::= { hwPstnCircuitTestOprEntry 4 }

  hwPstnCircuitTestReceivePulse OBJECT-TYPE
    SYNTAX      INTEGER{notest(1),test(2)}
    MAX-ACCESS  read-create
    STATUS      current
    DESCRIPTION
        "Describes the Circuit test-Receiving pulse.
         Options: 
            1. notest(1) -no test is applied
            2. test(2)   -a test is applied 
        "
    ::= { hwPstnCircuitTestOprEntry 5 }

  hwPstnCircuitTestReceiveDTMF OBJECT-TYPE
    SYNTAX      INTEGER{notest(1),test(2)}
    MAX-ACCESS  read-create
    STATUS      current
    DESCRIPTION
        "Describes the Circuit test-Receiving DTMF.
         Options: 
            1. notest(1) -no test is applied
            2. test(2)   -a test is applied 
        "
    ::= { hwPstnCircuitTestOprEntry 6 }

  hwPstnCircuitTestRingBackTone OBJECT-TYPE
    SYNTAX      INTEGER{notest(1),test(2)}
    MAX-ACCESS  read-create
    STATUS      current
    DESCRIPTION
        "Describes the Circuit test-Ring back tone.
         Options: 
            1. notest(1) -no test is applied
            2. test(2)   -a test is applied 
        "
    ::= { hwPstnCircuitTestOprEntry 7 }

  hwPstnCircuitTestBusyTone OBJECT-TYPE
    SYNTAX      INTEGER{notest(1),test(2)}
    MAX-ACCESS  read-create
    STATUS      current
    DESCRIPTION
        "Describes the Circuit test-Busy tone.
         Options: 
            1. notest(1) -no test is applied
            2. test(2)   -a test is applied 
        "
    ::= { hwPstnCircuitTestOprEntry 8 }

  hwPstnCircuitTestBatteryFeed OBJECT-TYPE
    SYNTAX      INTEGER{notest(1),test(2)}
    MAX-ACCESS  read-create
    STATUS      current
    DESCRIPTION
        "Describes the Circuit test-Feeder .
         Options: 
            1. notest(1) -no test is applied
            2. test(2)   -a test is applied 
        "
    ::= { hwPstnCircuitTestOprEntry 9 }

  hwPstnCircuitTestPoleDetect OBJECT-TYPE
    SYNTAX      INTEGER{notest(1),test(2)}
    MAX-ACCESS  read-create
    STATUS      current
    DESCRIPTION
        "Describes the Circuit test-Polarity reversal. 
         Options: 
            1. notest(1) -no test is applied
            2. test(2)   -a test is applied 
        "
    ::= { hwPstnCircuitTestOprEntry 10 }

  hwPstnCircuitTestOnHook OBJECT-TYPE
    SYNTAX      INTEGER{notest(1),test(2)}
    MAX-ACCESS  read-create
    STATUS      current
    DESCRIPTION
        "Describes the Circuit test-On hook.
         Options: 
            1. notest(1) -no test is applied
            2. test(2)   -a test is applied 
        "
    ::= { hwPstnCircuitTestOprEntry 11 }

  hwPstnCircuitTestRing OBJECT-TYPE
    SYNTAX      INTEGER{notest(1),test(2)}
    MAX-ACCESS  read-create
    STATUS      current
    DESCRIPTION
        "Describes the Circuit test-Ringing.
         Options: 
            1. notest(1) -no test is applied
            2. test(2)   -a test is applied 
        "
    ::= { hwPstnCircuitTestOprEntry 12 }

  hwPstnCircuitTestStopRing OBJECT-TYPE
    SYNTAX      INTEGER{notest(1),test(2)}
    MAX-ACCESS  read-create
    STATUS      current
    DESCRIPTION
        "Describes the Circuit test-Stop ringing.
         Options: 
            1. notest(1) -no test is applied
            2. test(2)   -a test is applied 
        "
    ::= { hwPstnCircuitTestOprEntry 13 }

  hwPstnCircuitTestFeedV OBJECT-TYPE
    SYNTAX      INTEGER{notest(1),test(2)}
    MAX-ACCESS  read-create
    STATUS      current
    DESCRIPTION
        "Describes the Circuit test-Feeder voltage.
         Options: 
            1. notest(1) -no test is applied
            2. test(2)   -a test is applied 
        "
    ::= { hwPstnCircuitTestOprEntry 14 }

  hwPstnCircuitTestRingV OBJECT-TYPE
    SYNTAX      INTEGER{notest(1),test(2)}
    MAX-ACCESS  read-create
    STATUS      current
    DESCRIPTION
        "Describes the Circuit test-Ringing current voltage.
         Options: 
            1. notest(1) -no test is applied
            2. test(2)   -a test is applied 
        "
    ::= { hwPstnCircuitTestOprEntry 15 }

  hwPstnCircuitTestBusyProcFlag OBJECT-TYPE
    SYNTAX      INTEGER{busynotest(1),busytest(2),busystrentest(3)}
    MAX-ACCESS  read-create
    STATUS      current
    DESCRIPTION
        "Describes the Circuit test-Busy control. 
         Options:
            1. busynotest(1)    -indicates no test when busy 
            2. busytest(2)      -indicates remedy test when busy 
            3. busystrentest(3) -indicates forced test on busy
         "
    ::= { hwPstnCircuitTestOprEntry 16 }

  hwPstnCircuitTestStatus OBJECT-TYPE
    SYNTAX      INTEGER{normal(1),testfail(2),portbusy(3),outoftime(4),testingAbnormal(5),broadbandtesting(6),capturefail(7),notratb(8)}
    MAX-ACCESS  read-only
    STATUS      current
    DESCRIPTION
        "Describes the Circuit test-Inline Test Status.
         Options:
            1. normal(1)            -indicates normal 
            2. testfail(2)          -indicates abnormal 
            3. portbusy(3)          -indicates busy port 
            4. outoftime(4)         -indicates timed-out 
            5. testingAbnormal(5)   -indicates test abnormal
            6. broadbandtesting(6)  -indicates broadband testing
            7. capturefail(7)       -indicates line capture failure
            8. notratb(8)           -indicates relay transfer board not exist
            "
    ::= { hwPstnCircuitTestOprEntry 17 }

  hwPstnCircuitTestOffHookResult OBJECT-TYPE
    SYNTAX      INTEGER{normal(1),abnormal(2),testouttime(3),nosupport(4)}
    MAX-ACCESS  read-only
    STATUS      current
    DESCRIPTION
        "Describes the Circuit Test Result-Off hook.
         Options:
            1. normal(1)        -indicates Normal          
            2. abnormal(2)      -indicates Abnormal        
            3. testouttime(3)   -indicates time out          
            4. nosupport(4)     -not support the test    
         "
    ::= { hwPstnCircuitTestOprEntry 18 }

  hwPstnCircuitTestDialToneResult OBJECT-TYPE
    SYNTAX      INTEGER{normal(1),abnormal(2),testouttime(3),nosupport(4)}
    MAX-ACCESS  read-only
    STATUS      current
    DESCRIPTION
        "Describes the Circuit Test Result-dial tone.
         Options:
            1. normal(1)        -indicates Normal          
            2. abnormal(2)      -indicates Abnormal        
            3. testouttime(3)   -indicates time out          
            4. nosupport(4)     -not support the test         
         "
    ::= { hwPstnCircuitTestOprEntry 19 }

  hwPstnCircuitTestReceivePulseResult OBJECT-TYPE
    SYNTAX      INTEGER{normal(1),abnormal(2),testouttime(3),nosupport(4)}
    MAX-ACCESS  read-only
    STATUS      current
    DESCRIPTION
        "Describes the Circuit Test Result-Receiving pulse.
         Options:
            1. normal(1)        -indicates Normal          
            2. abnormal(2)      -indicates Abnormal        
            3. testouttime(3)   -indicates time out          
            4. nosupport(4)     -not support the test          
         "
    ::= { hwPstnCircuitTestOprEntry 20 }

  hwPstnCircuitTestReceiveDTMFResult OBJECT-TYPE
    SYNTAX      INTEGER{normal(1),abnormal(2),testouttime(3),nosupport(4)}
    MAX-ACCESS  read-only
    STATUS      current
    DESCRIPTION
        "Describes the Circuit Test Result-Receiving DTMF.
         Options:
            1. normal(1)        -indicates Normal          
            2. abnormal(2)      -indicates Abnormal        
            3. testouttime(3)   -indicates time out          
            4. nosupport(4)     -not support the test          
         "
    ::= { hwPstnCircuitTestOprEntry 21 }

  hwPstnCircuitTestRingBackResult OBJECT-TYPE
    SYNTAX      INTEGER{normal(1),abnormal(2),testouttime(3),nosupport(4)}
    MAX-ACCESS  read-only
    STATUS      current
    DESCRIPTION
        "Describes the Circuit Test Result-Ring back tone.
         Options:
            1. normal(1)        -indicates Normal          
            2. abnormal(2)      -indicates Abnormal        
            3. testouttime(3)   -indicates time out          
            4. nosupport(4)     -not support the test  
         "
    ::= { hwPstnCircuitTestOprEntry 22 }

  hwPstnCircuitTestBusyToneResult OBJECT-TYPE
    SYNTAX      INTEGER{normal(1),abnormal(2),testouttime(3),nosupport(4)}
    MAX-ACCESS  read-only
    STATUS      current
    DESCRIPTION
        "Describes the Circuit Test Result-Busy tone.
         Options:
            1. normal(1)        -indicates Normal          
            2. abnormal(2)      -indicates Abnormal        
            3. testouttime(3)   -indicates time out          
            4. nosupport(4)     -not support the test  
         "
    ::= { hwPstnCircuitTestOprEntry 23 }

  hwPstnCircuitTestBatteryFeedResult OBJECT-TYPE
    SYNTAX      INTEGER{normal(1),abnormal(2),testouttime(3),nosupport(4)}
    MAX-ACCESS  read-only
    STATUS      current
    DESCRIPTION
        "Describes the Circuit Test Result-Feeder.
         Options:
            1. normal(1)        -indicates Normal          
            2. abnormal(2)      -indicates Abnormal        
            3. testouttime(3)   -indicates time out          
            4. nosupport(4)     -not support the test  
         "
    ::= { hwPstnCircuitTestOprEntry 24 }

  hwPstnCircuitTestPoleDetectResult OBJECT-TYPE
    SYNTAX      INTEGER{normal(1),abnormal(2),testouttime(3),nosupport(4)}
    MAX-ACCESS  read-only
    STATUS      current
    DESCRIPTION
        "Describes the Circuit Test Result-Polarity reversal.
         Options:
            1. normal(1)        -indicates Normal          
            2. abnormal(2)      -indicates Abnormal        
            3. testouttime(3)   -indicates time out          
            4. nosupport(4)     -not support the test  
         "
    ::= { hwPstnCircuitTestOprEntry 25 }

  hwPstnCircuitTestOnHookResult OBJECT-TYPE
    SYNTAX      INTEGER{normal(1),abnormal(2),testouttime(3),nosupport(4)}
    MAX-ACCESS  read-only
    STATUS      current
    DESCRIPTION
        "Describes the Circuit Test Result-On hook.
         Options:
            1. normal(1)        -indicates Normal          
            2. abnormal(2)      -indicates Abnormal        
            3. testouttime(3)   -indicates time out          
            4. nosupport(4)     -not support the test  
         "    
    ::= { hwPstnCircuitTestOprEntry 26 }

  hwPstnCircuitTestRingResult OBJECT-TYPE
    SYNTAX      INTEGER{normal(1),abnormal(2),testouttime(3),nosupport(4)}
    MAX-ACCESS  read-only
    STATUS      current
    DESCRIPTION
        "Describes the Circuit Test Result-Ringing.
         Options:
            1. normal(1)        -indicates Normal          
            2. abnormal(2)      -indicates Abnormal        
            3. testouttime(3)   -indicates time out          
            4. nosupport(4)     -not support the test  
         "    
    ::= { hwPstnCircuitTestOprEntry 27 }

  hwPstnCircuitTestStopRingResult OBJECT-TYPE
    SYNTAX      INTEGER{normal(1),abnormal(2),testouttime(3),nosupport(4)}
    MAX-ACCESS  read-only
    STATUS      current
    DESCRIPTION
        "Describes the Circuit Test Result-Stop ringing.
         Options:
            1. normal(1)        -indicates Normal          
            2. abnormal(2)      -indicates Abnormal        
            3. testouttime(3)   -indicates time out          
            4. nosupport(4)     -not support the test  
         "
    ::= { hwPstnCircuitTestOprEntry 28 }

  hwPstnCircuitTestFeedVValue OBJECT-TYPE
    SYNTAX      Integer32
    MAX-ACCESS  read-only
    STATUS      current
    DESCRIPTION
        "Describes the Circuit Test Result-Feeder voltage."
    ::= { hwPstnCircuitTestOprEntry 29 }

  hwPstnCircuitTestFeedVResult OBJECT-TYPE
    SYNTAX      INTEGER{normal(1),abnormal(2)}
    MAX-ACCESS  read-only
    STATUS      current
    DESCRIPTION
        "Describes the Circuit Test Result-Feeder voltage Result.
         Options:
            1. normal(1)        -indicates Normal          
            2. abnormal(2)      -indicates Abnormal          
        "
    ::= { hwPstnCircuitTestOprEntry 30 }

  hwPstnCircuitTestRingVValue OBJECT-TYPE
    SYNTAX      Integer32
    MAX-ACCESS  read-only
    STATUS      current
    DESCRIPTION
        "Describes the Circuit Test Result-Ringing current voltage.
         Unit: millivolt, ab. mV
        "
    ::= { hwPstnCircuitTestOprEntry 31 }

  hwPstnCircuitTestRingVResult OBJECT-TYPE
    SYNTAX      INTEGER{normal(1),abnormal(2)}
    MAX-ACCESS  read-only
    STATUS      current
    DESCRIPTION
        "Describes the Circuit Test Result-Ringing current voltage Result.
         Options:
            1. normal(1)        -indicates Normal          
            2. abnormal(2)      -indicates Abnormal         
        "
    ::= { hwPstnCircuitTestOprEntry 32 }

  hwPstnCircuitTestLoopCurrentValue OBJECT-TYPE
    SYNTAX      Integer32
    MAX-ACCESS  read-only
    STATUS      current
    DESCRIPTION
        "Describes the Circuit Test Result-Loop current.
         Unit: microampere, ab. uA
        "
    ::= { hwPstnCircuitTestOprEntry 33 }

  hwPstnCircuitTestLoopCurrentResult OBJECT-TYPE
    SYNTAX      INTEGER{normal(1),abnormal(2)}
    MAX-ACCESS  read-only
    STATUS      current
    DESCRIPTION
        "Describes the Circuit Test Result-Loop current Result.
         Options:
            1. normal(1)        -indicates Normal          
            2. abnormal(2)      -indicates Abnormal          
        "
    ::= { hwPstnCircuitTestOprEntry 34 }

  hwIsdnUserInTestOprTable OBJECT-TYPE
    SYNTAX      SEQUENCE OF HwIsdnUserInTestOprEntry
    MAX-ACCESS  not-accessible
    STATUS      current
    DESCRIPTION
      "Describes the Operation table for the ISDN subscriber circuit test:       
      It realizes the function of the circuit test for ISDN subscribers in the system. In the circuit test, the status (activated, deactivated) of the LT U port, LT power supply voltage, LT power supply overflow auto protection, manual switch-off line feeding voltage, and manual switch-on line feeding voltage are measured.
      The test result shows whether the ISDN subscriber circuit works in the normal state.
      The index of this table is ifIndex."
    ::= { hwNTestMIBObjects 2 }

  hwIsdnUserInTestOprEntry OBJECT-TYPE
    SYNTAX      HwIsdnUserInTestOprEntry
    MAX-ACCESS  not-accessible
    STATUS      current
    DESCRIPTION
      "Describes the Operation table for the ISDN subscriber circuit test:       
      It realizes the function of the circuit test for ISDN subscribers in the system. In the circuit test, the status (activated, deactivated) of the LT U port, LT power supply voltage, LT power supply overflow auto protection, manual switch-off line feeding voltage, and manual switch-on line feeding voltage are measured.
      The test result shows whether the ISDN subscriber circuit works in the normal state.
      The index of this entry is ifIndex."
    INDEX    {  
              ifIndex
             }
    ::= { hwIsdnUserInTestOprTable 1 }

  HwIsdnUserInTestOprEntry ::=
    SEQUENCE
    {
      hwIsdnUserInTestOprType   INTEGER,
      hwIsdnUserInTestActive    INTEGER,
      hwIsdnUserInTestDeactive  INTEGER,
      hwIsdnUserInTestLtSupplyPowerVol  INTEGER,
      hwIsdnUserInTestLtCurrentProctect INTEGER,
      hwIsdnUserInTestCutLineVol        INTEGER,
      hwIsdnUserInTestSwitchOnVol       INTEGER,
      hwIsdnUserInTestBusyProcFlag      INTEGER,
      hwIsdnUserInTestStatus    INTEGER,
      hwIsdnUserInTestActiveResult      INTEGER,
      hwIsdnUserInTestDeactiveResult    INTEGER,
      hwIsdnUserInTestLtSupplyPowerCap  Integer32,
      hwIsdnUserInTestLtSupplyPowerCapResult    INTEGER,
      hwIsdnUserInTestLtCurrentProctectResult   INTEGER,
      hwIsdnUserInTestCutLineVolVal     Integer32,
      hwIsdnUserInTestCutLineVolResult  INTEGER,
      hwIsdnUserInTestSwitchOnVolVal    Integer32,
      hwIsdnUserInTestSwitchOnVolResult INTEGER
    }

  hwIsdnUserInTestOprType OBJECT-TYPE
    SYNTAX      INTEGER{stop(1),start(2)}
    MAX-ACCESS  read-create
    STATUS      current
    DESCRIPTION
        "Describes the Operation type.
         Options: 
            1. stop(1)  -stop the test 
            2. start(2) -start the test  
        "
    ::= { hwIsdnUserInTestOprEntry 1 }

  hwIsdnUserInTestActive OBJECT-TYPE
    SYNTAX      INTEGER{notest(1),test(2)}
    MAX-ACCESS  read-create
    STATUS      current
    DESCRIPTION
        "Describes the ISDN subscriber circuit test-Active.
         Options: 
            1. notest(1) -no test is applied
            2. test(2)   -a test is applied 
        "
    ::= { hwIsdnUserInTestOprEntry 2 }

  hwIsdnUserInTestDeactive OBJECT-TYPE
    SYNTAX      INTEGER{notest(1),test(2)}
    MAX-ACCESS  read-create
    STATUS      current
    DESCRIPTION
        "Describes the ISDN circuit test-Deactive.
         Options: 
            1. notest(1) -no test is applied
            2. test(2)   -a test is applied 
        "
    ::= { hwIsdnUserInTestOprEntry 3 }

  hwIsdnUserInTestLtSupplyPowerVol OBJECT-TYPE
    SYNTAX      INTEGER{notest(1),test(2)}
    MAX-ACCESS  read-create
    STATUS      current
    DESCRIPTION
        "Describes the ISDN circuit test-LT supply power.
         Options: 
            1. notest(1) -no test is applied
            2. test(2)   -a test is applied 
        "
    ::= { hwIsdnUserInTestOprEntry 4 }

  hwIsdnUserInTestLtCurrentProctect OBJECT-TYPE
    SYNTAX      INTEGER{notest(1),test(2)}
    MAX-ACCESS  read-create
    STATUS      current
    DESCRIPTION
        "Describes the ISDN circuit test-LT power supply overflow auto protection .
         Options: 
            1. notest(1) -no test is applied
            2. test(2)   -a test is applied 
        "
    ::= { hwIsdnUserInTestOprEntry 5 }

  hwIsdnUserInTestCutLineVol OBJECT-TYPE
    SYNTAX      INTEGER{notest(1),test(2)}
    MAX-ACCESS  read-create
    STATUS      current
    DESCRIPTION
        "Describes the ISDN circuit test-Manual switch-off line feeding voltage.
         Options: 
            1. notest(1) -no test is applied
            2. test(2)   -a test is applied 
        "
    ::= { hwIsdnUserInTestOprEntry 6 }

  hwIsdnUserInTestSwitchOnVol OBJECT-TYPE
    SYNTAX      INTEGER{notest(1),test(2)}
    MAX-ACCESS  read-create
    STATUS      current
    DESCRIPTION
        "Describes the ISDN circuit test-Manual switch-on line feeding voltage .
         Options: 
            1. notest(1) -no test is applied
            2. test(2)   -a test is applied 
        "
    ::= { hwIsdnUserInTestOprEntry 7 }

  hwIsdnUserInTestBusyProcFlag OBJECT-TYPE
    SYNTAX      INTEGER{busynotest(1),busytest(2),busystrentest(3)}
    MAX-ACCESS  read-create
    STATUS      current
    DESCRIPTION
        "Describes the Busy control flag .
         Options: 
            1. busynotest(1)    -no test when busy
            2. busytest(2)      -remedy test when busy
            3. busystrentest(3) -forced test on busy
        "
    ::= { hwIsdnUserInTestOprEntry 8 }

  hwIsdnUserInTestStatus OBJECT-TYPE
    SYNTAX      INTEGER{normal(1),abnormal(2),portbusy(3),outoftime(4),testingAbnormal(5)}
    MAX-ACCESS  read-only
    STATUS      current
    DESCRIPTION
        "Describes the Test status .
         Options:
            1. normal(1)            -indicates normal 
            2. abnormal(2)          -indicates abnormal 
            3. portbusy(3)          -indicates busy port 
            4. outoftime(4)         -indicates timed-out 
            5. testingAbnormal(5)   -indicates test abnormal
         "
    ::= { hwIsdnUserInTestOprEntry 9 }

  hwIsdnUserInTestActiveResult OBJECT-TYPE
    SYNTAX      INTEGER{normal(1),abnormal(2),outOfTime(3),notest(4)}
    MAX-ACCESS  read-only
    STATUS      current
    DESCRIPTION
        "Describes the Activation result .
         Options:
            1. normal(1)            -indicates normal 
            2. abnormal(2)          -indicates abnormal           
            3. outOfTime(3)         -indicates timed-out              
            4. notest(4)            -indicates no test 
         "
    ::= { hwIsdnUserInTestOprEntry 10 }

  hwIsdnUserInTestDeactiveResult OBJECT-TYPE
    SYNTAX      INTEGER{normal(1),abnormal(2),outoftime(3),notest(4)}
    MAX-ACCESS  read-only
    STATUS      current
    DESCRIPTION
        "Describes the Deactivation result.
         Options:
            1. normal(1)            -indicates normal 
            2. abnormal(2)          -indicates abnormal           
            3. outoftime(3)         -indicates timed-out              
            4. notest(4)            -indicates no test     
         "
    ::= { hwIsdnUserInTestOprEntry 11 }

  hwIsdnUserInTestLtSupplyPowerCap OBJECT-TYPE
    SYNTAX      Integer32
    MAX-ACCESS  read-only
    STATUS      current
    DESCRIPTION
      "LT power supply voltage 
      Unit: millivolt"
    ::= { hwIsdnUserInTestOprEntry 12 }

  hwIsdnUserInTestLtSupplyPowerCapResult OBJECT-TYPE
    SYNTAX      INTEGER{normal(1),abnormal(2),outOfTime(3),notest(4),dslBoardNoSupport(5)}
    MAX-ACCESS  read-only
    STATUS      current
    DESCRIPTION
        "Describes the Test result-LT power supply voltage.
         Options:
        1. normal(1)            -indicates normal 
        2. abnormal(2)          -indicates abnormal           
        3. outOfTime(3)         -indicates timed-out              
        4. notest(4)            -indicates no test 
        5. dslBoardNoSupport(5) -indicates not supported by the DSL02 board
        "
    ::= { hwIsdnUserInTestOprEntry 13 }

  hwIsdnUserInTestLtCurrentProctectResult OBJECT-TYPE
    SYNTAX      INTEGER{outOfTime(1),noProtect(2),protectNoRestore(3),protectAndRestore(4),dslBoardNoSupport(5)}
    MAX-ACCESS  read-only
    STATUS      current
    DESCRIPTION
        "Describes the LT over current auto-protection capability .
         Options:
            1. outOfTime(1)         -indicates timed-out          
            2. noProtect(2)         -indicates not protected
            3. protectNoRestore(3)  -indicates protected but not restored automatically         
            4. protectAndRestore(4) -indicates protected and restored automatically
            5. dslBoardNoSupport(5) -indicates not supported by the DSL02 board
         "
    ::= { hwIsdnUserInTestOprEntry 14 }

  hwIsdnUserInTestCutLineVolVal OBJECT-TYPE
    SYNTAX      Integer32
    MAX-ACCESS  read-only
    STATUS      current
    DESCRIPTION
        "Describes the Manual switch-off line feeding voltage.
         Unit: millivolt, ab. mV
        "
    ::= { hwIsdnUserInTestOprEntry 15 }

  hwIsdnUserInTestCutLineVolResult OBJECT-TYPE
    SYNTAX      INTEGER{normal(1),abnormal(2),outOfTime(3),notest(4),dslBoardNoSupport(5)}
    MAX-ACCESS  read-only
    STATUS      current
    DESCRIPTION
        "Describes the Test result-Manual switch-off line feeding voltage.
         Options:
        1. normal(1)            -indicates normal 
        2. abnormal(2)          -indicates abnormal           
        3. outOfTime(3)         -indicates timed-out              
        4. notest(4)            -indicates no test 
        5. dslBoardNoSupport(5) -indicates not supported by the DSL02 board
         "
    ::= { hwIsdnUserInTestOprEntry 16 }

  hwIsdnUserInTestSwitchOnVolVal OBJECT-TYPE
    SYNTAX      Integer32
    MAX-ACCESS  read-only
    STATUS      current
    DESCRIPTION
        "Describes the Switch on voltage.
         Unit: millivolt, ab. mV
        "
    ::= { hwIsdnUserInTestOprEntry 17 }

  hwIsdnUserInTestSwitchOnVolResult OBJECT-TYPE
    SYNTAX      INTEGER{normal(1),abnormal(2),outOfTime(3),notest(4),dslBoardNoSupport(5)}
    MAX-ACCESS  read-only
    STATUS      current
    DESCRIPTION
        "Describes the Test result-switch on voltage.
         Options:
        1. normal(1)            -indicates normal 
        2. abnormal(2)          -indicates abnormal           
        3. outOfTime(3)         -indicates timed-out              
        4. notest(4)            -indicates no test 
        5. dslBoardNoSupport(5) -indicates not supported by the DSL02 board
         "
    ::= { hwIsdnUserInTestOprEntry 18 }

  hwIsdnUserOutTestOprTable OBJECT-TYPE
    SYNTAX      SEQUENCE OF HwIsdnUserOutTestOprEntry
    MAX-ACCESS  not-accessible
    STATUS      current
    DESCRIPTION
      "Operation table for the ISDN subscriber loop-line test:
      It realizes the function of the loop-line test for ISDN subscribers in the system. In the loop-line test, the Activate NT1, Deactivate NT1, and Transmission Bit Error Rate are tested.
      The index of this table is ifIndex."
    ::= { hwNTestMIBObjects 3 }

  hwIsdnUserOutTestOprEntry OBJECT-TYPE
    SYNTAX      HwIsdnUserOutTestOprEntry
    MAX-ACCESS  not-accessible
    STATUS      current
    DESCRIPTION
      "Operation table for the ISDN subscriber loop-line test:
      It realizes the function of the loop-line test for ISDN subscribers in the system. In the loop-line test, the Activate NT1, Deactivate NT1, and Transmission Bit Error Rate are tested.
      The index of this entry is ifIndex."
    INDEX    {  
              ifIndex
             }
    ::= { hwIsdnUserOutTestOprTable 1 }

  HwIsdnUserOutTestOprEntry ::=
    SEQUENCE
    {
      hwIsdnUserOutTestOprType              INTEGER,
      hwIsdnUserOutTestActiveNT1            INTEGER,
      hwIsdnUserOutTestDeactiveNT1          INTEGER,
      hwIsdnUserOutTestTransBitError        INTEGER,
      hwIsdnUserOutTestErrCodeTestTime      Integer32,
      hwIsdnUserOutTestBusyProcessFlag      INTEGER,
      hwIsdnUserOutTestStatus               INTEGER,
      hwIsdnUserOutTestActNT1Result         INTEGER,
      hwIsdnUserOutTestDeactNT1Result       INTEGER,
      hwIsdnUserOutTestTransBitErrorResult  INTEGER,
      hwIsdnUserOutTestTotalSend            Integer32,
      hwIsdnUserOutTestCodeErrorNumber      Integer32,
      hwIsdnUserOutTestCodeErrorRate        Integer32
    }

  hwIsdnUserOutTestOprType OBJECT-TYPE
    SYNTAX      INTEGER{stop(1),start(2)}
    MAX-ACCESS  read-create
    STATUS      current
    DESCRIPTION
        "Describes the Operation type.
         Options: 
            1. stop(1)  -stop the test 
            2. start(2) -start the test  
        "
    ::= { hwIsdnUserOutTestOprEntry 1 }

  hwIsdnUserOutTestActiveNT1 OBJECT-TYPE
    SYNTAX      INTEGER{notest(1),test(2)}
    MAX-ACCESS  read-create
    STATUS      current
    DESCRIPTION
        "Describes the ISDN loop line test-Activate NT1.
         Options: 
            1. notest(1) -no test is applied
            2. test(2)   -a test is applied 
        "
    ::= { hwIsdnUserOutTestOprEntry 2 }

  hwIsdnUserOutTestDeactiveNT1 OBJECT-TYPE
    SYNTAX      INTEGER{notest(1),test(2)}
    MAX-ACCESS  read-create
    STATUS      current
    DESCRIPTION
        "Describes the ISDN loop line test-Deactivate NT1.
         Options: 
            1. notest(1) -no test is applied
            2. test(2)   -a test is applied 
        "
    ::= { hwIsdnUserOutTestOprEntry 3 }

  hwIsdnUserOutTestTransBitError OBJECT-TYPE
    SYNTAX      INTEGER{notest(1),test(2)}
    MAX-ACCESS  read-create
    STATUS      current
    DESCRIPTION
        "Describes the ISDN loop line test-Transmission Bit Error Rate.
         Options: 
            1. notest(1) -no test is applied
            2. test(2)   -a test is applied 
        "
    ::= { hwIsdnUserOutTestOprEntry 4 }

  hwIsdnUserOutTestErrCodeTestTime OBJECT-TYPE
    SYNTAX      Integer32(1..255)
    MAX-ACCESS  read-create
    STATUS      current
    DESCRIPTION
        "Describes the Bit Error Rate Test Duration.
         Unit: s. 
         Default: 120 s for the EMS
        "
    DEFVAL      { 120 }
    ::= { hwIsdnUserOutTestOprEntry 5 }

  hwIsdnUserOutTestBusyProcessFlag OBJECT-TYPE
    SYNTAX      INTEGER{busyNoTest(1),busyTest(2)}
    MAX-ACCESS  read-create
    STATUS      current
    DESCRIPTION
        "Describes the Busy control flag.  
         Options:
         1. busyNoTest(1) -indicates no test when busy 
         2. busyTest(2)   -indicates remedy test when busy
         "
    ::= { hwIsdnUserOutTestOprEntry 6 }

  hwIsdnUserOutTestStatus OBJECT-TYPE
    SYNTAX      INTEGER{normal(1),abnormal(2),portbusy(3),outoftime(4),testingAbnormal(5) }
    MAX-ACCESS  read-only
    STATUS      current
    DESCRIPTION
        "Describes the Test status.
         Options:
            1. normal(1)            -indicates normal 
            2. abnormal(2)          -indicates abnormal 
            3. portbusy(3)          -indicates busy port 
            4. outoftime(4)         -indicates timed-out 
            5. testingAbnormal(5)   -indicates test abnormal
        "
    ::= { hwIsdnUserOutTestOprEntry 7 }

  hwIsdnUserOutTestActNT1Result OBJECT-TYPE
    SYNTAX      INTEGER{normal(1),activeFail(2),noNt1OrNt1NotUse(3),activeUifSuccess(4),activeUifAndSifSuccess(5),outOfTime(6),startTestFail(7)}
    MAX-ACCESS  read-only
    STATUS      current
    DESCRIPTION
        "Describes the Activation NT1 result .
         Options:
         1. normal(1)                 -indicates Normal
         2. activeFail(2)             -indicates failure
         3. noNt1OrNt1NotUse(3)       -indicates no NT1 or NT1 is unavailable
         4. activeUifSuccess(4)       -indicates U port activated successfully
         5. activeUifAndSifSuccess(5) -indicates U and S ports activated successfully
         6. outOfTime(6)              -indicates Timed-out
         7. startTestFail(7)          -indicates starting test fails
        "
    ::= { hwIsdnUserOutTestOprEntry 8 }

  hwIsdnUserOutTestDeactNT1Result OBJECT-TYPE
    SYNTAX      INTEGER{normal(1),abnormal(2),outoftime(3),notest(4)}
    MAX-ACCESS  read-only
    STATUS      current
    DESCRIPTION
        "Describes the Test result-Deactivate NT1.
         Options:   
         1. normal(1)           -indicates normal 
         2. abnormal(2)         -indicates abnormal 
         3. outoftime(3)        -indicates timed-out
         4. notest(4)           -indicates not tested
        "
    ::= { hwIsdnUserOutTestOprEntry 9 }

  hwIsdnUserOutTestTransBitErrorResult OBJECT-TYPE
    SYNTAX      INTEGER{normal(1),nt1BadOrNoTexist(2),nt1ActiveFail(3),nt1LoopFail(4),syncFail(5),outOfTime(6),notest(7)}
    MAX-ACCESS  read-only
    STATUS      current
    DESCRIPTION
        "Describes the Test result-Transmission bit error rate.
         Options:    
         1. normal(1)           -indicates normal 
         2. nt1BadOrNoTexist(2) -indicates NT1 is bad or no NT1 
         3. nt1ActiveFail(3)    -indicates activating NT1 fails 
         4. nt1LoopFail(4)      -indicates loopback on NT1 fails 
         5. syncFail(5)         -indicates bit error rate is too high and synchronization fails 
         6. outOfTime(6)        -indicates timed-out 
         7. notest(7)           -indicates not tested)
        "
    ::= { hwIsdnUserOutTestOprEntry 10 }

  hwIsdnUserOutTestTotalSend OBJECT-TYPE
    SYNTAX      Integer32
    MAX-ACCESS  read-only
    STATUS      current
    DESCRIPTION
        "Describes the Total number of sent bits"
    ::= { hwIsdnUserOutTestOprEntry 11 }

  hwIsdnUserOutTestCodeErrorNumber OBJECT-TYPE
    SYNTAX      Integer32
    MAX-ACCESS  read-only
    STATUS      current
    DESCRIPTION
        "Describes the Number of bit errors"
    ::= { hwIsdnUserOutTestOprEntry 12 }

  hwIsdnUserOutTestCodeErrorRate OBJECT-TYPE
    SYNTAX      Integer32
    MAX-ACCESS  read-only
    STATUS      current
    DESCRIPTION
        "Describes the Bit error rate"
    ::= { hwIsdnUserOutTestOprEntry 13 }

  hwIsdnUserOutLineTestOprTable OBJECT-TYPE
    SYNTAX      SEQUENCE OF HwIsdnUserOutLineTestOprEntry
    MAX-ACCESS  not-accessible
    STATUS      current
    DESCRIPTION
      "Operation table for the ISDN subscriber loop-line test.
      It realizes the function of the loop-line test for ISDN subscribers in the system. In the loop-line test, the voltage, resistance and capacitance of the loop line are tested to check for faults such as broken circuit, short circuit, grounding and cross-connected line.
      The index of this table is ifIndex"
    ::= { hwNTestMIBObjects 4 }

  hwIsdnUserOutLineTestOprEntry OBJECT-TYPE
    SYNTAX      HwIsdnUserOutLineTestOprEntry
    MAX-ACCESS  not-accessible
    STATUS      current
    DESCRIPTION
      "Operation table for the ISDN subscriber loop-line test.
      It realizes the function of the loop-line test for ISDN subscribers in the system. In the loop-line test, the voltage, resistance and capacitance of the loop line are tested to check for faults such as broken circuit, short circuit, grounding and cross-connected line.
      The index of this entry is ifIndex"
    INDEX    {  
              ifIndex
             }
    ::= { hwIsdnUserOutLineTestOprTable 1 }

  HwIsdnUserOutLineTestOprEntry ::=
    SEQUENCE
    {
      hwIsdnUserOutLineTestOprType      INTEGER,
      hwIsdnUserOutLineTestVoltage      INTEGER,
      hwIsdnUserOutLineTestResistance   INTEGER,
      hwIsdnUserOutLineTestCapacitance  INTEGER,
      hwIsdnUserOutLineTestBusyProcFlag INTEGER,
      hwIsdnUserOutLineTestStatus       INTEGER,
      hwIsdnUserOutLineTestConclusion   Integer32,
      hwIsdnUserOutLineTestACAG         Integer32,
      hwIsdnUserOutLineTestACBG         Integer32,
      hwIsdnUserOutLineTestACAB         Integer32,
      hwIsdnUserOutLineTestDCAG         Integer32,
      hwIsdnUserOutLineTestDCBG         Integer32,
      hwIsdnUserOutLineTestDCAB         Integer32,
      hwIsdnUserOutLineTestRAG          Integer32,
      hwIsdnUserOutLineTestRBG          Integer32,
      hwIsdnUserOutLineTestRAB          Integer32,
      hwIsdnUserOutLineTestCapAG        Integer32,
      hwIsdnUserOutLineTestCapBG        Integer32,
      hwIsdnUserOutLineTestCapAB        Integer32,
      hwIsdnUserOutLineTestImpedance    INTEGER,
      hwIsdnUserOutLineTestImpedanceAB  Integer32,
      hwIsdnUserOutLineTestImpedanceBA  Integer32,
      hwIsdnUserOutLineTestImpedanceAG  Integer32,
      hwIsdnUserOutLineTestImpedanceBG  Integer32,
      hwIsdnUserOutLineTestCurrent      INTEGER,
      hwIsdnUserOutLineTestACCurrentAG  Integer32,
      hwIsdnUserOutLineTestACCurrentBG  Integer32,
      hwIsdnUserOutLineTestACCurrentAB  Integer32,
      hwIsdnUserOutLineTestDCCurrentAG  Integer32,
      hwIsdnUserOutLineTestDCCurrentBG  Integer32,
      hwIsdnUserOutLineTestDCCurrentAB  Integer32,
      hwIsdnUserOutLineTestLoopCurrent  INTEGER,
      hwIsdnUserOutLineTestLC           Integer32,
      hwIsdnUserOutLineTestNoise        INTEGER,
      hwIsdnUserOutLineTestN            Integer32
    }

  hwIsdnUserOutLineTestOprType OBJECT-TYPE
    SYNTAX      INTEGER{stop(1),start(2)}
    MAX-ACCESS  read-create
    STATUS      current
    DESCRIPTION
        "Describes the Operation type.
         Options: 
            1. stop(1)  -stop the test 
            2. start(2) -start the test  
        "
    ::= { hwIsdnUserOutLineTestOprEntry 1 }

  hwIsdnUserOutLineTestVoltage OBJECT-TYPE
    SYNTAX      INTEGER{notest(1),test(2)}
    MAX-ACCESS  read-create
    STATUS      current
    DESCRIPTION
        "ISDN loop line test-Voltage.
         Options: 
            1. notest(1) -no test is applied
            2. test(2)   -a test is applied 
        "
    ::= { hwIsdnUserOutLineTestOprEntry 2 }

  hwIsdnUserOutLineTestResistance OBJECT-TYPE
    SYNTAX      INTEGER{notest(1),test(2)}
    MAX-ACCESS  read-create
    STATUS      current
    DESCRIPTION
        "ISDN loop line test-Resistance.
         Options: 
            1. notest(1) -no test is applied
            2. test(2)   -a test is applied 
        "
    ::= { hwIsdnUserOutLineTestOprEntry 3 }

  hwIsdnUserOutLineTestCapacitance OBJECT-TYPE
    SYNTAX      INTEGER{notest(1),test(2)}
    MAX-ACCESS  read-create
    STATUS      current
    DESCRIPTION
        "ISDN loop line test-Capacitance.
         Options: 
            1. notest(1) -no test is applied
            2. test(2)   -a test is applied 
        "
    ::= { hwIsdnUserOutLineTestOprEntry 4 }

  hwIsdnUserOutLineTestBusyProcFlag OBJECT-TYPE
    SYNTAX      INTEGER{busyNoTest(1),busyTest  (2)}
    MAX-ACCESS  read-create
    STATUS      current
    DESCRIPTION
        "Busy control flag .  
         Options:
         1. busyNoTest(1) -indicates no test when busy 
         2. busyTest(2)   -indicates remedy test when busy
         "
    ::= { hwIsdnUserOutLineTestOprEntry 5 }

  hwIsdnUserOutLineTestStatus OBJECT-TYPE
    SYNTAX      INTEGER{normal(1),abnormal(2),portbusy(3),outoftime(4),testingAbnormal(5)}
    MAX-ACCESS  read-only
    STATUS      current
    DESCRIPTION
        "Test status.
         Options:
            1. normal(1)            -indicates normal 
            2. abnormal(2)          -indicates abnormal 
            3. portbusy(3)          -indicates busy port 
            4. outoftime(4)         -indicates timed-out 
            5. testingAbnormal(5)   -indicates test abnormal
        "
    ::= { hwIsdnUserOutLineTestOprEntry 6 }

  hwIsdnUserOutLineTestConclusion OBJECT-TYPE
    SYNTAX      Integer32
    MAX-ACCESS  read-only
    STATUS      current
    DESCRIPTION
        "Conclusion 
         Range:1-89
        (Enumerated type. 
        1: Normal 2: Contact with the power line 3: A line mixed with others 4: B line mixed with others
        5: Mixed with others (two lines) 6: A line grounding 7: B line grounding 8: AB grounding
        9: Self-mixed (small resistance, self-mixed) 10: A-B poor insulation 11: A-ground leakage
        12: B-ground leakage 13: AB ground leakage 14: A-B leakage 15: NT1 not connected
        16: not on-hook 17: unknown 18: self-Mixed(inMDF) 19: self-Mixed(outMDF) 20: cutLine(inMDF) 21: cutLine(outMDF)
        22: A-B voltage abnormal 23:lines voltage abnormal 24:lines resistance abnormal 25: A-B resistance abnormal
        26: self-mixed (small resistance, self-mixed) or not on-hook 27:lines abnormal
        30: DC voltage(Power feed) 31: AC voltage(Ringing)
        32: DC voltage(Offhook) 33: DC voltage 34: AC voltage
        60: A->ground AC voltage abnormal 61: B->ground AC voltage abnormal 62: AB-ground AC voltage abnormal
        63: AB->ground DC voltage abnormal 64: A->ground DC voltage abnormal 65: B->ground DC voltage abnormal
        66: A-B DC voltage abnormal 67: A->ground insulation resistance abnormal 68: B->ground insulation resistance abnormal
        69: AB->ground insulation resistance abnormal 70: A->ground poor insulation 71: B->ground poor insulation
        72: AB->ground poor insulation 73: A->ground impedance abnormal 74: B->ground impedance abnormal
        75: A->B impedance abnormal 76: B->A impedance abnormal 77: A->ground AC current abnormal
        78: B->ground AC current abnormal 79: A-B AC current abnormal 80: A->ground DC current abnormal
        81: B->ground DC current abnormal 82: A-B DC current abnormal 83: loop current abnormal
        84: loop resistance abnormal 85: AB->ground capacitance abnormal 86: A->ground capacitance abnomal
        87: B->ground capacitacne abnormal 88: A-B capacitance abnomal 89: noise abnomal"
    ::= { hwIsdnUserOutLineTestOprEntry 7 }

  hwIsdnUserOutLineTestACAG OBJECT-TYPE
    SYNTAX      Integer32
    MAX-ACCESS  read-only
    STATUS      current
    DESCRIPTION
        "A->ground AC voltage.
         Unit: millivolt, ab. mV
        "
    ::= { hwIsdnUserOutLineTestOprEntry 8 }

  hwIsdnUserOutLineTestACBG OBJECT-TYPE
    SYNTAX      Integer32
    MAX-ACCESS  read-only
    STATUS      current
    DESCRIPTION
        "B->ground AC voltage. 
         Unit: millivolt, ab. mV
        "
    ::= { hwIsdnUserOutLineTestOprEntry 9 }

  hwIsdnUserOutLineTestACAB OBJECT-TYPE
    SYNTAX      Integer32
    MAX-ACCESS  read-only
    STATUS      current
    DESCRIPTION
        "A->B AC voltage.
         Unit: millivolt, ab. mV
        "
    ::= { hwIsdnUserOutLineTestOprEntry 10 }

  hwIsdnUserOutLineTestDCAG OBJECT-TYPE
    SYNTAX      Integer32
    MAX-ACCESS  read-only
    STATUS      current
    DESCRIPTION
        "A->ground DC voltage. 
         Unit: millivolt, ab. mV
        "
    ::= { hwIsdnUserOutLineTestOprEntry 11 }

  hwIsdnUserOutLineTestDCBG OBJECT-TYPE
    SYNTAX      Integer32
    MAX-ACCESS  read-only
    STATUS      current
    DESCRIPTION
        "B->ground DC voltage.
         Unit: millivolt, ab. mV
        "
    ::= { hwIsdnUserOutLineTestOprEntry 12 }

  hwIsdnUserOutLineTestDCAB OBJECT-TYPE
    SYNTAX      Integer32
    MAX-ACCESS  read-only
    STATUS      current
    DESCRIPTION
        "A->B DC voltage.
         Unit: millivolt, ab. mV
        "
    ::= { hwIsdnUserOutLineTestOprEntry 13 }

  hwIsdnUserOutLineTestRAG OBJECT-TYPE
    SYNTAX      Integer32
    MAX-ACCESS  read-only
    STATUS      current
    DESCRIPTION
        "A->ground insulation resistance.
         Unit: ohm
        "
    ::= { hwIsdnUserOutLineTestOprEntry 14 }

  hwIsdnUserOutLineTestRBG OBJECT-TYPE
    SYNTAX      Integer32
    MAX-ACCESS  read-only
    STATUS      current
    DESCRIPTION
        "B->ground insulation resistance.
         Unit: ohm
        "
    ::= { hwIsdnUserOutLineTestOprEntry 15 }

  hwIsdnUserOutLineTestRAB OBJECT-TYPE
    SYNTAX      Integer32
    MAX-ACCESS  read-only
    STATUS      current
    DESCRIPTION
        "A->B insulation resistance.
         Unit: ohm
        "
    ::= { hwIsdnUserOutLineTestOprEntry 16 }

  hwIsdnUserOutLineTestCapAG OBJECT-TYPE
    SYNTAX      Integer32
    MAX-ACCESS  read-only
    STATUS      current
    DESCRIPTION
        "A->ground capacitance.
         Unit: nF
        "
    ::= { hwIsdnUserOutLineTestOprEntry 17 }

  hwIsdnUserOutLineTestCapBG OBJECT-TYPE
    SYNTAX      Integer32
    MAX-ACCESS  read-only
    STATUS      current
    DESCRIPTION
        "B->ground capacitance.
         Unit: nF
        "
    ::= { hwIsdnUserOutLineTestOprEntry 18 }

  hwIsdnUserOutLineTestCapAB OBJECT-TYPE
    SYNTAX      Integer32
    MAX-ACCESS  read-only
    STATUS      current
    DESCRIPTION
        "A->B capacitance.
         Unit: nF
        "
    ::= { hwIsdnUserOutLineTestOprEntry 19 }
    
  hwIsdnUserOutLineTestImpedance OBJECT-TYPE
    SYNTAX INTEGER
        {
        notest(1),
        test(2)
        }
    MAX-ACCESS read-create
    STATUS current
    DESCRIPTION
        "Loop-Line Test-Impedance.
         Options: 
        1. notest(1) -no test is applied
        2. test(2)   -a test is applied 
        "
    ::= { hwIsdnUserOutLineTestOprEntry 20 }

  hwIsdnUserOutLineTestImpedanceAB OBJECT-TYPE
    SYNTAX Integer32
    MAX-ACCESS read-only
    STATUS current
    DESCRIPTION
        "A->B impedance.
         Unit: ohm
        "
    ::= { hwIsdnUserOutLineTestOprEntry 21 }
    
  hwIsdnUserOutLineTestImpedanceBA OBJECT-TYPE
    SYNTAX Integer32
    MAX-ACCESS read-only
    STATUS current
    DESCRIPTION
        "B->A impedance.
         Unit: ohm
        "
    ::= { hwIsdnUserOutLineTestOprEntry 22 }
    
  hwIsdnUserOutLineTestImpedanceAG OBJECT-TYPE
    SYNTAX Integer32
    MAX-ACCESS read-only
    STATUS current
    DESCRIPTION
        "A->ground impedance.
         Unit: ohm
        "
    ::= { hwIsdnUserOutLineTestOprEntry 23 }

  hwIsdnUserOutLineTestImpedanceBG OBJECT-TYPE
    SYNTAX Integer32
    MAX-ACCESS read-only
    STATUS current
    DESCRIPTION
        "B->ground impedance.
         Unit: ohm
        "
    ::= { hwIsdnUserOutLineTestOprEntry 24 }


  hwIsdnUserOutLineTestCurrent OBJECT-TYPE
    SYNTAX INTEGER
        {
        notest(1),
        test(2)
        }
    MAX-ACCESS read-create
    STATUS current
    DESCRIPTION
        "Loop line test-Current.
         Options: 
        1. notest(1) -no test is applied
        2. test(2)   -a test is applied 
        "
    ::= { hwIsdnUserOutLineTestOprEntry 25 }

  hwIsdnUserOutLineTestACCurrentAG OBJECT-TYPE
    SYNTAX Integer32
    MAX-ACCESS read-only
    STATUS current
    DESCRIPTION
        "A->ground AC current
         Unit: mA
        "
    ::= { hwIsdnUserOutLineTestOprEntry 26 }
    
  hwIsdnUserOutLineTestACCurrentBG OBJECT-TYPE
    SYNTAX Integer32
    MAX-ACCESS read-only
    STATUS current
    DESCRIPTION
        "B->ground AC current.
         Unit: mA
        "
    ::= { hwIsdnUserOutLineTestOprEntry 27 }

  hwIsdnUserOutLineTestACCurrentAB OBJECT-TYPE
    SYNTAX Integer32
    MAX-ACCESS read-only
    STATUS current
    DESCRIPTION
        "AB AC current.
         Unit: mA
        "
    ::= { hwIsdnUserOutLineTestOprEntry 28 }

  hwIsdnUserOutLineTestDCCurrentAG OBJECT-TYPE
    SYNTAX Integer32
    MAX-ACCESS read-only
    STATUS current
    DESCRIPTION
        "A->ground DC current.
         Unit: mA
        "
    ::= { hwIsdnUserOutLineTestOprEntry 29 }
    
  hwIsdnUserOutLineTestDCCurrentBG OBJECT-TYPE
    SYNTAX Integer32
    MAX-ACCESS read-only
    STATUS current
    DESCRIPTION
        "B->ground DC current.
         Unit: mA
        "
    ::= { hwIsdnUserOutLineTestOprEntry 30 }

  hwIsdnUserOutLineTestDCCurrentAB OBJECT-TYPE
    SYNTAX Integer32
    MAX-ACCESS read-only
    STATUS current
    DESCRIPTION
        "AB DC current.
         Unit: mA
        "
    ::= { hwIsdnUserOutLineTestOprEntry 31 }
    
  hwIsdnUserOutLineTestLoopCurrent OBJECT-TYPE
    SYNTAX INTEGER
        {
        notest(1),
        test(2)
        }
    MAX-ACCESS read-create
    STATUS current
    DESCRIPTION
        "Loop-Line Test-Loop Current.
         Options: 
        1. notest(1) -no test is applied
        2. test(2)   -a test is applied 
        "
    ::= { hwIsdnUserOutLineTestOprEntry 32 }

  hwIsdnUserOutLineTestLC OBJECT-TYPE
    SYNTAX Integer32
    MAX-ACCESS read-only
    STATUS current
    DESCRIPTION
        "Loop Current.
         Unit: mA
        "
    ::= { hwIsdnUserOutLineTestOprEntry 33 }

  hwIsdnUserOutLineTestNoise OBJECT-TYPE
    SYNTAX INTEGER
        {
        notest(1),
        test(2)
        }
    MAX-ACCESS read-create
    STATUS current
    DESCRIPTION
        "Loop-Line Test-Noise .
         Options: 
        1. notest(1) -no test is applied
        2. test(2)   -a test is applied
        "
    ::= { hwIsdnUserOutLineTestOprEntry 34 }

  hwIsdnUserOutLineTestN OBJECT-TYPE
    SYNTAX Integer32
    MAX-ACCESS read-only
    STATUS current
    DESCRIPTION
        "Noise.
         Unit: dBm
        "
    ::= { hwIsdnUserOutLineTestOprEntry 35 }

  hwIsdnPortStateSwitchTestOprTable OBJECT-TYPE
    SYNTAX      SEQUENCE OF HwIsdnPortStateSwitchTestOprEntry
    MAX-ACCESS  not-accessible
    STATUS      current
    DESCRIPTION
      "Operation table for the test on ISDN port status switching:
      It realizes the function of the test on ISDN port status switching in the system. In the test, the status of a port is switched between NT1 and LT to check whether the NT1 and LT functions of the port work.
      The index of this table is ifIndex"
    ::= { hwNTestMIBObjects 5 }

  hwIsdnPortStateSwitchTestOprEntry OBJECT-TYPE
    SYNTAX      HwIsdnPortStateSwitchTestOprEntry
    MAX-ACCESS  not-accessible
    STATUS      current
    DESCRIPTION
      "Operation table for the test on ISDN port status switching:
      It realizes the function of the test on ISDN port status switching in the system. In the test, the status of a port is switched between NT1 and LT to check whether the NT1 and LT functions of the port work.
      The index of this entry is ifIndex"
    INDEX    {  
              ifIndex
             }
    ::= { hwIsdnPortStateSwitchTestOprTable 1 }

  HwIsdnPortStateSwitchTestOprEntry ::=
    SEQUENCE
    {
      hwIsdnPortStateSwitchTestOprType  INTEGER,
      hwIsdnPortStateSwitchTestStatus   INTEGER
    }

  hwIsdnPortStateSwitchTestOprType OBJECT-TYPE
    SYNTAX      INTEGER{switchNT1(1),switchLT(2),switchnormal(3)}
    MAX-ACCESS  read-create
    STATUS      current
    DESCRIPTION
        "Operation type .
         Options: 
         1. switchNT1(1)    -indicates Switch to NT1 
         2. switchLT(2)     -indicates Switch to LT
         3. switchnormal(3) -indicates Switch to the normal state
         "
    ::= { hwIsdnPortStateSwitchTestOprEntry 1 }

  hwIsdnPortStateSwitchTestStatus OBJECT-TYPE
    SYNTAX      INTEGER{success(1),failure(2),portBusy(3),timeOut(4),testingAbnormal(5)}
    MAX-ACCESS  read-only
    STATUS      current
    DESCRIPTION
        "Test status.
         Options: 
         1. success(1)         -indicates normal
         2. failure(2)         -indicates abnormal
         3. portBusy(3)        -indicates busy port
         4. timeOut(4)         -indicates timed-out
         5. testingAbnormal(5) -indicates test abnormal
         "
    ::= { hwIsdnPortStateSwitchTestOprEntry 2 }

  hw112UserRingTestOprTable OBJECT-TYPE
    SYNTAX      SEQUENCE OF Hw112UserRingTestOprEntry
    MAX-ACCESS  not-accessible
    STATUS      current
    DESCRIPTION
      "Ringing test on the 112 analog subscriber phones:
      It realizes the function of the ringing test on the phones of subscribers in the system. This test helps check whether a subscriber phone can ring normally.
      The index of this table is ifIndex"
    ::= { hwNTestMIBObjects 6 }

  hw112UserRingTestOprEntry OBJECT-TYPE
    SYNTAX      Hw112UserRingTestOprEntry
    MAX-ACCESS  not-accessible
    STATUS      current
    DESCRIPTION
      "Ringing test on the 112 analog subscriber phones:
      It realizes the function of the ringing test on the phones of subscribers in the system. This test helps check whether a subscriber phone can ring normally.
      The index of this entry is ifIndex"

    INDEX    {  
              ifIndex
             }
    ::= { hw112UserRingTestOprTable 1 }

  Hw112UserRingTestOprEntry ::=
    SEQUENCE
    {
      hw112UserRingTestOprType  INTEGER,
      hw112UserRingTestTime     Integer32,
      hw112UserRingTestResult   INTEGER
    }

  hw112UserRingTestOprType OBJECT-TYPE
    SYNTAX      INTEGER{stop(1),start(2)}
    MAX-ACCESS  read-create
    STATUS      current
    DESCRIPTION
        "Operation type .
         Options: 
         1. stop(1)  -stop the test 
         2. start(2) -start the test 
         Note:The 112 protocol does not define the stop command.
        "
    ::= { hw112UserRingTestOprEntry 1 }

  hw112UserRingTestTime OBJECT-TYPE
    SYNTAX      Integer32(3..60)
    MAX-ACCESS  read-create
    STATUS      current
    DESCRIPTION
        "Ringing duration.
         Unit: second
        "
    ::= { hw112UserRingTestOprEntry 2 }

  hw112UserRingTestResult OBJECT-TYPE
    SYNTAX      INTEGER{offhook(1),onhook(2)}
    MAX-ACCESS  read-only
    STATUS      current
    DESCRIPTION
        "Test result.
         Options: 
         1. offhook(1)  -indicates off hook 
         2. onhook(2)   -indicates on hook
         The 112 protocol defines only two test results."
    ::= { hw112UserRingTestOprEntry 3 }

  hw112UserDialTestOprTable OBJECT-TYPE
    SYNTAX      SEQUENCE OF Hw112UserDialTestOprEntry
    MAX-ACCESS  not-accessible
    STATUS      current
    DESCRIPTION
      "Operation table for the test on the DTMF or pulse feature of the 112 analog subscriber phones:
      It realizes the test on the DTMF or pulse feature of the subscriber phones in the system. This test helps check whether a subscriber phone can make calls normally.
      The index of this table is ifIndex"
    ::= { hwNTestMIBObjects 7 }

  hw112UserDialTestOprEntry OBJECT-TYPE
    SYNTAX      Hw112UserDialTestOprEntry
    MAX-ACCESS  not-accessible
    STATUS      current
    DESCRIPTION
      "Operation table for the test on the DTMF or pulse feature of the 112 analog subscriber phones:
      It realizes the test on the DTMF or pulse feature of the subscriber phones in the system. This test helps check whether a subscriber phone can make calls normally.
      The index of this entry is ifIndex"
    INDEX    {  
              ifIndex
             }
    ::= { hw112UserDialTestOprTable 1 }

  Hw112UserDialTestOprEntry ::=
    SEQUENCE
    {
      hw112UserDialTestOprType          INTEGER,
      hw112UserDialTestReceiveNumber    Integer32,
      hw112UserDialTestResult           INTEGER,
      hw112UserDialTestDigit            INTEGER,
      hw112UserDialTestLowLevel         Integer32,
      hw112UserDialTestHighLevel        Integer32,
      hw112UserDialTestLowFreq          Integer32,
      hw112UserDialTestHighFreq         Integer32,
      hw112UserDialTestPulseLen         Integer32,
      hw112UserDialTestMakeDur          Integer32,
      hw112UserDialTestBreakDur         Integer32
    }

  hw112UserDialTestOprType OBJECT-TYPE
    SYNTAX      INTEGER{stop(1),start(2)}
    MAX-ACCESS  read-create
    STATUS      current
    DESCRIPTION
        "Operation type .
         Options: 
         1. stop(1)  -stop the test 
         2. start(2) -start the test 
         Note:The 112 protocol does not define the stop command.
        "
    ::= { hw112UserDialTestOprEntry 1 }

  hw112UserDialTestReceiveNumber OBJECT-TYPE
    SYNTAX      Integer32
    MAX-ACCESS  read-create
    STATUS      current
    DESCRIPTION
        "Number of received calls"
    ::= { hw112UserDialTestOprEntry 2 }

  hw112UserDialTestResult OBJECT-TYPE
    SYNTAX      INTEGER{success(1),fail(2)}
    MAX-ACCESS  read-only
    STATUS      current
    DESCRIPTION
        "Operation result.
         Options: 
         1. success(1)  -indicates the test is successful
         2. fail(2)     -indicates the test fail
        "
    ::= { hw112UserDialTestOprEntry 3 }

  hw112UserDialTestDigit OBJECT-TYPE
    SYNTAX      INTEGER{n1(1),n2(2),n3(3),n4(4),n5(5),n6(6),n7(7),n8(8),n9(9),n0(10),nStar(11),nWell(12),nOthers(13),onhook(14)}
    MAX-ACCESS  read-only
    STATUS      current
    DESCRIPTION
        "Dialing numeral.
         Options: 
         1. n1(1)       -indicates 1
         2. n2(2)       -indicates 2
         3. n3(3)       -indicates 3
         4. n4(4)       -indicates 4
         5. n5(5)       -indicates 5
         6. n6(6)       -indicates 6
         7. n7(7)       -indicates 7
         8. n8(8)       -indicates 8
         9. n9(9)       -indicates 9
         10. n0(10)       -indicates 0
         11. nStar(11)   -indicates *
         12. nWell(12)   -indicates #
         13. nOthers(13) -indicates others 
         14. onhook(14)  -indicates on hook
        "
    ::= { hw112UserDialTestOprEntry 4 }

  hw112UserDialTestLowLevel OBJECT-TYPE
    SYNTAX      Integer32
    MAX-ACCESS  read-only
    STATUS      current
    DESCRIPTION
        "Digital low power level.
         Unit: dBm
        "
    ::= { hw112UserDialTestOprEntry 5 }

  hw112UserDialTestHighLevel OBJECT-TYPE
    SYNTAX      Integer32
    MAX-ACCESS  read-only
    STATUS      current
    DESCRIPTION
        "Digital high power level.
         Unit: dBm
        "
    ::= { hw112UserDialTestOprEntry 6 }

  hw112UserDialTestLowFreq OBJECT-TYPE
    SYNTAX      Integer32
    MAX-ACCESS  read-only
    STATUS      current
    DESCRIPTION
        "Digital low frequency. 
         Unit: Hz
        "
    ::= { hw112UserDialTestOprEntry 7 }

  hw112UserDialTestHighFreq OBJECT-TYPE
    SYNTAX      Integer32
    MAX-ACCESS  read-only
    STATUS      current
    DESCRIPTION
        "Digital high frequency. 
         Unit: Hz
        "
    ::= { hw112UserDialTestOprEntry 8 }

  hw112UserDialTestPulseLen OBJECT-TYPE
    SYNTAX      Integer32
    MAX-ACCESS  read-only
    STATUS      current
    DESCRIPTION
        "Pulse length.
         Unit: millisecond
        "
    ::= { hw112UserDialTestOprEntry 9 }

  hw112UserDialTestMakeDur OBJECT-TYPE
    SYNTAX      Integer32
    MAX-ACCESS  read-only
    STATUS      current
    DESCRIPTION
        "Pulse duration.
         Unit: millisecond
        "
    ::= { hw112UserDialTestOprEntry 10 }

  hw112UserDialTestBreakDur OBJECT-TYPE
    SYNTAX      Integer32
    MAX-ACCESS  read-only
    STATUS      current
    DESCRIPTION
        "Pulse break length.
         Unit: millisecond
        "
    ::= { hw112UserDialTestOprEntry 11 }

  hw112UserHowlerTestOprrTable OBJECT-TYPE
    SYNTAX      SEQUENCE OF Hw112UserHowlerTestOprrEntry
    MAX-ACCESS  not-accessible
    STATUS      current
    DESCRIPTION
      "Operation table for the howler tone test on 112 analog subscriber phones:
      It realizes the function of the howler tone test on the subscriber phones in the system. This test helps check whether a subscriber phone can play the howler tone normally.
      The index of this table is ifIndex"
    ::= { hwNTestMIBObjects 8 }

  hw112UserHowlerTestOprrEntry OBJECT-TYPE
    SYNTAX      Hw112UserHowlerTestOprrEntry
    MAX-ACCESS  not-accessible
    STATUS      current
    DESCRIPTION
       "Operation table for the howler tone test on 112 analog subscriber phones:
      It realizes the function of the howler tone test on the subscriber phones in the system. This test helps check whether a subscriber phone can play the howler tone normally.
      The index of this entry is ifIndex"
    INDEX    {  
              ifIndex
             }
    ::= { hw112UserHowlerTestOprrTable 1 }

  Hw112UserHowlerTestOprrEntry ::=
    SEQUENCE
    {
      hw112UserHowlerTestOprType    INTEGER,
      hw112UserHowlerTestTime       Integer32,
      hw112UserHowlerTestResult     INTEGER
    }

  hw112UserHowlerTestOprType OBJECT-TYPE
    SYNTAX      INTEGER{stop(1),start(2)}
    MAX-ACCESS  read-create
    STATUS      current
    DESCRIPTION
        "Operation type .
         Options: 
         1. stop(1)  -stop the test 
         2. start(2) -start the test 
         Note:The 112 protocol does not define the stop command.
        "
    ::= { hw112UserHowlerTestOprrEntry 1 }

  hw112UserHowlerTestTime OBJECT-TYPE
    SYNTAX      Integer32(3..180)
    MAX-ACCESS  read-create
    STATUS      current
    DESCRIPTION
        "Howler tone length. 
         Unit: second
        "
    ::= { hw112UserHowlerTestOprrEntry 2 }

  hw112UserHowlerTestResult OBJECT-TYPE
    SYNTAX      INTEGER{offhook(1),onhook(2)}
    MAX-ACCESS  read-only
    STATUS      current
    DESCRIPTION
        "Operation result.
         Options: 
         1. offhook(1)  -indicates off hook 
         2. onhook(2)   -indicates on hook
         The 112 protocol defines only two test results."
    ::= { hw112UserHowlerTestOprrEntry 3 }

  hw112IsdnDiagnoseTestOprTable OBJECT-TYPE
    SYNTAX      SEQUENCE OF Hw112IsdnDiagnoseTestOprEntry
    MAX-ACCESS  not-accessible
    STATUS      current
    DESCRIPTION
      "Operation table for the diagnosis test on the 112 ISDN subscribers:
      It realizes the function of the diagnosis test on the 112 ISDN subscribers in the system. Its test items are the same as the test items of the circuit test on the PSTN subscribers.
      The index of this table is ifIndex"
    ::= { hwNTestMIBObjects 9 }

  hw112IsdnDiagnoseTestOprEntry OBJECT-TYPE
    SYNTAX      Hw112IsdnDiagnoseTestOprEntry
    MAX-ACCESS  not-accessible
    STATUS      current
    DESCRIPTION
      "Operation table for the diagnosis test on the 112 ISDN subscribers:
      It realizes the function of the diagnosis test on the 112 ISDN subscribers in the system. Its test items are the same as the test items of the circuit test on the PSTN subscribers.
      The index of this entry is ifIndex"
    INDEX    {  
              ifIndex
             }
    ::= { hw112IsdnDiagnoseTestOprTable 1 }

  Hw112IsdnDiagnoseTestOprEntry ::=
    SEQUENCE
    {
      hw112IsdnDiagnoseTestOprType          INTEGER,
      hw112IsdnDiagnoseTestLoopType         INTEGER,
      hw112IsdnDiagnoseTestLoopChannel      INTEGER,
      hw112IsdnDiagnoseTestResult           INTEGER,
      hw112IsdnDiagnoseTestLoopTime         Integer32,
      hw112IsdnDiagnoseTestLoopDirection    INTEGER ,
      hw112IsdnDiagnoseTestLoopTs           Integer32,
      hw112IsdnDiagnoseTestDeferredTestFlag INTEGER,
      hw112IsdnDiagnoseTestDeferredTime     Integer32,
      hw112IsdnDiagnoseTestTimeoutProc      INTEGER,
      hw112IsdnDiagnoseTestIfIndex          Integer32,
      hw112IsdnDiagnoseTestRequestID        Integer32
    }

  hw112IsdnDiagnoseTestOprType OBJECT-TYPE
    SYNTAX      INTEGER{start(1),stop(2)}
    MAX-ACCESS  read-create
    STATUS      current
    DESCRIPTION
        "Operation type .
         Options: 
         1. start(1)  -start the test 
         2. stop(2) -stop the test 
         Note:The 112 protocol does not define the stop command.
        "
    ::= { hw112IsdnDiagnoseTestOprEntry 1 }

  hw112IsdnDiagnoseTestLoopType OBJECT-TYPE
    SYNTAX      INTEGER{nt1(1),ltet(2)}
    MAX-ACCESS  read-create
    STATUS      current
    DESCRIPTION
        "Loopback type.
         Options:
         1. nt1(1)  -indicates NT1 
         2. ltet(2) -indicates LT/ET
        "
    ::= { hw112IsdnDiagnoseTestOprEntry 2 }

  hw112IsdnDiagnoseTestLoopChannel OBJECT-TYPE
    SYNTAX      INTEGER{bOne(1),bTwo(2),twoBAndD(3),pra(4)}
    MAX-ACCESS  read-create
    STATUS      current
    DESCRIPTION
        "Loopback .
         Options:
         1. bOne(1)      -indicates B1 
         2. bTwo(2)      -indicates B2
         3. twoBAndD(3)  -indicates 2B+D 
         4. pra(4)       -indicates PRA
        "
    ::= { hw112IsdnDiagnoseTestOprEntry 3 }

  hw112IsdnDiagnoseTestResult OBJECT-TYPE
    SYNTAX      INTEGER{success(1),failure(2),timeoutsuccess(3),exceptionstop(4),testcanceled(5)}
    MAX-ACCESS  read-only
    STATUS      current
    DESCRIPTION
        "Operation result. 
         Options:
           1. success(1)        -indicates loopback success, and user stop the test manually; 
           2. failure(2)        -indicates loopback failure;
           3. timeoutsuccess(3) -indicates loopback success, and loop time out.
           4. exceptionstop(4)  -indicates exception occur;
           5. testcanceled(5)   -indicates loopback test is not performed, and test is canceled by user or deferred time out"
    ::= { hw112IsdnDiagnoseTestOprEntry 4 }
 

  hw112IsdnDiagnoseTestLoopTime OBJECT-TYPE
    SYNTAX      Integer32(1..1440)
    MAX-ACCESS  read-create
    STATUS      current
    DESCRIPTION
        "
        Loop time. 
        Unit: minute
        "
    DEFVAL { 15 }
    ::= { hw112IsdnDiagnoseTestOprEntry 5 }

  hw112IsdnDiagnoseTestLoopDirection OBJECT-TYPE
    SYNTAX      INTEGER{nearloop(1),farloop(2)}
    MAX-ACCESS  read-create
    STATUS      current
    DESCRIPTION
        "
        Loop direction. 
        Options:
          1. nearloop(1)        -indicates loop direction is near loop 
          2. farloop(2)         -indicates loop direction is far loop
        "
    ::= { hw112IsdnDiagnoseTestOprEntry 6 }
    
  hw112IsdnDiagnoseTestLoopTs OBJECT-TYPE
    SYNTAX      Integer32(0..31)
    MAX-ACCESS  read-create
    STATUS      current
    DESCRIPTION
        "
        Time slot to be looped back
        "
    ::= { hw112IsdnDiagnoseTestOprEntry 7 }


  hw112IsdnDiagnoseTestDeferredTestFlag OBJECT-TYPE
    SYNTAX      INTEGER{immediatetest(1),deferredtest(2)}
    MAX-ACCESS  read-create
    STATUS      current
    DESCRIPTION
        "
        deferred test flag: 
        Options:
          1. immediatetest(1) -immediate test; 
          2. deferredtest(2)  -indicates deferred test: Initiated when the port is in service. If the port is busy, the test operation 
                              will be deferred. If the port changes to idle state before time out, the test will be executed 
                              immediately. If the port keeps busy by the time out, the system will excecute a corresponding 
                              operation according to what the user specified: canceling the test or forcing to test.
                              If the value of this leaf node is deferredtest(2), both hw112IsdnDiagnoseTestDeferredTime and 
                              hw112IsdnDiagnoseTestTimeoutProc must be set.
        Default:  immediatetest(1).
        "
    DEFVAL { 1 }
    ::= { hw112IsdnDiagnoseTestOprEntry 8 }
    
  hw112IsdnDiagnoseTestDeferredTime OBJECT-TYPE
    SYNTAX      Integer32(1..1440)
    MAX-ACCESS  read-create
    STATUS      current
    DESCRIPTION
        "
        Deferred time(unit: minute):
          this leaf node is valid only when the value of hw112IsdnDiagnoseTestDeferredTestFlag is deferredtest(2).
        Default:  30(minute).
        "
    DEFVAL { 30 }
    ::= { hw112IsdnDiagnoseTestOprEntry 9 }
    
  hw112IsdnDiagnoseTestTimeoutProc OBJECT-TYPE
    SYNTAX      INTEGER{notest(1),test(2)}
    MAX-ACCESS  read-create
    STATUS      current
    DESCRIPTION
        "
        Options: 
         1. notest(1) -no test is applied
         2. test(2)   -a test is applied 
        Timeout proc: 
           1-when deferred time out, if the port is still in service, test will be canceled; 
           2-when deferred time out, if the port is still in service, test will be preformed by force.
        this leaf node is valid only when the value of hw112IsdnDiagnoseTestDeferredTestFlag is deferredtest(2).
        Default: notest(1).
        "
    DEFVAL { 1 }
    ::= { hw112IsdnDiagnoseTestOprEntry 10 }

  hw112IsdnDiagnoseTestIfIndex OBJECT-TYPE
    SYNTAX Integer32
    MAX-ACCESS read-only
    STATUS      current
    DESCRIPTION
        "
        Port IfIndex
        "
    ::= { hw112IsdnDiagnoseTestOprEntry 11 }
    
  hw112IsdnDiagnoseTestRequestID OBJECT-TYPE
    SYNTAX Integer32
    MAX-ACCESS read-only
    STATUS      current
    DESCRIPTION
        "
        Request ID
        "
    ::= { hw112IsdnDiagnoseTestOprEntry 12 }

  hwPstnCallerEmulateOprTable OBJECT-TYPE
    SYNTAX      SEQUENCE OF HwPstnCallerEmulateOprEntry
    MAX-ACCESS  not-accessible
    STATUS      current
    DESCRIPTION
      "Operation table for the PSTN call emulation test (calling party):
      It realizes the function of the call emulation test (caller dial) in the system. This test helps check whether a subscriber port can make calls normally as a calling party.
      The index of this table is ifIndex."
    ::= { hwNTestMIBObjects 10 }

  hwPstnCallerEmulateOprEntry OBJECT-TYPE
    SYNTAX      HwPstnCallerEmulateOprEntry
    MAX-ACCESS  not-accessible
    STATUS      current
    DESCRIPTION
      "Operation table for the PSTN call emulation test (calling party):
      It realizes the function of the call emulation test (caller dial) in the system. This test helps check whether a subscriber port can make calls normally as a calling party.
      The index of this entry is ifIndex."
    INDEX    {  
              ifIndex
             }
    ::= { hwPstnCallerEmulateOprTable 1 }

  HwPstnCallerEmulateOprEntry ::=
    SEQUENCE
    {
      hwPstnCallerEmulateOprType            INTEGER,
      hwPstnCallerEmulateCalledTelNo        OCTET STRING,
      hwPstnCallerEmulateDialMode           INTEGER,
      hwPstnCallerEmulateTestStatus         INTEGER,
      hwPstnCallerEmulateTestResult         INTEGER,
      hwPstnCallerEmulateTestDTMFDetected   OCTET STRING,
      hwPstnCallerEmulateTestHoldTime       Unsigned32,
      hwPstnCallerEmulateReportNumber       OCTET STRING,
      hwPstnCallerEmulateLocalErrorCode     Unsigned32,
      hwPstnCallerEmulateRemoteErrorCode    Unsigned32,
      hwPstnCallerEmulateTestRequestID      Unsigned32,
      hwPstnCallerEmulateTestFailReason     Unsigned32
    }

  hwPstnCallerEmulateOprType OBJECT-TYPE
    SYNTAX      INTEGER{stop(1),start(2),offHookConfirm(3), sendDTMF(4)}
    MAX-ACCESS  read-create
    STATUS      current
    DESCRIPTION
        "Operation type. 
         Options:
         1: stop(1)           -indicates Stop test
         2: start(2)          -indicates Start test
         3: offHookConfirm(3) -indicates Off hook confirmation
         4: sendDTMF(4)       -indicates Send DTMF
        "
    ::= { hwPstnCallerEmulateOprEntry 1 }

  hwPstnCallerEmulateCalledTelNo OBJECT-TYPE
    SYNTAX      OCTET STRING(SIZE(32))
    MAX-ACCESS  read-create
    STATUS      current
    DESCRIPTION
        "Called telephone number (max length: 32)"
    ::= { hwPstnCallerEmulateOprEntry 2 }

  hwPstnCallerEmulateDialMode OBJECT-TYPE
    SYNTAX      INTEGER{dtmf(1), pulse(2)}
    MAX-ACCESS  read-create
    STATUS      current
    DESCRIPTION
        "Dial type (Enumerated type.) 
         Options:
         1. dtmf(1)     -indicates the dial mode is DTMF
         2. pulse(2)    -indicates the dial mode is pulse
        "
    ::= { hwPstnCallerEmulateOprEntry 3 }

  hwPstnCallerEmulateTestStatus OBJECT-TYPE
    SYNTAX      INTEGER{startSuccessfully(1),stopSuccessfully(2), sendDTMFSuccessfully(3), testOuttime(4), noDialtone(5), callerDialNumberAlready(6), noRinging(7), noRingbackTone(8), waitingAgentMessageOuttime(9), testingFailure(10), agentMessageAck(11),calledoffhook(12),testingAbnormal(13),broadbandtesting(14),capturefail(15),notratb(16),configsuccessfully(17), ring(18), calleroffhook(19),  playdialtone(20), receiving(21), dialnumbercomplete(22), ringingbacktone(23), talking(24), testfinished(28)}
    MAX-ACCESS  read-only
    STATUS      current
    DESCRIPTION
        "Test Status. 
         Options:
         1. startSuccessfully(1)          -indicates start successfully
         2. stopSuccessfully(2)           -indicates stop successfully
         3. sendDTMFSuccessfully(3)       -indicates send DTMF successfully
         4. testOuttime(4)                -indicates timed-out;
         5. noDialtone(5)                 -indicates no dial tone
         6. callerDialNumberAlready(6)    -indicates caller already dials a number
         7. noRinging(7)                  -indicates no ringing
         8. noRingbackTone(8)             -indicates no ring-back tone 
         9. waitingAgentMessageOuttime(9) -indicates timed-out (waiting for EMS processing)
         10.testingFailure(10)            -indicates test failure
         11.agentMessageAck(11)           -indicates host responds to the EMS
         12.calledoffhook(12)             -indicates off hook (called party)
         13.testingAbnormal(13)           -indicates test abnormal;
         14.broadbandtesting(14)          -indicates broadband testing
         15.capturefail(15)               -indicates line capture failure
         16.notratb(16)                   -indicates relay transfer board does not exist
         17.configsuccessfully(17)        -indicates configured successfully
         18.ring(18)                      -indicates ringing
         19.calleroffhook(19)             -indicates off hook (calling party)
         20.playdialtone(20)              -indicates play the dial tone
         21.receiving(21)                 -indicates receiving
         22.dialnumbercomplete(22)        -indicates dialup is finished
         23.ringingbacktone(23)           -indicates ringing back tone
         24.talking(24)                   -indicates talking
         25.testfinished(28)              -indicates the test is over
        "
    ::= { hwPstnCallerEmulateOprEntry 4 }
    
  hwPstnCallerEmulateTestResult OBJECT-TYPE
    SYNTAX      INTEGER{callerNoDialTone(1), callerOffHookingBusy(2), callerDialingBusy(3), callerNoDial(4), callerDialedBusy(5), callerDialedNoTalk(6), callRelease(7), matchNoCompleted(8), sendNoCompleted(9), testSucceed(10), callerMatchFailed(11), callerPortAbnormal(12)}
    MAX-ACCESS  read-only
    STATUS      current
    DESCRIPTION
        "Emulational Caller Test Result
         Options:
         1. callerNoDialTone(1)          -indicates the caller does not have dial tone
         2. callerOffHookingBusy(2)      -indicates the caller is busy in off-hooking 
         3. callerDialingBusy(3)         -indicates the caller is busy in dialing
         4. callerNoDial(4)              -indicates the caller does not dial
         5. callerDialedBusy(5)          -indicates the caller is busy in dialed
         6. callerDialedNoTalk(6)        -indicates the caller has already dialed but has not connected
         7. callRelease(7)               -indicates the call is released
         8. matchNoCompleted(8)          -indicates the match is not completed 
         9. sendNoCompleted(9)           -indicates the sending is not completed
         10.testSucceed(10)              -indicates the test succeed
         11.callerMatchFailed(11)        -indicates the caller match failed
         12.callerPortAbnormal(12)       -indicates the caller's port is abnormal
        "
    ::= { hwPstnCallerEmulateOprEntry 5 }
    
  hwPstnCallerEmulateTestDTMFDetected OBJECT-TYPE
    SYNTAX      OCTET STRING(SIZE(64))
    MAX-ACCESS  read-only
    STATUS      current
    DESCRIPTION
        "Detected Dtmf Num List"
    ::= { hwPstnCallerEmulateOprEntry 6 }
    
  hwPstnCallerEmulateTestHoldTime OBJECT-TYPE
    SYNTAX      Unsigned32(5..600)
    MAX-ACCESS   read-create
    STATUS      current
    DESCRIPTION
        "
        Caller Emulate test hold time, the test will auto ended when this time out.
        "
    DEFVAL {4294967295}
    ::= { hwPstnCallerEmulateOprEntry 7 }
    
  hwPstnCallerEmulateReportNumber OBJECT-TYPE
    SYNTAX      OCTET STRING(SIZE(32))
    MAX-ACCESS  read-only
    STATUS      current
    DESCRIPTION
        "The actual called number string checked and send to MGC or IMS."
    ::= { hwPstnCallerEmulateOprEntry 8 }
    
  hwPstnCallerEmulateLocalErrorCode OBJECT-TYPE
    SYNTAX      Unsigned32
    MAX-ACCESS  read-only
    STATUS      current
    DESCRIPTION
        "Error code send by Local side."
    ::= { hwPstnCallerEmulateOprEntry 9 }
    
  hwPstnCallerEmulateRemoteErrorCode OBJECT-TYPE
    SYNTAX      Unsigned32
    MAX-ACCESS  read-only
    STATUS      current
    DESCRIPTION
        "Error code received from remote side."
    ::= { hwPstnCallerEmulateOprEntry 10 }
    
  hwPstnCallerEmulateTestRequestID OBJECT-TYPE
    SYNTAX      Unsigned32
    MAX-ACCESS  read-only
    STATUS      current
    DESCRIPTION
        "Request ID"
    ::= { hwPstnCallerEmulateOprEntry 11 }
    
  hwPstnCallerEmulateTestFailReason OBJECT-TYPE
    SYNTAX      Unsigned32
    MAX-ACCESS  read-only
    STATUS      current
    DESCRIPTION
        "Emulational caller test fail reasons.
         Options:
        1.noreason(0)                           -indicates no reason, means normal                                                                                                                                                                                                                                                          
        2.otherproblem(1)                       -indicates other problem:other reason                                                                                                                                                                                                                               
        3.interfaceclose(65536)                 -indicates The config of AG is abnormal:interface is closed                                                                                                                                                                                                             
        4.theSALnodigimap(65537)                -indicates The config of AG is abnormal:SAL service has no digimap                                                                                                                                                                                                      
        5.emergencycallnodigimap(65538)         -indicates The config of AG is abnormal:emergency call has no digimap                                                                                                                                                                                                   
        6.novaliddigimapSIP(65539)              -indicates The config of AG is abnormal:no valid digimap(SIP)                                                                                                                                                                                                       
        7.noSALservice(65540)                   -indicates The config of AG is abnormal:no SAL service                                                                                                                                                                                                                  
        8.portloop(69632)                       -indicates The config of AG is abnormal:port is loop                                                                                                                                                                                                                    
        9.portprohibited(69633)                 -indicates The config of AG is abnormal:port is prohibited                                                                                                                                                                                                              
        10.usertypeerror(73728)                 -indicates The config of AG is abnormal:type of user is error                                                                                                                                                                                                           
        11.localendservice(73729)               -indicates The config of AG is abnormal:local party ends service                                                                                                                                                                                                        
        12.portnouser(73730)                    -indicates The config of AG is abnormal:port has no user                                                                                                                                                                                                                
        13.notelnum(73731)                      -indicates The config of AG is abnormal:no telephone number                                                                                                                                                                                                             
        14.localnocalledtelnum(73732)           -indicates The config of AG is abnormal:local party has no called telephone number                                                                                                                                                                                                     
        15.deluserendservice(73733)             -indicates The config of AG is abnormal:end service by deleting user                                                                                                                                                                                                    
        16.teststop(77824)                      -indicates The config of AG is abnormal:emulational test is stoped                                                                                                                                                                                                      
        17.userLicnotenough(77825)              -indicates The config of AG is abnormal:user License is not enough                                                                                                                                                                                                      
        18.theASLLicnotenough(77826)            -indicates The config of AG is abnormal:ASL License is not enough                                                                                                                                                                                                               
        19.calledpartynotexist(77827)           -indicates The config of AG is abnormal:called party is not exist                                                                                                                                                                                                                   
        20.calledpartynoestmismatchdmap(77828)  -indicates The config of AG is abnormal:called party is not exist or mismatch the digital map                                                                                                                                                                                                                  
        21.otherreasonAGconfigabnormal(131071)  -indicates The config of AG is abnormal:other reason                                                                                                                                                                                                                                
        22.userremoteblock(131072)              -indicates The state of AG is abnormal:user port is remote block                                                                                                                                                                                                            
        23.userremoteunblock(131073)            -indicates The state of AG is abnormal:user port is remote unblock                                                                                                                                                                                                          
        24.userendservieauto(131074)            -indicates The state of AG is abnormal:user ends servie automatically                                                                                                                                                                                                       
        25.useroffhook(131075)                  -indicates The state of AG is abnormal:user is offhook                                                                                                                                                                                                                  
        26.useroffhookPowerDailer(131076)       -indicates The state of AG is abnormal:user offhook PowerDailer                                                                                                                                                                                                                 
        27.userringing(131077)                  -indicates The state of AG is abnormal:user is ringing                                                                                                                                                                                                                      
        28.userlocke(131078)                    -indicates The state of AG is abnormal:user is locked                                                                                                                                                                                                                       
        29.useroutofservice(131079)             -indicates The state of AG is abnormal:user is out of service                                                                                                                                                                                                               
        30.userregisterexpire(131080)           -indicates The state of AG is abnormal:user's register time is expired                                                                                                                                                                                                      
        31.calledpartybusy(131081)              -indicates The state of AG is abnormal:called party is busy                                                                                                                                                                                                                 
        32.vaginterfacefault(135168)            -indicates The state of AG is abnormal:VAG interface is fault                                                                                                                                                                                                               
        33.bandoverload(135169)                 -indicates The state of AG is abnormal:the band is overloaded                                                                                                                                                                                                                   
        34.mgcoverloade(135170)                 -indicates The state of AG is abnormal:MGC is overloaded                                                                                                                                                                                                                    
        35.mgoverload(135171)                   -indicates The state of AG is abnormal:MG is overloaded                                                                                                                                                                                                                     
        36.poweroverload(139264)                -indicates The state of AG is abnormal:the power is overloaded                                                                                                                                                                                                                  
        37.innerresourceabnormal(139265)        -indicates The state of AG is abnormal:inner resource is abnormal                                                                                                                                                                                                           
        38.normalservicebrokenSAL(139266)       -indicates The state of AG is abnormal:SAL is broken by normal service                                                                                                                                                                                                      
        39.DSPfault(139267)                     -indicates The state of AG is abnormal:DSP is fault                                                                                                                                                                                                                         
        40.DSPresourcelack(139268)              -indicates The state of AG is abnormal:DSP's resource is not enough                                                                                                                                                                                                         
        41.mainbackupswitching(139269)          -indicates The state of AG is abnormal:main and backup board is switchi                                                                                                                                                                                                         
        42.portpowerdown(143360)                -indicates The state of AG is abnormal:port is power down                                                                                                                                                                                                               
        43.portnotexist(143361)                 -indicates The state of AG is abnormal:port is not exist                                                                                                                                                                                                                    
        44.porttesting(143362)                  -indicates The state of AG is abnormal:port is testing                                                                                                                                                                                                                              
        45.portfault(143363)                    -indicates The state of AG is abnormal:port is fault                                                                                                                                                                                                                                
        46.portoffhookPowerDailer(143364)       -indicates The state of AG is abnormal:port offhook PowerDailer                                                                                                                                                                                                                 
        47.portoffhookfailed(143365)            -indicates The state of AG is abnormal:port offhook failed                                                                                                                                                                                                                          
        48.agdialingunfinish(143366)            -indicates The state of AG is abnormal:AG's dialing is unfinished                                                                                                                                                                                                               
        49.otherreasonAGstateabnormal(196607)   -indicates The state of AG is abnormal:other reason                                                                                                                                                                                                                             
        50.localrefusecall(196608)              -indicates The interaction of signaling is abnormal:loacl party refuse                                                                                                                                                                                                      
        51.serviceflowabnormal(196609)          -indicates The interaction of signaling is abnormal:service flow is abn                                                                                                                                                                                                         
        52.remoterefusecall(200704)             -indicates The interaction of signaling is abnormal:remote party refuse                                                                                                                                                                                                     
        53.localnotsupport(204800)              -indicates The interaction of signaling is abnormal:local party dose no                                                                                                                                                                                                     
        54.remoteRTPmodeabnormal(208896)        -indicates The interaction of signaling is abnormal:RTP mode appointed by remote party is abnormal
        55.sdpnegotiatefail(208897)             -indicates The interaction of signaling is abnormal:SDP negotiate failed
        56.mgccontextmismatch(208898)           -indicates The interaction of signaling is abnormal:MGC's context is mismatch
        57.MGCnotcheckevent(208899)             -indicates The interaction of signaling is abnormal:MGC dose not appoint to check events
        58.novaliddigimapH248MGCP(208900)       -indicates The interaction of signaling is abnormal:no valid digimap(H248/MGCP)
        59.remotewrongrespond(208901)           -indicates The interaction of signaling is abnormal:the other party dose not respond correctly after dialing
        60.remotewrongrespondsignaling(208902)  -indicates The interaction of signaling is abnormal:the other party does not respond the signaling correctly 
        61.notstarttalk(208903)                 -indicates The interaction of signaling is abnormal:have not started talking
        62.notappointring(208904)               -indicates The interaction of signaling is abnormal:dose not appoint to ring
        63.remotenotcalllocal(208905)           -indicates The interaction of signaling is abnormal:remote party does not call local remote
        64.remoterealsecall(208906)             -indicates The interaction of signaling is abnormal:remote party realse the call
        65.remoterefusecallbt(208907)           -indicates The interaction of signaling is abnormal:remote party refuse call by busy tone
        66.unexpectedsignaling(208908)          -indicates The interaction of signaling is abnormal:unexpected signaling
        67.otherreasonsignalabnormal(262143)    -indicates The interaction of signaling is abnormal:other reason                                                                                                                                                                                                             
        "
    ::= { hwPstnCallerEmulateOprEntry 12 }
    
  hwPstnCalledEmulateOprTable OBJECT-TYPE
    SYNTAX      SEQUENCE OF HwPstnCalledEmulateOprEntry
    MAX-ACCESS  not-accessible
    STATUS      current
    DESCRIPTION
      "The operation table of the caller test of the PSTN call emulation test. It is used to realize the caller 
      test of the PSTN call emulation test, which is used to test whether a user of a port functioned as the 
      caller can make a call.      
      Operation table for the PSTN call emulation test (called party):
      It realizes the function of the call emulation test (called party) in the system. This test helps check whether a subscriber port can make calls normally as a called party.
      The index of this table is ifIndex"
    ::= { hwNTestMIBObjects 11 }

  hwPstnCalledEmulateOprEntry OBJECT-TYPE
    SYNTAX      HwPstnCalledEmulateOprEntry
    MAX-ACCESS  not-accessible
    STATUS      current
    DESCRIPTION
      "The operation table of the caller test of the PSTN call emulation test. It is used to realize the caller 
      test of the PSTN call emulation test, which is used to test whether a user of a port functioned as the 
      caller can make a call.      
      Operation table for the PSTN call emulation test (called party):
      It realizes the function of the call emulation test (called party) in the system. This test helps check whether a subscriber port can make calls normally as a called party.
      The index of this entry is ifIndex"
    INDEX    {  
              ifIndex
             }
    ::= { hwPstnCalledEmulateOprTable 1 }

  HwPstnCalledEmulateOprEntry ::=
    SEQUENCE
    {
      hwPstnCalledEmulateOprType            INTEGER,
      hwPstnCalledEmulateTestStatus         INTEGER,
      hwPstnCalledEmulateTestResult         INTEGER,
      hwPstnCalledEmulateTestDTMFDetected   OCTET STRING,
      hwPstnCalledEmulateTestWaitTime       Unsigned32,
      hwPstnCalledEmulateTestHoldTime       Unsigned32,
      hwPstnCalledEmulateLocalErrorCode     Unsigned32,
      hwPstnCalledEmulateRemoteErrorCode    Unsigned32,
      hwPstnCalledEmulateTestRequestID      Unsigned32,
      hwPstnCalledEmulateTestFailReason     Unsigned32
    }

  hwPstnCalledEmulateOprType OBJECT-TYPE
    SYNTAX      INTEGER{stop(1),start(2), dialConfirm(3), sendDTMF(4), config(5)}
    MAX-ACCESS  read-create
    STATUS      current
    DESCRIPTION
        "Operation type. 
         Options:
         1. stop(1)         -indicates Stop test 
         2. start(2)        -indicates Start test 
         3. dialConfirm(3)  -indicates Dial number confirmation 
         4. sendDTMF(4)     -indicates Send DTMF 
         5. config(5)       -indicates Configuration test
        "                     
    ::= { hwPstnCalledEmulateOprEntry 1 }

  hwPstnCalledEmulateTestStatus OBJECT-TYPE
    SYNTAX      INTEGER{startSuccessfully(1),stopSuccessfully(2), sendDTMFSuccessfully(3), testOuttime(4), noDialtone(5), callerDialNumberAlready(6),noRinging(7), noRingbackTone(8), waitingAgentMessageOuttime(9), testingFailure(10), agentMessageAck(11),calledoffhook(12),testingAbnormal(13),broadbandtesting(14),capturefail(15),notratb(16),configsuccessfully(17),ring(18),calleroffhook(19),playdialtone(20),dialnumbercomplete(21), testfinished(23)}
    MAX-ACCESS  read-only
    STATUS      current
    DESCRIPTION 
        "Test Status.
         Options:
         1. startSuccessfully(1)         -indicates start successfully
         2. stopSuccessfully(2)          -indicates stop successfully
         3. sendDTMFSuccessfully(3)      -indicates send DTMF successfully
         4. testOuttime(4)               -indicates timed-out;
         5. noDialtone(5)                -indicates no dial tone
         6. callerDialNumberAlready(6)   -indicates caller already dials a number
         7. noRinging(7)                 -indicates no ringing
         8. noRingbackTone(8)            -indicates no ring-back tone;
         9. waitingAgentMessageOuttime(9)-indicates timed-out (waiting for EMS processing)
         10.testingFailure(10)           -indicates test failure
         11.agentMessageAck(11)          -indicates host responds to the EMS
         12.calledoffhook(12)            -indicates off hook (called party)
         13.testingAbnormal(13)          -indicates test abnormal;
         14.broadbandtesting(14)         -indicates broadband testing
         15.capturefail(15)              -indicates line capture failure
         16.notratb(16)                  -indicates transfer board does not exist
         17.configsuccessfully(17)       -indicates configured successfully
         18.ring(18)                     -indicates ringing
         19.calleroffhook(19)            -indicates off hook (calling party)
         20.playdialtone(20)             -indicates play the dial tone
         21.dialnumbercomplete(21)       -indicates dialup is finished
         22.testfinished(23)             -indicates the test is over
        "
    ::= { hwPstnCalledEmulateOprEntry 2 }

  hwPstnCalledEmulateTestResult OBJECT-TYPE
    SYNTAX      INTEGER{calledNoRing(1), calledNoOffHook(2), calledOffHookingBusy(3), calledNoTalk(4), callRelease(5), matchNoCompleted(6), sendNoCompleted(7), testSucceed(8), calledMatchFailed(9), calledPortAbnormal(10)}
    MAX-ACCESS  read-only
    STATUS      current
    DESCRIPTION 
        "Emulational Called Test Result
         Options:
         1. calledNoRing(1)             -indicates the called user dose not ring
         2. calledNoOffHook(2)          -indicates the called user dose not off hook
         3. calledOffHookingBusy(3)     -indicates the called user is busy in off-hooking
         4. calledNoTalk(4)             -indicates the called user does not connect
         5. callRelease(5)              -indicates the call is released
         6. matchNoCompleted(6)         -indicates the match is not completed
         7. sendNoCompleted(7)          -indicates the sending is not completed
         8. testSucceed(8)              -indicates the test succeed
         9. calledMatchFailed(9)        -indicates the called user match failed
         10.calledPortAbnormal(10)      -indicates the called port is abnormal
        "
    ::= { hwPstnCalledEmulateOprEntry 3 }
    
  hwPstnCalledEmulateTestDTMFDetected OBJECT-TYPE
    SYNTAX      OCTET STRING(SIZE(64))
    MAX-ACCESS  read-only
    STATUS      current
    DESCRIPTION 
        "Detected Dtmf Num List"
    ::= { hwPstnCalledEmulateOprEntry 4 }
    
  hwPstnCalledEmulateTestWaitTime OBJECT-TYPE    
    SYNTAX      Unsigned32(5..600)
    MAX-ACCESS   read-create
    STATUS      current
    DESCRIPTION
        "
        Called Emulate test waiting time, the test will auto failed when this time out and called port not received ring.
        "
    DEFVAL {4294967295}
    ::= { hwPstnCalledEmulateOprEntry 5 }


   hwPstnCalledEmulateTestHoldTime OBJECT-TYPE    
    SYNTAX      Unsigned32(5..600)
    MAX-ACCESS   read-create
    STATUS      current
    DESCRIPTION
        "
        Called Emulate test hold time, the test will auto ended when this time out.
        "
        DEFVAL  {4294967295}
    ::= { hwPstnCalledEmulateOprEntry 6 }
    
  hwPstnCalledEmulateLocalErrorCode OBJECT-TYPE    
    SYNTAX      Unsigned32
    MAX-ACCESS   read-only
    STATUS      current
    DESCRIPTION
        "Error code send by Local side."
    ::= { hwPstnCalledEmulateOprEntry 7}
    
  hwPstnCalledEmulateRemoteErrorCode OBJECT-TYPE    
    SYNTAX      Unsigned32
    MAX-ACCESS  read-only
    STATUS      current
    DESCRIPTION
        "
        Error code received from remote side.
        "
    ::= { hwPstnCalledEmulateOprEntry 8 }       
    
  hwPstnCalledEmulateTestRequestID OBJECT-TYPE    
    SYNTAX      Unsigned32
    MAX-ACCESS  read-only
    STATUS      current
    DESCRIPTION
        "Request ID"
    ::= { hwPstnCalledEmulateOprEntry 9 }       
    
    
  hwPstnCalledEmulateTestFailReason OBJECT-TYPE
    SYNTAX      Unsigned32
    MAX-ACCESS  read-only
    STATUS      current
    DESCRIPTION
        "Emulational called test fail reasons.
         Options:
        1.noreason(0)                           -indicates no reason, means normal                                                                                                                                                                                                                                                          
        2.otherproblem(1)                       -indicates other problem:other reason                                                                                                                                                                                                                               
        3.interfaceclose(65536)                 -indicates The config of AG is abnormal:interface is closed                                                                                                                                                                                                             
        4.theSALnodigimap(65537)                -indicates The config of AG is abnormal:SAL service has no digimap                                                                                                                                                                                                      
        5.emergencycallnodigimap(65538)         -indicates The config of AG is abnormal:emergency call has no digimap                                                                                                                                                                                                   
        6.novaliddigimapSIP(65539)              -indicates The config of AG is abnormal:no valid digimap(SIP)                                                                                                                                                                                                       
        7.noSALservice(65540)                   -indicates The config of AG is abnormal:no SAL service                                                                                                                                                                                                                  
        8.portloop(69632)                       -indicates The config of AG is abnormal:port is loop                                                                                                                                                                                                                    
        9.portprohibited(69633)                 -indicates The config of AG is abnormal:port is prohibited                                                                                                                                                                                                              
        10.usertypeerror(73728)                 -indicates The config of AG is abnormal:type of user is error                                                                                                                                                                                                           
        11.localendservice(73729)               -indicates The config of AG is abnormal:local party ends service                                                                                                                                                                                                        
        12.portnouser(73730)                    -indicates The config of AG is abnormal:port has no user                                                                                                                                                                                                                
        13.notelnum(73731)                      -indicates The config of AG is abnormal:no telephone number                                                                                                                                                                                                             
        14.localnocalledtelnum(73732)           -indicates The config of AG is abnormal:local party has no called telephone number                                                                                                                                                                                                     
        15.deluserendservice(73733)             -indicates The config of AG is abnormal:end service by deleting user                                                                                                                                                                                                    
        16.teststop(77824)                      -indicates The config of AG is abnormal:emulational test is stoped                                                                                                                                                                                                      
        17.userLicnotenough(77825)              -indicates The config of AG is abnormal:user License is not enough                                                                                                                                                                                                      
        18.theASLLicnotenough(77826)            -indicates The config of AG is abnormal:ASL License is not enough                                                                                                                                                                                                               
        19.calledpartynotexist(77827)           -indicates The config of AG is abnormal:called party is not exist                                                                                                                                                                                                                   
        20.calledpartynoestmismatchdmap(77828)  -indicates The config of AG is abnormal:called party is not exist or mismatch the digital map                                                                                                                                                                                                                  
        21.otherreasonAGconfigabnormal(131071)  -indicates The config of AG is abnormal:other reason                                                                                                                                                                                                                                
        22.userremoteblock(131072)              -indicates The state of AG is abnormal:user port is remote block                                                                                                                                                                                                            
        23.userremoteunblock(131073)            -indicates The state of AG is abnormal:user port is remote unblock                                                                                                                                                                                                          
        24.userendservieauto(131074)            -indicates The state of AG is abnormal:user ends servie automatically                                                                                                                                                                                                       
        25.useroffhook(131075)                  -indicates The state of AG is abnormal:user is offhook                                                                                                                                                                                                                  
        26.useroffhookPowerDailer(131076)       -indicates The state of AG is abnormal:user offhook PowerDailer                                                                                                                                                                                                                 
        27.userringing(131077)                  -indicates The state of AG is abnormal:user is ringing                                                                                                                                                                                                                      
        28.userlocke(131078)                    -indicates The state of AG is abnormal:user is locked                                                                                                                                                                                                                       
        29.useroutofservice(131079)             -indicates The state of AG is abnormal:user is out of service                                                                                                                                                                                                               
        30.userregisterexpire(131080)           -indicates The state of AG is abnormal:user's register time is expired                                                                                                                                                                                                      
        31.calledpartybusy(131081)              -indicates The state of AG is abnormal:called party is busy                                                                                                                                                                                                                 
        32.vaginterfacefault(135168)            -indicates The state of AG is abnormal:VAG interface is fault                                                                                                                                                                                                               
        33.bandoverload(135169)                 -indicates The state of AG is abnormal:the band is overloaded                                                                                                                                                                                                                   
        34.mgcoverloade(135170)                 -indicates The state of AG is abnormal:MGC is overloaded                                                                                                                                                                                                                    
        35.mgoverload(135171)                   -indicates The state of AG is abnormal:MG is overloaded                                                                                                                                                                                                                     
        36.poweroverload(139264)                -indicates The state of AG is abnormal:the power is overloaded                                                                                                                                                                                                                  
        37.innerresourceabnormal(139265)        -indicates The state of AG is abnormal:inner resource is abnormal                                                                                                                                                                                                           
        38.normalservicebrokenSAL(139266)       -indicates The state of AG is abnormal:SAL is broken by normal service                                                                                                                                                                                                      
        39.DSPfault(139267)                     -indicates The state of AG is abnormal:DSP is fault                                                                                                                                                                                                                         
        40.DSPresourcelack(139268)              -indicates The state of AG is abnormal:DSP's resource is not enough                                                                                                                                                                                                         
        41.mainbackupswitching(139269)          -indicates The state of AG is abnormal:main and backup board is switchi                                                                                                                                                                                                         
        42.portpowerdown(143360)                -indicates The state of AG is abnormal:port is power down                                                                                                                                                                                                               
        43.portnotexist(143361)                 -indicates The state of AG is abnormal:port is not exist                                                                                                                                                                                                                    
        44.porttesting(143362)                  -indicates The state of AG is abnormal:port is testing                                                                                                                                                                                                                              
        45.portfault(143363)                    -indicates The state of AG is abnormal:port is fault                                                                                                                                                                                                                                
        46.portoffhookPowerDailer(143364)       -indicates The state of AG is abnormal:port offhook PowerDailer                                                                                                                                                                                                                 
        47.portoffhookfailed(143365)            -indicates The state of AG is abnormal:port offhook failed                                                                                                                                                                                                                          
        48.agdialingunfinish(143366)            -indicates The state of AG is abnormal:AG's dialing is unfinished                                                                                                                                                                                                               
        49.otherreasonAGstateabnormal(196607)   -indicates The state of AG is abnormal:other reason                                                                                                                                                                                                                             
        50.localrefusecall(196608)              -indicates The interaction of signaling is abnormal:loacl party refuse                                                                                                                                                                                                      
        51.serviceflowabnormal(196609)          -indicates The interaction of signaling is abnormal:service flow is abn                                                                                                                                                                                                         
        52.remoterefusecall(200704)             -indicates The interaction of signaling is abnormal:remote party refuse                                                                                                                                                                                                     
        53.localnotsupport(204800)              -indicates The interaction of signaling is abnormal:local party dose no                                                                                                                                                                                                     
        54.remoteRTPmodeabnormal(208896)        -indicates The interaction of signaling is abnormal:RTP mode appointed by remote party is abnormal
        55.sdpnegotiatefail(208897)             -indicates The interaction of signaling is abnormal:SDP negotiate failed
        56.mgccontextmismatch(208898)           -indicates The interaction of signaling is abnormal:MGC's context is mismatch
        57.MGCnotcheckevent(208899)             -indicates The interaction of signaling is abnormal:MGC dose not appoint to check events
        58.novaliddigimapH248MGCP(208900)       -indicates The interaction of signaling is abnormal:no valid digimap(H248/MGCP)
        59.remotewrongrespond(208901)           -indicates The interaction of signaling is abnormal:the other party dose not respond correctly after dialing
        60.remotewrongrespondsignaling(208902)  -indicates The interaction of signaling is abnormal:the other party does not respond the signaling correctly 
        61.notstarttalk(208903)                 -indicates The interaction of signaling is abnormal:have not started talking
        62.notappointring(208904)               -indicates The interaction of signaling is abnormal:dose not appoint to ring
        63.remotenotcalllocal(208905)           -indicates The interaction of signaling is abnormal:remote party does not call local remote
        64.remoterealsecall(208906)             -indicates The interaction of signaling is abnormal:remote party realse the call
        65.remoterefusecallbt(208907)           -indicates The interaction of signaling is abnormal:remote party refuse call by busy tone
        66.unexpectedsignaling(208908)          -indicates The interaction of signaling is abnormal:unexpected signaling
        67.otherreasonsignalabnormal(262143)    -indicates The interaction of signaling is abnormal:other reason                                                                                                                                                                                                             
        "
    ::= { hwPstnCalledEmulateOprEntry 10 }
    
     
  hwPstnTelephoneTestOprTable OBJECT-TYPE
    SYNTAX      SEQUENCE OF HwPstnTelephoneTestOprEntry
    MAX-ACCESS  not-accessible
    STATUS      current
    DESCRIPTION
      "
      The operation table of the called test of the PSTN call emulation test. It is used to realize the called 
      test of the PSTN call emulation test, which is used to test whether a user of a port functioned as the 
      called party can make a call.
      The index of this table is ifIndex.
      Operation table for the PSTN telephone test:
      It realizes the function of the test on subscriber phones in the system. This test helps test the features of the subscriber phone and check whether a subscriber phone works in the normal state."
    ::= { hwNTestMIBObjects 12 }

  hwPstnTelephoneTestOprEntry OBJECT-TYPE
    SYNTAX      HwPstnTelephoneTestOprEntry
    MAX-ACCESS  not-accessible
    STATUS      current
    DESCRIPTION
      "
      The operation table of the called test of the PSTN call emulation test. It is used to realize the called 
      test of the PSTN call emulation test, which is used to test whether a user of a port functioned as the 
      called party can make a call.
      The index of this entry is ifIndex.
      Operation table for the PSTN telephone test:
      It realizes the function of the test on subscriber phones in the system. This test helps test the features of the subscriber phone and check whether a subscriber phone works in the normal state."
    INDEX    {  
              ifIndex
             }
    ::= { hwPstnTelephoneTestOprTable 1 }

  HwPstnTelephoneTestOprEntry ::=
    SEQUENCE
    {
      hwPstnTelephoneTestOprType        INTEGER,
      hwPstnTelephoneTestStatus         INTEGER,
      hwPstnTelephoneTestLoopResist     Integer32,
      hwPstnTelephoneTestHookingTime    Integer32,
      hwPstnTelephoneTestReverse        INTEGER,
      hwPstnTelephoneTestDialDigit      INTEGER,
      hwPstnTelephoneTestPulseLen       Integer32,
      hwPstnTelephoneTestMakeDur        Integer32,
      hwPstnTelephoneTestBreakDur       Integer32,
      hwPstnTelephoneTestAssisTelno     OCTET STRING,
      hwPstnTelephoneTestRingTime       Integer32
    }

  hwPstnTelephoneTestOprType OBJECT-TYPE
    SYNTAX      INTEGER{stop(1), start(2), ringing(3), stopRinging(4), recieveNumber(5), stopRecievingNumber(6), poleTest(7), loopResistance(8), 
    busyTone(9), stopBusyTone(10), howlTone(11), stopHowlTone(12), flash(13), stopFlash(14)}
    MAX-ACCESS  read-create
    STATUS      current
    DESCRIPTION
        "Operation type.
         Options:
         1. stop(1)                 -indicates Stop test
         2. start(2)                -indicates Start test
         3. ringing(3)              -indicates Ring
         4. stopRinging(4)          -indicates Stop ringing
         5. recieveNumber(5)        -indicates Receive a number
         6. stopRecievingNumber(6)  -indicates Stop receiving a number
         7. poleTest(7)             -indicates Reverse polarity
         8. loopResistance(8)       -indicates Test the loop resistance
         9. busyTone(9)             -indicates Send the interrupted tone
         10.stopBusyTone(10)        -indicates Stop sending the interrupted tone
         11.howlTone(11)            -indicates Send the continuous tone
         12.stopHowlTone(12)        -indicates Stop sending the continuous tone
         13.flash(13)               -indicates Receive hookflash
         14.stopFlash(14)           -indicates Stop receiving hookflash
        "
    ::= { hwPstnTelephoneTestOprEntry 1 }

  hwPstnTelephoneTestStatus OBJECT-TYPE
    SYNTAX      INTEGER{startSuccessfully(1),stopSuccessfully(2), testOuttime(3), asisportringing(4),detectRingingOuttime(5),waitingOffHookouttime(6), waitingoffHook(7), testingFailure(8), onHook(9), offHook(10), ringingSuccessful(11), stopRingingSuccessfully(12),startToRecieveDigit(13),stopRevievingDigitSuccessfully(14),sendBusyToneSuccessfully(15),stopBusyToneSuccessfully(16),sendHowlToneSuccessfully(17),stopHowlToneSuccessfully(18),startToRecieveFlash(19),stopRevFlashSuccessfully(20),waitHTcmdTimeout(21),reporttestreport(22),testingAbnormal(23),broadbandtesting(29),capturefail(30),notratb(31),ringtimeout(32)}
    MAX-ACCESS  read-only
    STATUS      current
    DESCRIPTION
        "Test status. 
         Options:
         1. startSuccessfully(1)                -indicates Start test successfully 
         2. stopSuccessfully(2)                 -indicates Stop test successfully 
         3. testOuttime(3)                      -indicates Timed-out (test)  
         4. asisportringing(4)                  -indicates Assistance port ringing
         5. detectRingingOuttime(5)             -indicates Timed-out (detecting the assistance port ringing)  
         6. waitingOffHookouttime(6)            -indicates Timed-out (waiting for off-hook)  
         7. waitingoffHook(7)                   -indicates Waiting for off-hook 
         8. testingFailure(8)                   -indicates Test failure;
         9. onHook(9)                           -indicates On hook 
         10. offHook(10)                        -indicates Off hook 
         11. ringingSuccessful(11)              -indicates Ring successful 
         12. stopRingingSuccessfully(12)        -indicates Stop ringing successfully 
         13. startToRecieveDigit(13)            -indicates Receive a number 
         14. stopRevievingDigitSuccessfully(14) -indicates Stop receiving a number successfully 
         15. sendBusyToneSuccessfully(15)       -indicates Send the interrupted tone successfully 
         16. stopBusyToneSuccessfully(16)       -indicates Stop sending the interrupted tone successfully;
         17. sendHowlToneSuccessfully(17)       -indicates Send the continuous tone successfully
         18. stopHowlToneSuccessfully(18)       -indicates Stop sending the continuous tone successfully 
         19. startToRecieveFlash(19)            -indicates Receive hookflash
         20. stopRevFlashSuccessfully(20)       -indicates Stop receiving hookflash 
         21. waitHTcmdTimeout(21)               -indicates Timed-out (waiting for subscriber processing)  
         22. reporttestreport(22)               -indicates Report the test result 
         23. testingAbnormal(23)                -indicates Test abnormal;
         24. broadbandtesting(29)               -indicates Broadband testing 
         25. capturefail(30)                    -indicates Line capture failure 
         26. notratb(31)                        -indicates Relay transfer board does not exist 
         27. ringtimeout(32)                    -indicates Ring timeout
        "
    ::= { hwPstnTelephoneTestOprEntry 2 }

  hwPstnTelephoneTestLoopResist OBJECT-TYPE
    SYNTAX      Integer32
    MAX-ACCESS  read-only
    STATUS      current
    DESCRIPTION
        "Loop resistance. 
         Unit: ohm
        "
    ::= { hwPstnTelephoneTestOprEntry 3 }

  hwPstnTelephoneTestHookingTime OBJECT-TYPE
    SYNTAX      Integer32
    MAX-ACCESS  read-only
    STATUS      current
    DESCRIPTION
        "Hookflash time.
         Unit: millisecond
        "
    ::= { hwPstnTelephoneTestOprEntry 4 }

  hwPstnTelephoneTestReverse OBJECT-TYPE
    SYNTAX      INTEGER{aPositiveAndbNegative(1),aNegativeAndbPositive(2), noFeedVoltage(3),reverseTestOver(4)}
    MAX-ACCESS  read-only
    STATUS      current
    DESCRIPTION
        "Polarity reversal .
         Options: 
         1: aPositiveAndbNegative(1)     -indicates  A+ B-
         2: aNegativeAndbPositive(2)     -indicates A- B+
         3: noFeedVoltage(3)             -indicates No feeding voltage
         4: reverseTestOver(4)           -indicates Polarity reversal test is finished
        "
    ::= { hwPstnTelephoneTestOprEntry 5 }

  hwPstnTelephoneTestDialDigit OBJECT-TYPE
    SYNTAX      INTEGER{n1(1),n2(2),n3(3),n4(4),n5(5),n6(6),n7(7),n8(8),n9(9),n0(10),nStar(11),nWell(12),nOthers(13)}
    MAX-ACCESS  read-only
    STATUS      current
    DESCRIPTION
        "Dialing numeral 
         Options: 
         1. n1(1)       -indicates 1
         2. n2(2)       -indicates 2
         3. n3(3)       -indicates 3
         4. n4(4)       -indicates 4
         5. n5(5)       -indicates 5
         6. n6(6)       -indicates 6
         7. n7(7)       -indicates 7
         8. n8(8)       -indicates 8
         9. n9(9)       -indicates 9
         10.n0(10)      -indicates 0
         11.nStar(11)   -indicates *
         12.nWell(12)   -indicates #
         13.nOthers(13) -indicates others; 
        "
    ::= { hwPstnTelephoneTestOprEntry 6 }

  hwPstnTelephoneTestPulseLen OBJECT-TYPE
    SYNTAX      Integer32
    MAX-ACCESS  read-only
    STATUS      current
    DESCRIPTION
        "Pulse length.
         Unit: millisecond
        "
    ::= { hwPstnTelephoneTestOprEntry 7 }

  hwPstnTelephoneTestMakeDur OBJECT-TYPE
    SYNTAX      Integer32
    MAX-ACCESS  read-only
    STATUS      current
    DESCRIPTION
        "Pulse duration.
         Unit: millisecond
        "
    ::= { hwPstnTelephoneTestOprEntry 8 }

  hwPstnTelephoneTestBreakDur OBJECT-TYPE
    SYNTAX      Integer32
    MAX-ACCESS  read-only
    STATUS      current
    DESCRIPTION
        "Pulse break length.
         Unit: millisecond
        "
    ::= { hwPstnTelephoneTestOprEntry 9 }

  hwPstnTelephoneTestAssisTelno OBJECT-TYPE
    SYNTAX      OCTET STRING(SIZE(16))
    MAX-ACCESS  read-only
    STATUS      current
    DESCRIPTION
        "Telephone number of the assistant port (the host sends the number to the EMS when the telephone test starts)"
    ::= { hwPstnTelephoneTestOprEntry 10 }

  hwPstnTelephoneTestRingTime OBJECT-TYPE
    SYNTAX      Integer32(0..360)
    MAX-ACCESS  read-create
    STATUS      current
    DESCRIPTION
        "Ring time.
         Unit: second
        "
    ::= { hwPstnTelephoneTestOprEntry 11 }

  hwIsdnUserDiagnoseTestOprTable OBJECT-TYPE
    SYNTAX      SEQUENCE OF HwIsdnUserDiagnoseTestOprEntry
    MAX-ACCESS  not-accessible
    STATUS      current
    DESCRIPTION
      "Operation table for the diagnosis test on the ISDN subscribers:
      It realizes the diagnosis test on the ISDN subscribers in the system. This test helps check the status and performance of the NT1 and transmission channel.
      The index of this table is ifIndex"
    ::= { hwNTestMIBObjects 13 }

  hwIsdnUserDiagnoseTestOprEntry OBJECT-TYPE
    SYNTAX      HwIsdnUserDiagnoseTestOprEntry
    MAX-ACCESS  not-accessible
    STATUS      current
    DESCRIPTION
      "Operation table for the diagnosis test on the ISDN subscribers:
      It realizes the diagnosis test on the ISDN subscribers in the system. This test helps check the status and performance of the NT1 and transmission channel.
      The index of this entry is ifIndex"
    INDEX    {  
              ifIndex
             }
    ::= { hwIsdnUserDiagnoseTestOprTable 1 }

  HwIsdnUserDiagnoseTestOprEntry ::=
    SEQUENCE
    {
      hwIsdnUserDiagnoseTestOprType     INTEGER,
      hwIsdnUserDiagnoseTestStatus      INTEGER
    }

  hwIsdnUserDiagnoseTestOprType OBJECT-TYPE
    SYNTAX      INTEGER{activate(1), deactivate(2), bbdLoopbackFromNT1(3), b1LoopbackFromNT1(4), b2LoopbackFromNT1(5), depravingCRCRequest(6),
     depravingCRCAck(7),holdingState(8), restore(9), nT1PowerState(10), loopback1(11), cancelLoopback1(12), stopTest(13), 
     loopback4(14),  cancelloopback4(15), sendCCRC(16), stopSendCCRC(17), testingAbnormal(18)}
    MAX-ACCESS  read-create
    STATUS      current
    DESCRIPTION
        "Operation type.
         Options: 
         1: activate(1)             -indicates Activate
         2: deactivate(2)           -indicates Deactivate
         3: bbdLoopbackFromNT1(3)   -indicates 2B+D loopback on NT1
         4: b1LoopbackFromNT1(4)    -indicates B1 loopback on NT1
         5: b2LoopbackFromNT1(5)    -indicates B1 loopback on NT1
         6: depravingCRCRequest(6)  -indicates Bad CRC request
         7: depravingCRCAck(7)      -indicates Bad CRC notification
         8: holdingState(8)         -indicates State-retaining 
         9: restore(9)              -indicates Return to normal
         10: nT1PowerState(10)      -indicates NT1 power status
         11: loopback1(11)          -indicates Loopback1
         12: cancelLoopback1(12)    -indicates Cancel loopback1
         13: stopTest(13)           -indicates Stop the diagnosis test
         14: loopback4(14)          -indicates Loopback4
         15: cancelloopback4(15)    -indicates Cancel loopback4 
         16: sendCCRC(16)           -indicates Send CCRC
         17: stopSendCCRC(17)       -indicates Stop sending CCRC
         18: testingAbnormal(18)    -indicates Test abnormal
        "
    ::= { hwIsdnUserDiagnoseTestOprEntry 1 }

  hwIsdnUserDiagnoseTestStatus OBJECT-TYPE
    SYNTAX      INTEGER{startSuccessfully(1),stopSuccessfully(2),testingNormal(3),actUIfouttime(4),dslDeactOrCancelLoop(5),actUIfFailed(6),normalMasterPowerAbnormalStandbyPowerAbnormal(7),normalMasterPowerNormalStandbyPowerAbnormal(8),normalMasterPowerAbNormalStandbyPowerNormal(9),normalMasterPowerNormalStandbyPowerNormal(10),singleTestingOutTime(11),singleTestingFailure(12),outtime(13),dslReportFailure(14),notTesting(15),testingAbnormal(16)}
    MAX-ACCESS  read-only
    STATUS      current
    DESCRIPTION
        "Test status.
         Options:
         1: startSuccessfully(1)                            -indicates Start test successfully (the EMS can activate or loop back a port without starting the test)
         2: stopSuccessfully(2)                             -indicates Stop test successfully
         3: testingNormal(3)                                -indicates Test normal
         4: actUIfouttime(4)                                -indicates Timed-out (activating the U interface)
         5: dslDeactOrCancelLoop(5)                         -indicates Deactivate the DSL report/cancel loopback1 (the EMS may receive this message when the EMS does not deliver the activate or loopback command)
         6: actUIfFailed(6)                                 -indicates Activating the U interface fails
         7: normalMasterPowerAbnormalStandbyPowerAbnormal(7)-indicates Normal, the primary power does not work, and the standby power does not work
         8: normalMasterPowerNormalStandbyPowerAbnormal(8)  -indicates Normal, the primary power works, and the standby power does not work
         9: normalMasterPowerAbNormalStandbyPowerNormal(9)  -indicates Normal, the primary power does not work, and the standby power works
         10: normalMasterPowerNormalStandbyPowerNormal(10)  -indicates  Normal, the primary power works, and the standby power works;
         11: singleTestingOutTime(11)                       -indicates Timed-out (a single test)
         12: singleTestingFailure(12)                       -indicates A single test fails 
         13: outtime(13)                                    -indicates Timed-out (test) 
         14: dslReportFailure(14)                           -indicates DSL report fails;
         15: notTesting(15)                                 -indicates Not tested
         16: testingAbnormal(16)                            -indicates Test abnormal
        "
    ::= { hwIsdnUserDiagnoseTestOprEntry 2 }

  hwPstnSignalToneTestOprTable OBJECT-TYPE
    SYNTAX      SEQUENCE OF HwPstnSignalToneTestOprEntry
    MAX-ACCESS  not-accessible
    STATUS      current
    DESCRIPTION
      "Operation table for the PSTN signal tone test:
      It realizes the function of the PSTN signal tone test in the system. This test helps check whether the dial tone and the dial tone delay function.
      The index of this table is ifIndex"
    ::= { hwNTestMIBObjects 14 }

  hwPstnSignalToneTestOprEntry OBJECT-TYPE
    SYNTAX      HwPstnSignalToneTestOprEntry
    MAX-ACCESS  not-accessible
    STATUS      current
    DESCRIPTION
      "Operation table for the PSTN signal tone test:
      It realizes the function of the PSTN signal tone test in the system. This test helps check whether the dial tone and the dial tone delay function.
      The index of this entry is ifIndex"
    INDEX    {  
              ifIndex
             }
    ::= { hwPstnSignalToneTestOprTable 1 }

  HwPstnSignalToneTestOprEntry ::=
    SEQUENCE
    {
      hwPstnSignalToneTestOprType       INTEGER,
      hwPstnSignalToneTestBusyFlag      INTEGER,
      hwPstnSignalToneTestResult        INTEGER,
      hwPstnSignalToneTestDTDelayTime   Integer32,
      hwPstnSignalTonePlayTime          Integer32,
      hwPstnSignalToneActualDeferTime   Integer32,
      hwPstnSignalToneTestMode          INTEGER,
      hwPstnSignalToneTestRequestID     Integer32,
      hwPstnSignalToneTestDTStop        INTEGER
    }
        
    hwPstnSignalToneTestOprType OBJECT-TYPE
    SYNTAX      INTEGER{dialtone(1), dailtoneDelay(2), specialdailtone(3), stopTest(4), ringbacktone(5), busytone(6), invalidValue(-1) }
    MAX-ACCESS  read-create
    STATUS      current
    DESCRIPTION
        "Operation type.
         Options: 
         1. dialtone(1)          -indicates  Dial tone test
         2. dailtoneDelay(2)     -indicates  Dial tone delay test
         3. specialdailtone(3)   -indicates  Special Dial tone test
         4. stopTest(4)          -indicates  Stop Dial tone test  
         5. ringbacktone(5)      -indicates  Ring back tone test 
         6. busytone(6)          -indicates  Busy tone test 
         7. invalidValue(-1)     -indicates  Invalid value 
        "
    ::= { hwPstnSignalToneTestOprEntry 1 }

  hwPstnSignalToneTestBusyFlag OBJECT-TYPE
    SYNTAX      INTEGER{busynotest(1), busystrentest(2), invalidvalue(-1) }
    MAX-ACCESS  read-create
    STATUS      current
    DESCRIPTION
        "Signal tone test-Busy control.
         Options: 
         1. busynotest(1)        -indicates  no test when busy
         2. busystrentest(2)     -indicates  forced test when busy
         3. invalidvalue(-1)     -indicates  Invalid value 
        "
    ::= { hwPstnSignalToneTestOprEntry 2 }

  hwPstnSignalToneTestResult OBJECT-TYPE
    SYNTAX      INTEGER{signaltoneNormal(1), noSignaltone(2), signaltoneAbnormal(3), unknownError(4),testingAbnormal(5),broadbandtesting(6),capturefail(7),notratb(8),notone(9),testnotfinish(10)}
    MAX-ACCESS  read-only
    STATUS      current
    DESCRIPTION
        "Operation result.
         Options: 
         1. signaltoneNormal(1)     -indicates Signal tone normal
         2. noSignaltone(2)         -indicates No signal tone
         3. signaltoneAbnormal(3)   -indicates  Signal tone abnormal
         4. unknownError(4)         -indicates Unknown error
         5. testingAbnormal(5)      -indicates Test abnormal
         6. broadbandtesting(6)     -indicates Broadband testing
         7. capturefail(7)          -indicates Line capture failure
         8. notratb(8)              -indicates Relay transfer board does not exist 
         9. notone(9)               -indicates No tone
         10. testnotfinish(10)      -indicates signal tone test not finish
        "
    ::= { hwPstnSignalToneTestOprEntry 3 }

  hwPstnSignalToneTestDTDelayTime OBJECT-TYPE
    SYNTAX      Integer32(-1 | 0..65535)
    MAX-ACCESS  read-only
    STATUS      current
    DESCRIPTION
        "Dial tone delay. 
         Unit: millisecond
        "
    ::= { hwPstnSignalToneTestOprEntry 4 }

    
  hwPstnSignalTonePlayTime OBJECT-TYPE
    SYNTAX      Integer32(-1 | 5..30)
    MAX-ACCESS  read-create
    STATUS      current
    DESCRIPTION
        "Tone play time. 
         Default:  10
         Unit: second
        "

    ::= { hwPstnSignalToneTestOprEntry 5 }

  hwPstnSignalToneActualDeferTime OBJECT-TYPE
    SYNTAX      Integer32(-1 | 0..65535)
    MAX-ACCESS  read-only
    STATUS      current
    DESCRIPTION
        "Signal Actually Defer Timer.
         Unit: millisecond
        "

    ::= { hwPstnSignalToneTestOprEntry 6 }
    
  hwPstnSignalToneTestMode OBJECT-TYPE
    SYNTAX      INTEGER{outOfService(1), inService(2), invalidValue(-1)}
    MAX-ACCESS  read-create
    STATUS      current
    DESCRIPTION
        "Test Mode.
         Options: 
         1. outOfService(1)     -Test port not need in service
         2. inService(2)        -Test port must be in servcie 
         3. invalidValue(-1)    -Invalid value
        "
    ::= { hwPstnSignalToneTestOprEntry 7 }

  hwPstnSignalToneTestRequestID OBJECT-TYPE
    SYNTAX      Integer32
    MAX-ACCESS  read-only
    STATUS      current
    DESCRIPTION
        "
         Request ID
        "
    ::= { hwPstnSignalToneTestOprEntry 8 }
    
  hwPstnSignalToneTestDTStop OBJECT-TYPE
    SYNTAX      INTEGER{yes(1), no(2), invalidValue(-1)}
    MAX-ACCESS  read-only
    STATUS      current
    DESCRIPTION
        "
        Detect stop dial tone.
        Options:
        1.yes(1)           -Detected stop dial tone
        2.no(2)            -Not detected stop dial tone 
        3.invalidValue(-1) -Invalid value 
        "
    ::= { hwPstnSignalToneTestOprEntry 9 }
    
    hwIsdnMeterTestOprTable OBJECT-TYPE
    SYNTAX SEQUENCE OF HwIsdnMeterTestOprEntry
    MAX-ACCESS not-accessible
    STATUS current
    DESCRIPTION          
        "Operation table for the ISDN meter test: 
        It realizes the function of the ISDN meter test in the system. The test board provides, through the meter test function, the interface connected to the external test meter such as the multimeter.
        The index of this table is ifIndex"
    ::= { hwNTestMIBObjects 15 }


        
  hwIsdnMeterTestOprEntry OBJECT-TYPE
    SYNTAX HwIsdnMeterTestOprEntry
    MAX-ACCESS not-accessible
    STATUS current
    DESCRIPTION          
        "Operation table for the ISDN meter test: 
        It realizes the function of the ISDN meter test in the system. The test board provides, through the meter test function, the interface connected to the external test meter such as the multimeter.
        The index of this entry is ifIndex"
        INDEX    {  
                  ifIndex
                 }
    ::= { hwIsdnMeterTestOprTable 1 }
    
  HwIsdnMeterTestOprEntry ::=
    SEQUENCE { 
        hwIsdnMeterTestOprType
            INTEGER,
        hwIsdnMeterTestItem
            INTEGER,
        hwIsdnMeterTestStatus
            INTEGER
     }

  hwIsdnMeterTestOprType OBJECT-TYPE
    SYNTAX INTEGER
        {
        stop(1),
        start(2)
        }
    MAX-ACCESS read-create
    STATUS current
    DESCRIPTION
        "Describes the Operation type.
         Options: 
            1. stop(1)  -stop the test 
            2. start(2) -start the test  
        "
    ::= { hwIsdnMeterTestOprEntry 1 }
        
  hwIsdnMeterTestItem OBJECT-TYPE
    SYNTAX INTEGER
        {
        inline(1),
        outline(2)
        }
    MAX-ACCESS read-create
    STATUS current
    DESCRIPTION
        "Test item.
         Options: 
         1. inline(1)  -indicates Circuit test
         2. outline(2) -indicates Loop-line test
        "
    ::= { hwIsdnMeterTestOprEntry 2 }
        
  hwIsdnMeterTestStatus OBJECT-TYPE
    SYNTAX INTEGER
        {
        success(1),
        fail(2),
        portbusy(3),
        outoftime(4),
        testingAbnormal(5)
        }
    MAX-ACCESS read-only
    STATUS current
    DESCRIPTION
        "Test status. 
         Options: 
         1. success(1)          -indicates normal
         2. fail(2)             -indicates abnormal
         3. portbusy(3)         -indicates busy port
         4. outoftime(4)        -indicates timed-out
         5. testingAbnormal(5)  -indicates test abnormal
        "
    ::= { hwIsdnMeterTestOprEntry 3 }

    hwTestBusTestOprTable OBJECT-TYPE
    SYNTAX      SEQUENCE OF HwTestBusTestOprEntry
    MAX-ACCESS  not-accessible
    STATUS      current
    DESCRIPTION
      "Test on the circuit/loop-line test bus:
      It realizes the function of the test on the circuit/loop-line test bus. This test helps check whether the circuit/loop-line test bus is normal.
      The index of this table is hwTestGroupNo"
    ::= { hwNTestMIBObjects 16 }

  hwTestBusTestOprEntry OBJECT-TYPE
    SYNTAX      HwTestBusTestOprEntry
    MAX-ACCESS  not-accessible
    STATUS      current
    DESCRIPTION
      "Test on the circuit/loop-line test bus:
      It realizes the function of the test on the circuit/loop-line test bus. This test helps check whether the circuit/loop-line test bus is normal.
      The index of this entry is hwTestGroupNo"
    INDEX    {  
              hwTestGroupNo
             }
    ::= { hwTestBusTestOprTable 1 }

  HwTestBusTestOprEntry ::=
    SEQUENCE
    {
      hwTestBusTestOprType       INTEGER,
      hwTestBusTestBusType       INTEGER,
      hwTestBusTestResult        INTEGER,
      hwTestBusTestVoltage       Integer32,
      hwTestBusTestResistance    Integer32,
      hwTestBusTestCapacitance   Integer32
    }

  hwTestBusTestOprType OBJECT-TYPE
    SYNTAX      INTEGER{stop(1), start(2) }
    MAX-ACCESS  read-create
    STATUS      current
    DESCRIPTION
       "Describes the Operation type.
         Options: 
            1. stop(1)  -stop the test 
            2. start(2) -start the test  
        "
    ::= { hwTestBusTestOprEntry 1 }

  hwTestBusTestBusType OBJECT-TYPE
    SYNTAX      INTEGER{inbus(1), outbus(2) }
    MAX-ACCESS  read-create
    STATUS      current
    DESCRIPTION
        "Operation type. 
         Options: 
         1. inbus(1)  -indicates Circuit test bus        
         2. outbus(2) -indicates Loop-line test bus
        "
    ::= { hwTestBusTestOprEntry 2 }

  hwTestBusTestResult OBJECT-TYPE
    SYNTAX      INTEGER{testbusNormal(1), voltageAbnormal(2), resistanceAbnormal(3),capacitanceAbnormal(4), testOutoftime(5),
     unknownError(6),testingAbnormal(7),broadbandtesting(8),capturefail(9),notratb(10)}
    MAX-ACCESS  read-only
    STATUS      current
    DESCRIPTION
        "Operation result. 
         Options:
         1. testbusNormal(1)        -indicates Normal
         2. voltageAbnormal(2)      -indicates Voltage abnormal
         3. resistanceAbnormal(3)   -indicates Resistance abnormal
         4. capacitanceAbnormal(4)  -indicates Capacitance abnormal
         5. testOutoftime(5)        -indicates Timed-out
         6. unknownError(6)         -indicates Unknown error
         7. testingAbnormal(7)      -indicates Test abnormal
         8. broadbandtesting(8)     -indicates Broadband testing
         9. capturefail(9)          -indicates Line capture failure
         10. notratb(10)            -indicates Relay transfer board does not exist
        "
    ::= { hwTestBusTestOprEntry 3 }

  hwTestBusTestVoltage OBJECT-TYPE
    SYNTAX      Integer32
    MAX-ACCESS  read-only
    STATUS      current
    DESCRIPTION
        "Voltage.
         Unit: millivolt, ab. mV
        "
    ::= { hwTestBusTestOprEntry 4 }
    
  hwTestBusTestResistance OBJECT-TYPE
    SYNTAX      Integer32
    MAX-ACCESS  read-only
    STATUS      current
    DESCRIPTION
        "Resistance.
         Unit: ohm
        "
    ::= { hwTestBusTestOprEntry 5 }    
    
  hwTestBusTestCapacitance OBJECT-TYPE
    SYNTAX      Integer32
    MAX-ACCESS  read-only
    STATUS      current
    DESCRIPTION
        "Capacitance.
         Unit: nF
        "
    ::= { hwTestBusTestOprEntry 6 }

  hwFrameLooplineAdjustOprTable OBJECT-TYPE
    SYNTAX      SEQUENCE OF HwFrameLooplineAdjustOprEntry
    MAX-ACCESS  not-accessible
    STATUS      current
    DESCRIPTION
      "The loop line test for get check value.
      The index of this table is hwFrameIndex"
    ::= { hwNTestMIBObjects 17 }

  hwFrameLooplineAdjustOprEntry OBJECT-TYPE
    SYNTAX      HwFrameLooplineAdjustOprEntry
    MAX-ACCESS  not-accessible
    STATUS      current
    DESCRIPTION
      "The loop line test for get check value.
      The index of this entry is hwFrameIndex"
    INDEX    {  
              hwFrameIndex
             }
    ::= { hwFrameLooplineAdjustOprTable 1 }

  HwFrameLooplineAdjustOprEntry ::=
    SEQUENCE
    {
      hwFrameLooplineAdjustCutlineSlotID    Integer32,
      hwFrameLooplineAdjustCutlinePortID    Integer32,
      hwFrameLooplineAdjustSelfMixedSlotID  Integer32,
      hwFrameLooplineAdjustSelfMixedPortID  Integer32,
      hwFrameLooplineAdjustOprType          INTEGER,
      hwFrameLooplineAdjustResult           INTEGER,  
      hwFrameLooplineAdjustOprCab           Integer32,
      hwFrameLooplineAdjustOprCag           Integer32,
      hwFrameLooplineAdjustOprCbg           Integer32,
      hwFrameLooplineAdjustOprRab           Integer32,
      hwFrameLooplineAdjustFrameIndex       Integer32,
      hwFrameLooplineAdjustRequestID        Integer32,
      hwFrameLooplineAdjustBusyFlag         INTEGER
    }

  hwFrameLooplineAdjustCutlineSlotID OBJECT-TYPE
    SYNTAX      Integer32(0..63)
    MAX-ACCESS  read-create
    STATUS      current
    DESCRIPTION
        "Slot ID.
         Range:0-63
        "
    ::= { hwFrameLooplineAdjustOprEntry 1 }

  hwFrameLooplineAdjustCutlinePortID OBJECT-TYPE
    SYNTAX      Integer32(0..63)
    MAX-ACCESS  read-create
    STATUS      current
    DESCRIPTION
        "Port ID. 
         Range:0-63
        "
    ::= { hwFrameLooplineAdjustOprEntry 2 }

  hwFrameLooplineAdjustSelfMixedSlotID OBJECT-TYPE
    SYNTAX      Integer32(0..63)
    MAX-ACCESS  read-create
    STATUS      current
    DESCRIPTION
        "Slot ID.
         Range:0-63 
        "
    ::= { hwFrameLooplineAdjustOprEntry 3 }

  hwFrameLooplineAdjustSelfMixedPortID OBJECT-TYPE
    SYNTAX      Integer32(0..63)
    MAX-ACCESS  read-create
    STATUS      current
    DESCRIPTION
        "Port ID.
         Range:0-63
        "
    ::= { hwFrameLooplineAdjustOprEntry 4 }
    
    
  hwFrameLooplineAdjustOprType OBJECT-TYPE
    SYNTAX      INTEGER{test(1), modify(2), restore(3)}
    MAX-ACCESS  read-create
    STATUS      current
    DESCRIPTION
        "Operation type.
         Options:
         1. test(1)     -indicates test
         2. modify(2)   -indicates modify the test
         3. restore(3)  -indicates return to normal
        "
    ::= { hwFrameLooplineAdjustOprEntry 5 }

  hwFrameLooplineAdjustResult OBJECT-TYPE
    SYNTAX      INTEGER{normal(1), outoftime(2), unknownError(3),notgetselfmixedvalue(4),notgetcutlinevalue(5),notgetallvalue(6)}
    MAX-ACCESS  read-only
    STATUS      current
    DESCRIPTION
        "Operation result. 
         Options:
         1: normal(1)               -indicates Normal 
         2: outoftime(2)            -indicates Timed-out 
         3: unknownError(3)         -indicates Unknown error
         4: notgetselfmixedvalue(4) -indicates Failed to obtain the self-mixed calibration value
         5: notgetcutlinevalue(5)   -indicates Failed to obtain the cut-line calibration value
         6: notgetallvalue(6)       -indicates Failed to obtain the self-mixed and cut-line values
        "
    ::= { hwFrameLooplineAdjustOprEntry 6 }

  hwFrameLooplineAdjustOprCab OBJECT-TYPE
    SYNTAX      Integer32
    MAX-ACCESS  read-create
    STATUS      current
    DESCRIPTION
        "A-B capacitance.
         Unit: nF
        "
    ::= { hwFrameLooplineAdjustOprEntry 7 }    
    
  hwFrameLooplineAdjustOprCag OBJECT-TYPE
    SYNTAX      Integer32
    MAX-ACCESS  read-create
    STATUS      current
    DESCRIPTION
        "A-Ground capacitance.
         Unit: nF
        "
    ::= { hwFrameLooplineAdjustOprEntry 8 }        

  hwFrameLooplineAdjustOprCbg OBJECT-TYPE
    SYNTAX      Integer32
    MAX-ACCESS  read-create
    STATUS      current
    DESCRIPTION
        "B-Ground capacitance.
         Unit: nF
        "
    ::= { hwFrameLooplineAdjustOprEntry 9 }     
    

  hwFrameLooplineAdjustOprRab OBJECT-TYPE
    SYNTAX      Integer32
    MAX-ACCESS  read-create
    STATUS      current
    DESCRIPTION
        "A-B resistance..
         Unit: ohm
        "
    ::= { hwFrameLooplineAdjustOprEntry 10 }    

  hwFrameLooplineAdjustFrameIndex OBJECT-TYPE
    SYNTAX      Integer32
    MAX-ACCESS  read-only
    STATUS      current
    DESCRIPTION
        "Frame index"
    ::= { hwFrameLooplineAdjustOprEntry 11 } 
    
  hwFrameLooplineAdjustRequestID OBJECT-TYPE
    SYNTAX      Integer32
    MAX-ACCESS  read-only
    STATUS      current
    DESCRIPTION
        "Request ID"
    ::= { hwFrameLooplineAdjustOprEntry 12 }
    
  hwFrameLooplineAdjustBusyFlag OBJECT-TYPE
    SYNTAX      INTEGER{cancel(1), force(2), invalid(-1)}
    MAX-ACCESS  read-create
    STATUS      current
    DESCRIPTION
        "Whether test or not when port is busy. 
         Options:
         1: cancel(1)           -indicates notest 
         2: force(2)            -indicates test 
         3: invalid(-1)         -indicates invalid
         "
    ::= { hwFrameLooplineAdjustOprEntry 13 }   
        
  hwFrameLooplineAdjustTable OBJECT-TYPE
    SYNTAX      SEQUENCE OF HwFrameLooplineAdjustEntry
    MAX-ACCESS  not-accessible
    STATUS      current
    DESCRIPTION
      "GET table for the shelf calibration values:
      It realizes the function of obtaining the shelf calibration values.
      The index of this table is hwFrameIndex."
    ::= { hwNTestMIBObjects 18 }

  hwFrameLooplineAdjustEntry OBJECT-TYPE
    SYNTAX      HwFrameLooplineAdjustEntry
    MAX-ACCESS  not-accessible
    STATUS      current
    DESCRIPTION
      "GET table for the shelf calibration values:
      It realizes the function of obtaining the shelf calibration values.
      The index of this entry is hwFrameIndex."
    INDEX    {  
              hwFrameIndex
             }
    ::= { hwFrameLooplineAdjustTable 1 }

  HwFrameLooplineAdjustEntry ::=
    SEQUENCE
    {
      hwFrameLooplineAdjustFlag          INTEGER,   
      hwFrameLooplineAdjustCab           Integer32,
      hwFrameLooplineAdjustCag           Integer32,
      hwFrameLooplineAdjustCbg           Integer32,
      hwFrameLooplineAdjustRab           Integer32
    }

 hwFrameLooplineAdjustFlag OBJECT-TYPE
    SYNTAX      INTEGER{nosetflag(1), capacitanceflag(2), resistanceflag(3), allsetflag(4)}
    MAX-ACCESS  read-only
    STATUS      current
    DESCRIPTION
        "Calibration value flag of the loop-line test. 
         Options:
         1: nosetflag(1)        -indicates No calibration value is set
         2: capacitanceflag(2)  -indicates The capacitance calibration value is set
         3: resistanceflag(3)   -indicates The resistance calibration value is set
         4: allsetflag(4)       -indicates All the calibration values are set
        "
    ::= { hwFrameLooplineAdjustEntry 1 }

 hwFrameLooplineAdjustCab OBJECT-TYPE
    SYNTAX      Integer32
    MAX-ACCESS  read-only
    STATUS      current
    DESCRIPTION
        "A-B capacitance"
    ::= { hwFrameLooplineAdjustEntry 2 }

 hwFrameLooplineAdjustCag OBJECT-TYPE
    SYNTAX      Integer32
    MAX-ACCESS  read-only
    STATUS      current
    DESCRIPTION
        "A-Ground capacitance"
    ::= { hwFrameLooplineAdjustEntry 3 }

   
 hwFrameLooplineAdjustCbg OBJECT-TYPE
    SYNTAX      Integer32
    MAX-ACCESS  read-only
    STATUS      current
    DESCRIPTION
        "B-Ground capacitance"
    ::= { hwFrameLooplineAdjustEntry 4 }

          
  hwFrameLooplineAdjustRab OBJECT-TYPE
    SYNTAX      Integer32
    MAX-ACCESS  read-only
    STATUS      current
    DESCRIPTION
        "A-B resistance"
    ::= { hwFrameLooplineAdjustEntry 5 }

  hwQosTestIndexNext OBJECT-TYPE
    SYNTAX         Integer32 (0..16)
    MAX-ACCESS     read-only
    STATUS         current
    DESCRIPTION
     "This object contains an appropriate value to
      be used for hwQosTestIndex when creating
      entries in the hwQosTestTable.  The value
      0 indicates that no unassigned entries are
      available. To obtain the hwQosTestIndex
      value for a new entry, the manager issues a
      management protocol retrieval operation to obtain
      the current value of this object.  After each
      retrieval, the agent should modify the value to
      the next unassigned index.
      After a manager retrieves a value the agent will
      determine through its local policy when this index
      value will be made available for reuse."
    ::= { hwNTestMIBObjects 19 }

  hwQosTestOprTable OBJECT-TYPE
    SYNTAX      SEQUENCE OF HwQosTestOprEntry
    MAX-ACCESS  not-accessible
    STATUS      current
    DESCRIPTION
      "Table for the QoS test.
      The index of this table is hwQosTestIndex."
    ::= { hwNTestMIBObjects 20 }

  hwQosTestOprEntry OBJECT-TYPE
    SYNTAX      HwQosTestOprEntry
    MAX-ACCESS  not-accessible
    STATUS      current
    DESCRIPTION
      "Table for the QoS test.
      The index of this entry is hwQosTestIndex."
    INDEX {  
              hwQosTestIndex
             }
    ::= { hwQosTestOprTable 1 }

  HwQosTestOprEntry ::=
    SEQUENCE
    {
      hwQosTestIndex    Integer32,
      hwQosTestGWAddr   IpAddress,
      hwQosTestPeerAddr IpAddress,
      hwQosTestDuration Integer32,
      hwQosTestTick Integer32,
      hwQosTestRowStatus    RowStatus,
      hwQosTestInPkts   Integer32,
      hwQosTestOutPkts  Integer32,
      hwQosTestInOctets Integer32,
      hwQosTestOutOctets    Integer32,
      hwQosTestInDropPkts   Integer32,
      hwQosTestStatsMaxDropPktsRate Integer32,
      hwQosTestStatsMaxDropPktsPort OCTET STRING,
      hwQosTestStatsMinDropPktsRate Integer32,
      hwQosTestStatsMinDropPktsPort OCTET STRING,
      hwQosTestStatsMaxDitherDelay  Integer32,
      hwQosTestStatsMaxDitherPort   OCTET STRING,
      hwQosTestStatsMinDitherDelay  Integer32,
      hwQosTestStatsMinDitherPort   OCTET STRING,
      hwQosTestStatsMaxLoopDelay    Integer32,
      hwQosTestStatsMaxLoopPort OCTET STRING,
      hwQosTestStatsMinLoopDelay    Integer32,
      hwQosTestStatsMinLoopPort OCTET STRING
    }

  hwQosTestIndex OBJECT-TYPE
    SYNTAX      Integer32
    MAX-ACCESS  accessible-for-notify
    STATUS      current
    DESCRIPTION
        "Index of the a test"
    ::={ hwQosTestOprEntry 1 }

  hwQosTestGWAddr OBJECT-TYPE
    SYNTAX      IpAddress
    MAX-ACCESS  read-write
    STATUS      current
    DESCRIPTION
        "IP address of the local gateway"
    ::={ hwQosTestOprEntry 2 }

  hwQosTestPeerAddr OBJECT-TYPE
    SYNTAX      IpAddress
    MAX-ACCESS  read-write
    STATUS      current
    DESCRIPTION
        "IP address of the peer gateway (or NAT, SAN)"
    ::={ hwQosTestOprEntry 3 }

  hwQosTestDuration OBJECT-TYPE
    SYNTAX      Integer32
    MAX-ACCESS  read-write
    STATUS      current
    DESCRIPTION
        "Test duration. By default, the test duration is one hour.
         Default:3600"
    DEFVAL      { 3600 }
    ::={ hwQosTestOprEntry 4 }

  hwQosTestTick OBJECT-TYPE
    SYNTAX      Integer32
    MAX-ACCESS  read-write
    STATUS      current
    DESCRIPTION
        "Report cycle. By default, the report cycle is 60s.
         Default:60"
    DEFVAL      { 60 }
    ::={ hwQosTestOprEntry 5 }

  hwQosTestRowStatus OBJECT-TYPE
    SYNTAX      RowStatus
    MAX-ACCESS  read-create
    STATUS      current
    DESCRIPTION
        "Row status"
    ::={ hwQosTestOprEntry 6 }
    
  hwQosTestInPkts OBJECT-TYPE
    SYNTAX      Integer32
    MAX-ACCESS  read-only
    STATUS      current
    DESCRIPTION
        "Test In Pkts"
    ::={ hwQosTestOprEntry 7 }

  hwQosTestOutPkts OBJECT-TYPE
    SYNTAX      Integer32
    MAX-ACCESS  read-only
    STATUS      current
    DESCRIPTION
        "Test Out Pkts"
    ::={ hwQosTestOprEntry 8 }
    
  hwQosTestInOctets OBJECT-TYPE
    SYNTAX      Integer32
    MAX-ACCESS  read-only
    STATUS      current
    DESCRIPTION
        "Test In Octets"
    ::={ hwQosTestOprEntry 9 }

  hwQosTestOutOctets OBJECT-TYPE
    SYNTAX      Integer32
    MAX-ACCESS  read-only
    STATUS      current
    DESCRIPTION
        "Test Out Octets"
    ::={ hwQosTestOprEntry 10 }

  hwQosTestInDropPkts OBJECT-TYPE
    SYNTAX      Integer32
    MAX-ACCESS  read-only
    STATUS      current
    DESCRIPTION
        "Test In Drop Pkts"
    ::={ hwQosTestOprEntry 11 }

  hwQosTestStatsMaxDropPktsRate OBJECT-TYPE
    SYNTAX      Integer32
    MAX-ACCESS  read-only
    STATUS      current
    DESCRIPTION
        "Test Stats Max Drop Pkts Rate"
    ::={ hwQosTestOprEntry 12 }

  hwQosTestStatsMaxDropPktsPort OBJECT-TYPE
    SYNTAX      OCTET STRING
    MAX-ACCESS  read-only
    STATUS      current
    DESCRIPTION
        "Test Stats Max Drop Pkts Port"
    ::={ hwQosTestOprEntry 13 }

  hwQosTestStatsMinDropPktsRate OBJECT-TYPE
    SYNTAX      Integer32
    MAX-ACCESS  read-only
    STATUS      current
    DESCRIPTION
        "Test Stats Min Drop Pkts Rate"
    ::={ hwQosTestOprEntry 14 }

  hwQosTestStatsMinDropPktsPort OBJECT-TYPE
    SYNTAX      OCTET STRING
    MAX-ACCESS  read-only
    STATUS      current
    DESCRIPTION
        "Test Stats Min Drop Pkts Port"
    ::={ hwQosTestOprEntry 15 }

  hwQosTestStatsMaxDitherDelay OBJECT-TYPE
    SYNTAX      Integer32
    MAX-ACCESS  read-only
    STATUS      current
    DESCRIPTION
        "Test Stats Max Dither Delay"
    ::={ hwQosTestOprEntry 16 }

  hwQosTestStatsMaxDitherPort OBJECT-TYPE
    SYNTAX      OCTET STRING
    MAX-ACCESS  read-only
    STATUS      current
    DESCRIPTION
        "Test Stats Max Dither Port"
    ::={ hwQosTestOprEntry 17 }

  hwQosTestStatsMinDitherDelay OBJECT-TYPE
    SYNTAX      Integer32
    MAX-ACCESS  read-only
    STATUS      current
    DESCRIPTION
        "Test Stats Min Dither Delay"
    ::={ hwQosTestOprEntry 18 }

  hwQosTestStatsMinDitherPort OBJECT-TYPE
    SYNTAX      OCTET STRING
    MAX-ACCESS  read-only
    STATUS      current
    DESCRIPTION
        "Test Stats Min Dither Port"
    ::={ hwQosTestOprEntry 19 }

  hwQosTestStatsMaxLoopDelay OBJECT-TYPE
    SYNTAX      Integer32
    MAX-ACCESS  read-only
    STATUS      current
    DESCRIPTION
        "Test Stats Max Loop Delay"
    ::={ hwQosTestOprEntry 20 }

  hwQosTestStatsMaxLoopPort OBJECT-TYPE
    SYNTAX      OCTET STRING
    MAX-ACCESS  read-only
    STATUS      current
    DESCRIPTION
        "Test Stats Max Loop Port"
    ::={ hwQosTestOprEntry 21 }

  hwQosTestStatsMinLoopDelay OBJECT-TYPE
    SYNTAX      Integer32
    MAX-ACCESS  read-only
    STATUS      current
    DESCRIPTION
        "Test Stats Min Loop Delay"
    ::={ hwQosTestOprEntry 22 }

  hwQosTestStatsMinLoopPort OBJECT-TYPE
    SYNTAX      OCTET STRING
    MAX-ACCESS  read-only
    STATUS      current
    DESCRIPTION
        "Test Stats Min Loop Port"
    ::={ hwQosTestOprEntry 23 }

  
  

 hwPotsLooplineThresholdTable OBJECT IDENTIFIER ::= { hwNTestMIBObjects 21 }
      
  -- Associated command lines
  -- Name of the threshold for the line test                        Threshold
  -- Hazardous AC voltage level (V)                                  50
  -- Foreign EMF DC voltage level (V)                                10
  -- Loop line grounding Ground resistance threshold (ohm)               20000
  -- Off hook: A-B resistance lower limit (ohm)                3000
  -- Off hook: A-B resistance upper limit (ohm)              100000
  -- Off hook: Loop resistance lower limit (ohm)                100
  -- Off hook: Loop resistance upper limit (ohm)                3000
  -- Loop-line mixed with others: A-B resistance threshold (ohm)                2000
  -- A-B insulation difference: A-B resistance lower limit (ohm)            2000
  -- A-B insulation difference: A-B resistance upper limit (ohm).           20000
  -- Leakage: Ground capacitance threshold (nF)                    700
  -- Normal: Ground capacitance threshold 1 (nF)                    200
  -- Normal: Ground capacitance threshold 2 (nF)                    350
  -- Normal: Ground capacitance threshold 3 (nF)                    50
  -- A-B Impedance Abnormal: A-B impedance min. threshold(ohm)                             10000  
  -- AC current Abnormal: AC current threshold(amp)                                         1000  
  -- DC current Abnormal: DC current threshold(amp)                                         1000  
  -- AC Voltage Abnormal: AC voltage threshold(volt)                                          10  
  -- DC Voltage Abnormal: DC voltage threshold 1(volt)                                        10  
  -- DC Voltage Abnormal: DC voltage threshold 2(volt)                                       -55  
  -- On hook Loop-Electric Current Abnormal: on hook loop-Electric Current max. threshold(amp)    30
  -- On hook Loop Resistance Abnormal: on hook Loop Resistance threshold(ohm)                 250000
  -- Off hook Loop Resistance Abnormal: off hook Loop Resistance threshold(ohm)               250000
  -- Ground Insulation Resistance Abnormal: ground insulation Resistance threshold 1(ohm) 5000000
  -- Ground Insulation Resistance Abnormal: ground insulation Resistance threshold 2(ohm) 2500000
  -- Ground Capacitance Abnormal: ground capacitance threshold 1(nF)                        200  
  -- A-B Capacitance Abnormal: A-B capacitance min. threshold(nF)                            100  
  -- A-B Capacitance Abnormal: A-B capacitance max. threshold(nF)                            600  
  -- Noise Abnormal: Noise threshold(dBm)                                                     65
  -- Cable characteristic capacitance per unit length between tip and ring (nf per km)        19                               
  -- Cable characteristic capacitance per unit length between tip and GND and ring and GND (nf per km)  62
  -- Cable loop DC resistance per unit length (sum of both wires).(ohm per km)                295
  -- maximum resistance for tip or ring short-circuit to GND (ohm)         2000
  -- maximum resistance for tip or ring leakage to GND (ohm)               200000
  -- Hazardous DC voltage level (mV)                                       80000
  -- Foreign EMF AC voltage level (mVrms)                                  10000
  -- minimum ETSI signature capacitance (nf)                               350
  -- maximum ETSI signature capacitance(nf)                                520
  -- minimum PPA resisitance(ohm)                                          350000
  -- maximum PPA resistance(ohm)                                           520000
  -- minimum voltage to conduct current through the zener diode(mV)        1000
  -- maximum RC network resistance between tip and ring(ohm)               1000000
  -- minimum RC network resistance between tip and ring (ohm)              10000
  -- minimum RC network capacitance between tip and ring(nf)               350
  -- minimum high resistance between tip and ring(ohm)                     1000000
  -- minimum foreign voltage(mV)                                           8000
  -- minimum equivalent resistance when off-hook on zero kilometres(ohm)   200 
  -- line length windage for open wire failure(m)                          200  
  --threshold operation type

 hwTouchThePowerVolThreshold OBJECT-TYPE
    SYNTAX      Integer32(0..2147483647)
    MAX-ACCESS  read-write
    STATUS      current
    DESCRIPTION
      " 
      Hazardous AC voltage level
      Unit: V
      Default: 50
      "
    ::= { hwPotsLooplineThresholdTable 1 }
    
 hwLoopLineMixedVolThreshold OBJECT-TYPE
    SYNTAX      Integer32(0..2147483647)
    MAX-ACCESS  read-write
    STATUS      current
    DESCRIPTION
      "
      Foreign EMF DC voltage level.
      Unit: V
      Default: 10
      "
    ::= { hwPotsLooplineThresholdTable 2 }
 
 hwLoopLineGroundingVolThreshold OBJECT-TYPE
    SYNTAX      Integer32(0..2147483647)
    MAX-ACCESS  read-write
    STATUS      current
    DESCRIPTION
      " 
      Loop line grounding: Ground resistance threshold.
      Unit: ohm
      Default: 20000
      "
    ::= { hwPotsLooplineThresholdTable 3 }

 hwOffHookABMinThreshold OBJECT-TYPE
    SYNTAX      Integer32(0..2147483647)
    MAX-ACCESS  read-write
    STATUS      current
    DESCRIPTION
      " 
      Off-hook: A-B resistance lower limit.
      Unit: ohm
      Default: 3000
      "
    ::= { hwPotsLooplineThresholdTable 4 }
 
  hwOffHookABMaxThreshold OBJECT-TYPE
    SYNTAX      Integer32(0..2147483647)
    MAX-ACCESS  read-write
    STATUS      current
    DESCRIPTION
      " 
      Off-hook: A-B resistance upper limit.
      Unit: ohm
      Default: 100000
      "
    ::= { hwPotsLooplineThresholdTable 5 }
           
  hwOffHookLoopMinThreshold OBJECT-TYPE
    SYNTAX      Integer32(0..2147483647)
    MAX-ACCESS  read-write
    STATUS      current
    DESCRIPTION
      " 
      Off-hook: loop resistance lower limit.
      Unit: ohm 
      Initial value: 100
      "
    ::= { hwPotsLooplineThresholdTable 6 }
    
  hwOffHookLoopMaxThreshold OBJECT-TYPE
    SYNTAX      Integer32(0..2147483647)
    MAX-ACCESS  read-write
    STATUS      current
    DESCRIPTION
      " 
      Off-hook: loop resistance upper limit.
      Unit: ohm 
      Initial value: 3000
      "
    ::= { hwPotsLooplineThresholdTable 7 }
                  
  hwLoopLineMixedABThreshold OBJECT-TYPE
    SYNTAX      Integer32(0..2147483647)
    MAX-ACCESS  read-write
    STATUS      current
    DESCRIPTION
      " 
      Loop line mixed with others: A-B resistance threshold.
      Unit: ohm
      Initial value: 2000
      "
    ::= { hwPotsLooplineThresholdTable 8 }
  
  hwABPoorLineInsulationMinThreshold OBJECT-TYPE
    SYNTAX      Integer32(0..2147483647)
    MAX-ACCESS  read-write
    STATUS      current
    DESCRIPTION
      " 
      A-B insulation difference: A-B resistance lower limit.
      Unit: ohm
      Initial value: 2000
      "
    ::= { hwPotsLooplineThresholdTable 9 }
  
  hwABPoorLineInsulationMaxThreshold OBJECT-TYPE
    SYNTAX      Integer32(0..2147483647)
    MAX-ACCESS  read-write
    STATUS      current
    DESCRIPTION
      " 
      A-B insulation difference: A-B resistance upper limit.
      Unit: ohm
      Default: 20000
      "
    ::= { hwPotsLooplineThresholdTable 10 }
    
  hwLeakageGroundCapThreshold OBJECT-TYPE
    SYNTAX      Integer32(0..2147483647)
    MAX-ACCESS  read-write
    STATUS      current
    DESCRIPTION
      " 
      Leakage: ground capacitance threshold.
      Unit: nF 
      Default: 700
      "
    ::= { hwPotsLooplineThresholdTable 11 }

  hwNormalGroundCap1Threshold OBJECT-TYPE
    SYNTAX      Integer32(0..2147483647)
    MAX-ACCESS  read-write
    STATUS      current
    DESCRIPTION
      " 
      Normal: ground capacitance threshold 1.
      Unit: nF
      Default: 200
      "
    ::= { hwPotsLooplineThresholdTable 12 }
  
  hwNormalGroundCap2Threshold OBJECT-TYPE
    SYNTAX      Integer32(0..2147483647)
    MAX-ACCESS  read-write
    STATUS      current
    DESCRIPTION
      " 
      Normal: ground capacitance threshold 2.
      Unit: nF
      Default: 350
      "
    ::= { hwPotsLooplineThresholdTable 13 }

  hwNormalGroundCap3Threshold OBJECT-TYPE
    SYNTAX      Integer32(0..2147483647)
    MAX-ACCESS  read-write
    STATUS      current
    DESCRIPTION
      " 
      Normal: ground capacitance threshold 3.
      Unit: nF 
      Default: 50
      "
    ::= { hwPotsLooplineThresholdTable 14 }
    
  hwAbnormalImpedanceABhreshold OBJECT-TYPE
    SYNTAX      Integer32(0..2147483647)
    MAX-ACCESS  read-write
    STATUS      current
    DESCRIPTION
      " 
      On hook: lower limit of the A-B abnormal impedance (ohm)
      Default: 10000
      "
    ::= { hwPotsLooplineThresholdTable 15 }
    
  hwAbnormalACElectricCurrentThreshold OBJECT-TYPE
    SYNTAX      Integer32(0..2147483647)
    MAX-ACCESS  read-write
    STATUS      current
    DESCRIPTION
      " 
      Abnormal AC current: threshold of the abnormal AC current (mA)
      Default: 1000
      "
    ::= { hwPotsLooplineThresholdTable 16 }
    
  hwAbnormalDCElectricCurrentThreshold OBJECT-TYPE
    SYNTAX      Integer32(0..2147483647)
    MAX-ACCESS  read-write
    STATUS      current
    DESCRIPTION
      " 
      Abnormal DC current: threshold of the abnormal DC current (mA)
      Default: 1000
      "
    ::= { hwPotsLooplineThresholdTable 17 }
    
  hwAbnormalACVoltageThreshold OBJECT-TYPE
    SYNTAX      Integer32(0..2147483647)
    MAX-ACCESS  read-write
    STATUS      current
    DESCRIPTION
      " 
      Abnormal AC voltage: threshold 1 of the abnormal AC voltage (V)
      Default: 10
      "
    ::= { hwPotsLooplineThresholdTable 18 }
    
  hwAbnormalDCVoltage1Threshold OBJECT-TYPE
    SYNTAX      Integer32(0..2147483647)
    MAX-ACCESS  read-write
    STATUS      current
    DESCRIPTION
      " 
      Abnormal DC voltage: threshold 1 of the abnormal DC voltage (V)
      Default: 10
      "
    ::= { hwPotsLooplineThresholdTable 19 }
    
  hwAbnormalDCVoltage2Threshold OBJECT-TYPE
    SYNTAX      Integer32(0..2147483647)
    MAX-ACCESS  read-write
    STATUS      current
    DESCRIPTION
      " 
      Abnormal DC voltage: threshold 2 of the abnormal DC voltage (V)
      Default: 55
      "
    ::= { hwPotsLooplineThresholdTable 20 }
    
  hwAbnormalOnhookLoopLineElectricCurrentMaxThreshold OBJECT-TYPE
    SYNTAX      Integer32(0..2147483647)
    MAX-ACCESS  read-write
    STATUS      current
    DESCRIPTION
      " 
      Abnormal on-hook loop current: upper limit of the abnormal on-hook loop current (mA)
      Default: 30
      "
    ::= { hwPotsLooplineThresholdTable 21 }
    
  hwAbnormalOnhookLoopResistanceThreshold OBJECT-TYPE
    SYNTAX      Integer32(0..2147483647)
    MAX-ACCESS  read-write
    STATUS      current
    DESCRIPTION
      " 
      Abnormal on-hook loop resistance: threshold of the abnormal on-hook loop resistance (ohm)
      Default: 250000
      "
    ::= { hwPotsLooplineThresholdTable 22 }
    
  hwAbnormalOffhookLoopResistanceThreshold OBJECT-TYPE
    SYNTAX      Integer32(0..2147483647)
    MAX-ACCESS  read-write
    STATUS      current
    DESCRIPTION
      " 
      Abnormal off-hook loop resistance: threshold of the abnormal off-hook loop resistance (ohm)
      Default: 250000
      "
    ::= { hwPotsLooplineThresholdTable 23 }
    
  hwAbnormalGroundInsulationResistance1Threshold OBJECT-TYPE
    SYNTAX      Integer32(0..2147483647)
    MAX-ACCESS  read-write
    STATUS      current
    DESCRIPTION
      " 
      Abnormal ground insulation resistance: threshold 1 of the abnormal ground insulation resistance (ohm)
      Default: 5000000
      "
    ::= { hwPotsLooplineThresholdTable 24 }
    
  hwAbnormalGroundPoorLineInsulation1Threshold OBJECT-TYPE
    SYNTAX      Integer32(0..2147483647)
    MAX-ACCESS  read-write
    STATUS      current
    DESCRIPTION
      " 
      Abnormal ground insulation difference: threshold 1 of the abnormal ground insulation difference (ohm)
      Default: 250000
      "
    ::= { hwPotsLooplineThresholdTable 25 }
    
  hwAbnormalGroundCapacitanceThreshold OBJECT-TYPE
    SYNTAX      Integer32(0..2147483647)
    MAX-ACCESS  read-write
    STATUS      current
    DESCRIPTION
      " 
      Abnormal ground capacitance: threshold of the abnormal ground capacitance (nF)
      Default: 200
      "
    ::= { hwPotsLooplineThresholdTable 26 }
    
  hwAbnormalCapacitanceABMinThreshold OBJECT-TYPE
    SYNTAX      Integer32(0..2147483647)
    MAX-ACCESS  read-write
    STATUS      current
    DESCRIPTION
      " 
      Abnormal: lower limit of the abnormal A-B capacitance (nF)
      Default: 0
      "
    ::= { hwPotsLooplineThresholdTable 27 }
    
  hwAbnormalCapacitanceABMaxThreshold OBJECT-TYPE
    SYNTAX      Integer32(0..2147483647)
    MAX-ACCESS  read-write
    STATUS      current
    DESCRIPTION
      " 
      Abnormal: upper limit of the abnormal A-B capacitance (nF)
      Default: 2000
      "
    ::= { hwPotsLooplineThresholdTable 28 }
    
  hwAbnormalNoiseThreshold OBJECT-TYPE
    SYNTAX      Integer32(0..2147483647)
    MAX-ACCESS  read-write
    STATUS      current
    DESCRIPTION
      " 
      Abnormal noise: threshold 1 of the abnormal noise (dBm)
      Default: 65
      "
    ::= { hwPotsLooplineThresholdTable 29 }
  
  hwLoopParamsCab OBJECT-TYPE
    SYNTAX      Integer32(0..2147483647)
    MAX-ACCESS  read-write
    STATUS      current
    DESCRIPTION
      " 
      Cable characteristic capacitance per unit length between tip and ring 
      Unit : nf per km 
      Range: 0-100   
      Default: 19
      "
    ::= { hwPotsLooplineThresholdTable 30 }

 hwLoopParamsCagbg OBJECT-TYPE
    SYNTAX      Integer32(0..2147483647)
    MAX-ACCESS  read-write
    STATUS      current
    DESCRIPTION
      " 
      Cable characteristic capacitance per unit length between tip and GND and ring and GND
      Unit : nf per km
      Range: 0-100 
      Default: 62
      "
    ::= { hwPotsLooplineThresholdTable 31 }

 hwLoopParamsRab OBJECT-TYPE
    SYNTAX      Integer32(0..2147483647)
    MAX-ACCESS  read-write
    STATUS      current
    DESCRIPTION
      " 
      Cable loop DC resistance per unit length (sum of both wires)
      Unit : ohm per km
      Range: 50-600 
      Default: 295                            
      "
    ::= { hwPotsLooplineThresholdTable 32 }

 hwLrcThMaxsc OBJECT-TYPE
    SYNTAX      Integer32(0..2147483647)
    MAX-ACCESS  read-write
    STATUS      current
    DESCRIPTION
      " 
      maximum resistance for tip or ring short-circuit to GND
      Unit : ohm
      Range: 0-1000000 
      Default: 2000
      "
    ::= { hwPotsLooplineThresholdTable 33 }

 hwLrcThMaxLg OBJECT-TYPE
    SYNTAX      Integer32(0..2147483647)
    MAX-ACCESS  read-write
    STATUS      current
    DESCRIPTION
      " 
      maximum resistance for tip or ring leakage to GND
      Unit : ohm
      Range: 0-1000000
      Default: 200000
      "
    ::= { hwPotsLooplineThresholdTable 34}

 hwHdcvL OBJECT-TYPE
    SYNTAX      Integer32(0..2147483647)
    MAX-ACCESS  read-write
    STATUS      current
    DESCRIPTION
      " 
      Hazardous DC voltage level 
      Unit : mV 
      Range: 0-500000
      Default: 80000
      "
    ::= { hwPotsLooplineThresholdTable 35 }

 hwFacvL OBJECT-TYPE
    SYNTAX      Integer32(0..2147483647)
    MAX-ACCESS  read-write
    STATUS      current
    DESCRIPTION
      " 
      Foreign EMF AC voltage level
      Unit : mVrms 
      Range: 0-200000
      Default: 10000
      "
    ::= { hwPotsLooplineThresholdTable 36 }

 hwMinetsiSc OBJECT-TYPE
    SYNTAX      Integer32(0..2147483647)
    MAX-ACCESS  read-write
    STATUS      current
    DESCRIPTION
      " 
      minimum ETSI signature capacitance
      Unit : nf 
      Range: 100-500
      Default: 350
      "
    ::= { hwPotsLooplineThresholdTable 37}

 hwMaxetsiSc OBJECT-TYPE
    SYNTAX      Integer32(0..2147483647)
    MAX-ACCESS  read-write
    STATUS      current
    DESCRIPTION
      " 
      maximum ETSI signature capacitance
      Unit : nf 
      Range: 500-1000
      Default: 520
      "
    ::= { hwPotsLooplineThresholdTable 38 }

 hwMinetsiPr OBJECT-TYPE
    SYNTAX      Integer32(0..2147483647)
    MAX-ACCESS  read-write
    STATUS      current
    DESCRIPTION
      " 
      minimum PPA resisitance
      Unit : ohm 
      Range: 200000-400000
      Default: 350000
      "
    ::= { hwPotsLooplineThresholdTable 39 }

 hwMaxetsiPr OBJECT-TYPE
    SYNTAX      Integer32(0..2147483647)
    MAX-ACCESS  read-write
    STATUS      current
    DESCRIPTION
      " 
      maximum PPA resistance
      Unit : ohm
      Range: 400000-700000
      Default: 520000
      "
    ::= { hwPotsLooplineThresholdTable 40 }

 hwMinZenerZv OBJECT-TYPE
    SYNTAX      Integer32(0..2147483647)
    MAX-ACCESS  read-write
    STATUS      current
    DESCRIPTION
      " 
      minimum voltage to conduct current through the zener diode
      Unit : mV
      Range: 500-10000
      Default: 1000 
      Step: 100
      "
    ::= { hwPotsLooplineThresholdTable 41 }

 hwMaxRcrTr OBJECT-TYPE
    SYNTAX      Integer32(0..2147483647)
    MAX-ACCESS  read-write
    STATUS      current
    DESCRIPTION
      " 
      maximum RC network resistance between tip and ring
      Unit : ohm
      Range: 0-10000000
      Default: 1000000
      "
    ::= { hwPotsLooplineThresholdTable 42 }

 hwMinRcrTr OBJECT-TYPE
    SYNTAX      Integer32(0..2147483647)
    MAX-ACCESS  read-write
    STATUS      current
    DESCRIPTION
      " 
      minimum RC network resistance between tip and ring
      Unit : ohm
      Range: 0-10000000
      Default: 10000
      "
    ::= { hwPotsLooplineThresholdTable 43 }

 hwCpeCab OBJECT-TYPE
    SYNTAX      Integer32(0..2147483647)
    MAX-ACCESS  read-write
    STATUS      current
    DESCRIPTION
      " 
      minimum RC network capacitance between tip and ring
      Unit : nf
      Range: 0-5000
      Default: 350
      "
    ::= { hwPotsLooplineThresholdTable 44 }

 hwMinhrTr OBJECT-TYPE
    SYNTAX      Integer32(0..2147483647)
    MAX-ACCESS  read-write
    STATUS      current
    DESCRIPTION
      " 
      minimum high resistance between tip and ring
      Unit : ohm 
      Range: 0-10000000
      Default: 1000000
      "
    ::= { hwPotsLooplineThresholdTable 45 }


  hwFvcLim OBJECT-TYPE
    SYNTAX      Integer32(0..2147483647)
    MAX-ACCESS  read-write
    STATUS      current
    DESCRIPTION
      " 
      minimum foreign voltage
      Unit : mV   
      Range: 0-50000
      Default: 8000
      "
    ::= { hwPotsLooplineThresholdTable 46 }

 hwMinOffhookR OBJECT-TYPE
    SYNTAX      Integer32(0..2147483647)
    MAX-ACCESS  read-write
    STATUS      current
    DESCRIPTION
      " 
      minimum equivalent resistance when off-hook on zero kilometres
      Unit : ohm 
      Range: 0-1000
      Default: 200
      "
    ::= { hwPotsLooplineThresholdTable 47 }


  hwLepPar OBJECT-TYPE
    SYNTAX      Integer32(0..2147483647)
    MAX-ACCESS  read-write
    STATUS      current
    DESCRIPTION
      " 
      line length windage for open wire failure
      Unit : m 
      Range: 0-500
      Default: 200
      "
    ::= { hwPotsLooplineThresholdTable 48 }

  hwLooplineThresholdOprType OBJECT-TYPE
    SYNTAX      INTEGER{restore(1), invalid(-1)}
    MAX-ACCESS  read-write
    STATUS      current
    DESCRIPTION
        "Operation type.
         Options:
         1. restore(1)    -restore default threshold value
         2. invalid(-1)   -invalid
        "
    ::= { hwPotsLooplineThresholdTable 49 }   
    
     
    


  hwResistEmendationThresholdTable OBJECT IDENTIFIER ::= { hwNTestMIBObjects 22 }
      
  -- Associated command lines
  -- Name of the resistance calibration threshold for the line test                        Threshold
  -- A-Ground resistance calibration value (ohm)                   0
  -- B-Ground resistance calibration value (ohm)                   0
  -- A-B resistance calibration value (ohm)                    0
  -- Loop resistance calibration value (ohm)                    0
  -- Polarity reversal resistance calibration value (ohm)                  0

 hwAGroundResistanceEmendation OBJECT-TYPE
    SYNTAX      Integer32(0..2147483647)
    MAX-ACCESS  read-write
    STATUS      current
    DESCRIPTION
      " 
      A-Ground resistance calibration value .
      Unit: ohm 
      Default: 0
      "
    ::= { hwResistEmendationThresholdTable 1 }
    
 hwBGroundResistanceEmendation OBJECT-TYPE
    SYNTAX      Integer32(0..2147483647)
    MAX-ACCESS  read-write
    STATUS      current
    DESCRIPTION
      " 
      B-Ground resistance calibration value.
      Unit: ohm
      Default: 0 
      "
    ::= { hwResistEmendationThresholdTable 2 }    
 
 hwABResistanceEmendation OBJECT-TYPE
    SYNTAX      Integer32(0..2147483647)
    MAX-ACCESS  read-write
    STATUS      current
    DESCRIPTION
      " 
      A-B resistance calibration value.
      Unit: ohm
      Default: 0
      "
    ::= { hwResistEmendationThresholdTable 3 }  
      
 hwLoopResistanceEmendation OBJECT-TYPE
    SYNTAX      Integer32(0..2147483647)
    MAX-ACCESS  read-write
    STATUS      current
    DESCRIPTION
      " 
      Loop resistance calibration value.
      Unit: ohm
      Default: 0 
      "
    ::= { hwResistEmendationThresholdTable 4 }      
  
 hwPolarityReversalResistanceEmendation OBJECT-TYPE
    SYNTAX      Integer32(0..2147483647)
    MAX-ACCESS  read-write
    STATUS      current
    DESCRIPTION
      " 
      Polarity reversal resistance calibration value.
      Unit: ohm 
      Default: 0
      "
    ::= { hwResistEmendationThresholdTable 5 }      

 hwTestTimeLimitThresholdTable OBJECT IDENTIFIER ::= { hwNTestMIBObjects 23 }
      
  --Associated command lines show the "test-time-limit"    

  --   Name of the threshold of the timeout control parameter for the line test                       Threshold

  --  Timeout control parameter of the telephone test (minute)                      15
  --  Timeout control parameter of the call emulation test (minute)                      15
  --  Timeout control parameter of the digital subscriber diagnosis test             15

 hwTelephoneTestWaitingAck OBJECT-TYPE
    SYNTAX      Integer32(1..60)
    MAX-ACCESS  read-write
    STATUS      current
    DESCRIPTION
      " 
      Timeout control parameter of the telephone test.
      Unit: minute
      Default: 15 
      "
    ::= { hwTestTimeLimitThresholdTable 1 }
 
 hwRemoteTestWaitingAck OBJECT-TYPE
    SYNTAX      Integer32(1..60)
    MAX-ACCESS  read-write
    STATUS      current
    DESCRIPTION
      " 
      Timeout control parameter of the call emulation test.
      Unit: minute
      Default: 15 
      "
    ::= { hwTestTimeLimitThresholdTable 2 }  
    
 hwIsdnDiagnoseTestWaitingAck OBJECT-TYPE
    SYNTAX      Integer32(1..60)
    MAX-ACCESS  read-write
    STATUS      current
    DESCRIPTION
      " 
      Timeout control parameter of the digital subscriber diagnosis test.
      Unit: minute 
      Default: 15 
      "
    ::= { hwTestTimeLimitThresholdTable 3 }   

  hwSDLMeterTestOprTable OBJECT-TYPE
    SYNTAX SEQUENCE OF HwSDLMeterTestOprEntry
    MAX-ACCESS not-accessible
    STATUS current
    DESCRIPTION          
    "Operation table for the SDL meter test: 
        It realizes the function of the SDL meter test in the system. The test board provides, through the meter test function, the interface connected to the external test meter such as the multimeter.
        The index of this table is ifIndex."
    ::= { hwNTestMIBObjects 24 }


        
  hwSDLMeterTestOprEntry OBJECT-TYPE
    SYNTAX HwSDLMeterTestOprEntry
    MAX-ACCESS not-accessible
    STATUS current
    DESCRIPTION          
    "Operation table for the SDL meter test: 
        It realizes the function of the SDL meter test in the system. The test board provides, through the meter test function, the interface connected to the external test meter such as the multimeter.
        The index of this entry is ifIndex."
        INDEX    {  
                  ifIndex
                 }
    ::= { hwSDLMeterTestOprTable 1 }
    
  HwSDLMeterTestOprEntry ::=
    SEQUENCE { 
        hwSDLMeterTestOprType
            INTEGER,
        hwSDLMeterTestStatus
            INTEGER
     }

  hwSDLMeterTestOprType OBJECT-TYPE
    SYNTAX INTEGER
        {
        stop(1),
        start(2)
        }
    MAX-ACCESS read-create
    STATUS current
    DESCRIPTION
        "Operation type.
         Options:
         1. stop(1)  -stop the test
         2. start(2) -start the test"
    ::= { hwSDLMeterTestOprEntry 1 }
        
  hwSDLMeterTestStatus OBJECT-TYPE
    SYNTAX INTEGER
        {
        success(1),         
        fail(2),            
        portbusy(3),        
        outoftime(4),       
        testingAbnormal(5)  
        }
    MAX-ACCESS read-only
    STATUS current
    DESCRIPTION
        "Test status.
         Options:
         1. success(1)          -indicates normal
         2. fail(2)             -indicates abnormal
         3. portbusy(3)         -indicates busy port
         4. outoftime(4)        -indicates timed-out
         5. testingAbnormal(5)  -indicates test abnormal"
    ::= { hwSDLMeterTestOprEntry 2 }


  hwSDLDMMTestOprTable OBJECT-TYPE
    SYNTAX      SEQUENCE OF HwSDLDMMTestOprEntry
    MAX-ACCESS  not-accessible
    STATUS      current
    DESCRIPTION
      "Operation table for the SDL DMM test: 
      It realizes the function of the SDL DMM test in the system. 
      In the test, the voltage, resistance, and capacitance of the 
      loop line are tested to check for faults such as broken circuit,
      short circuit, grounding and cross-connected line.
      The index of this table is ifIndex"
    ::= { hwNTestMIBObjects 25 }

  hwSDLDMMTestOprEntry OBJECT-TYPE
    SYNTAX      HwSDLDMMTestOprEntry
    MAX-ACCESS  not-accessible
    STATUS      current
    DESCRIPTION
      "Operation table for the SDL DMM test: 
      It realizes the function of the SDL DMM test in the system. 
      In the test, the voltage, resistance, and capacitance of the 
      loop line are tested to check for faults such as broken circuit,
      short circuit, grounding and cross-connected line.
      The index of this entry is ifIndex"
    INDEX    {  
              ifIndex
             }
    ::= { hwSDLDMMTestOprTable 1 }

  HwSDLDMMTestOprEntry ::=
    SEQUENCE
    {
      hwSDLDMMTestOprType       INTEGER,
      hwSDLDMMTestVoltage       INTEGER,
      hwSDLDMMTestResistance    INTEGER,
      hwSDLDMMTestCapacitance   INTEGER,
      hwSDLDMMTestStatus        INTEGER,
      hwSDLDMMTestConclusion    INTEGER,
      hwSDLDMMTestACAG          Integer32,
      hwSDLDMMTestACBG          Integer32,
      hwSDLDMMTestACAB          Integer32,
      hwSDLDMMTestDCAG          Integer32,
      hwSDLDMMTestDCBG          Integer32,
      hwSDLDMMTestDCAB          Integer32,
      hwSDLDMMTestRAG           Integer32,
      hwSDLDMMTestRBG           Integer32,
      hwSDLDMMTestRAB           Integer32,
      hwSDLDMMTestCapAG         Integer32,
      hwSDLDMMTestCapBG         Integer32,
      hwSDLDMMTestCapAB         Integer32
    }

  hwSDLDMMTestOprType OBJECT-TYPE
    SYNTAX      INTEGER{stop(1),start(2)}
    MAX-ACCESS  read-create
    STATUS      current
    DESCRIPTION
        "Describes the Operation type.
         Options: 
            1. stop(1)  -stop the test 
            2. start(2) -start the test  
        "
    ::= { hwSDLDMMTestOprEntry 1 }

  hwSDLDMMTestVoltage OBJECT-TYPE
    SYNTAX      INTEGER{notest(1),test(2)}
    MAX-ACCESS  read-create
    STATUS      current
    DESCRIPTION
        "SDL DMM test-Voltage .
         Options: 
         1. notest(1) -no test is applied
         2. test(2)   -a test is applied 
        "
    ::= { hwSDLDMMTestOprEntry 2 }

  hwSDLDMMTestResistance OBJECT-TYPE
    SYNTAX      INTEGER{notest(1),test(2)}
    MAX-ACCESS  read-create
    STATUS      current
    DESCRIPTION
        "SDL DMM test-Resistance.
         Options: 
         1. notest(1) -no test is applied
         2. test(2)   -a test is applied 
        "
    ::= { hwSDLDMMTestOprEntry 3 }

  hwSDLDMMTestCapacitance OBJECT-TYPE
    SYNTAX      INTEGER{notest(1),test(2)}
    MAX-ACCESS  read-create
    STATUS      current
    DESCRIPTION
        "SDL DMM test-Capacitance.
         Options: 
         1. notest(1) -no test is applied
         2. test(2)   -a test is applied 
        "
    ::= { hwSDLDMMTestOprEntry 4 }

  hwSDLDMMTestStatus OBJECT-TYPE
    SYNTAX      INTEGER{normal(1),abnormal(2),portbusy(3),outoftime(4),testingAbnormal(5)}
    MAX-ACCESS  read-only
    STATUS      current
    DESCRIPTION
        "Test status.
         Options: 
         1. normal(1)           -indicates Normal 
         2. abnormal(2)         -indicates Abnormal 
         3. portbusy(3)         -indicates Busy port 
         4. outoftime(4)        -indicates Timed-out 
         5. testingAbnormal(5)  -indicates Test abnormal
        "
    ::= { hwSDLDMMTestOprEntry 5 }

  hwSDLDMMTestConclusion OBJECT-TYPE
    SYNTAX      INTEGER{normal(1),powerline(2),amix(3),bmix(4),abmix(5),agrnd(6),bgrnd(7),abgrnd(8),selfmix(9),
    abpoorinsulation(10),agleak(11),bgleak(12),abgleak(13),abgleak(14),nomodem(15),unknown(16),abgrndorshortlinenoonu(50),onunotexist(51),normalwithonu(52),abmixnoonu(53),singlegndnoonu(54),singlegndwithonu(55),singlecutoff(56)}
    MAX-ACCESS  read-only
    STATUS      current
    DESCRIPTION
        "Conclusion.
         Options:  
         1. normal(1)                   -indicates Normal
         2. powerline(2)                -indicates Contact of power lines
         3. amix(3)                     -indicates A line mixed with others
         4. bmix(4)                     -indicates B line mixed with others         
         5. abmix(5)                    -indicates Mixed with others (two lines)
         6. agrnd(6)                    -indicates A line grounding
         7. bgrnd(7)                    -indicates B line grounding
         8. abgrnd(8)                   -indicates A and B grounding
         9. selfmix(9)                  -indicates Self-mixed (small resistance, self-mixed)
         10. abpoorinsulation(10)       -indicates A-B poor insulation
         11. agleak(11)                 -indicates A-ground leakage
         12. bgleak(12)                 -indicates B-ground leakage
         13. abgleak(13)                -indicates A and B ground leakage
         14. abgleak(14)                -indicates A-B leakage
         15. nomodem(15)                -indicates Modem not connected
         16. unknown(16)                -indicates Unknown
         17. abgrndorshortlinenoonu(50) -indicates A and B grounding or very short line without ONU
         18. onunotexist(51)            -indicates ONU not connected
         19. normalwithonu(52)          -indicates Normal, ONU04 connected
         20. abmixnoonu(53)             -indicates ONU04 not connected and A-B short circuit
         21. singlegndnoonu(54)         -indicatess ONU04 not connected, A or B line grounding
         22. singlegndwithonu(55)       -indicates ONU04 connected, A or B line grounding
         23. singlecutoff(56)           -indicates A or B line is cutoff
        "
    ::= { hwSDLDMMTestOprEntry 6 }

  hwSDLDMMTestACAG OBJECT-TYPE
    SYNTAX      Integer32
    MAX-ACCESS  read-only
    STATUS      current
    DESCRIPTION
        "A->ground AC voltage.
         Unit: millivolt, ab. mV
        "
    ::= { hwSDLDMMTestOprEntry 7 }

  hwSDLDMMTestACBG OBJECT-TYPE
    SYNTAX      Integer32
    MAX-ACCESS  read-only
    STATUS      current
    DESCRIPTION
        "B->ground AC voltage.
         Unit: millivolt, ab. mV
        "
    ::= { hwSDLDMMTestOprEntry 8 }

  hwSDLDMMTestACAB OBJECT-TYPE
    SYNTAX      Integer32
    MAX-ACCESS  read-only
    STATUS      current
    DESCRIPTION
        "A->B AC voltage. 
         Unit: millivolt, ab. mV
        "
    ::= { hwSDLDMMTestOprEntry 9 }

  hwSDLDMMTestDCAG OBJECT-TYPE
    SYNTAX      Integer32
    MAX-ACCESS  read-only
    STATUS      current
    DESCRIPTION
        "A->ground DC voltage. 
         Unit: millivolt, ab. mV
        "
    ::= { hwSDLDMMTestOprEntry 10 }

  hwSDLDMMTestDCBG OBJECT-TYPE
    SYNTAX      Integer32
    MAX-ACCESS  read-only
    STATUS      current
    DESCRIPTION
        "B->ground DC voltage.  
        Unit: millivolt, ab. mV
       "
    ::= { hwSDLDMMTestOprEntry 11 }

  hwSDLDMMTestDCAB OBJECT-TYPE
    SYNTAX      Integer32
    MAX-ACCESS  read-only
    STATUS      current
    DESCRIPTION
        "A->B DC voltage. 
         Unit: millivolt, ab. mV
        "
    ::= { hwSDLDMMTestOprEntry 12 }

  hwSDLDMMTestRAG OBJECT-TYPE
    SYNTAX      Integer32
    MAX-ACCESS  read-only
    STATUS      current
    DESCRIPTION
        "A->ground insulation resistance. 
         Unit: ohm
        "
    ::= { hwSDLDMMTestOprEntry 13 }

  hwSDLDMMTestRBG OBJECT-TYPE
    SYNTAX      Integer32
    MAX-ACCESS  read-only
    STATUS      current
    DESCRIPTION
        "B->ground insulation resistance.  
         Unit: ohm
        "
    ::= { hwSDLDMMTestOprEntry 14 }

  hwSDLDMMTestRAB OBJECT-TYPE
    SYNTAX      Integer32
    MAX-ACCESS  read-only
    STATUS      current
    DESCRIPTION
        "A->B insulation resistance. 
         Unit: ohm
        "
    ::= { hwSDLDMMTestOprEntry 15 }

  hwSDLDMMTestCapAG OBJECT-TYPE
    SYNTAX      Integer32
    MAX-ACCESS  read-only
    STATUS      current
    DESCRIPTION
        "A->ground capacitance. 
         Unit: nF
        "
    ::= { hwSDLDMMTestOprEntry 16 }

  hwSDLDMMTestCapBG OBJECT-TYPE
    SYNTAX      Integer32
    MAX-ACCESS  read-only
    STATUS      current
    DESCRIPTION
        "B->ground capacitance. 
         Unit: nF
        "
    ::= { hwSDLDMMTestOprEntry 17 }

  hwSDLDMMTestCapAB OBJECT-TYPE
    SYNTAX      Integer32
    MAX-ACCESS  read-only
    STATUS      current
    DESCRIPTION
        "A->B capacitance. 
         Unit: nF
        "
    ::= { hwSDLDMMTestOprEntry 18 }
  

  hwLoopLineToneOprTable OBJECT-TYPE
    SYNTAX SEQUENCE OF HwLoopLineToneOprEntry
    MAX-ACCESS not-accessible
    STATUS current
    DESCRIPTION          
    "Operation table for the loop-line tone test:
        It realizes the function of the test on the circuit and loop-line signals.
      The index of this table is ifIndex.
    "
    ::= { hwNTestMIBObjects 26 }


        
  hwLoopLineToneOprEntry OBJECT-TYPE
    SYNTAX HwLoopLineToneOprEntry
    MAX-ACCESS not-accessible
    STATUS current
    DESCRIPTION          
    "Operation table for the loop-line tone test:
        It realizes the function of the test on the circuit and loop-line signals.
      The index of this entry is ifIndex.
    "
        INDEX    {  
                  ifIndex
                 }
    ::= { hwLoopLineToneOprTable 1 }
    
  HwLoopLineToneOprEntry ::=
    SEQUENCE { 
        hwLoopLineToneOprType
            INTEGER,
        hwLoopLineToneIntensity
            INTEGER,
        hwLoopLineToneBusyFlag
            INTEGER,
        hwLoopLineToneResult
            INTEGER
     }                       

 hwLoopLineToneOprType OBJECT-TYPE
    SYNTAX INTEGER
        {
        check(1),
        send(2),
        stopsend(3)
        }
    MAX-ACCESS read-create
    STATUS current
    DESCRIPTION
        "Operation type. 
         Options:
         1. check(1)    -indicates Detect the signal tone
         2. send(2)     -indicates Send the signal tone 
         3. stopsend(3) -indicates Stop sending the signal tone)
        "
    ::= { hwLoopLineToneOprEntry 1 }
        
  hwLoopLineToneIntensity OBJECT-TYPE
    SYNTAX INTEGER
        {
        fivedB(1),
        tendB(2),
        fifteendB(3)
        }
    MAX-ACCESS read-create
    STATUS current
    DESCRIPTION
        "Signal tone intensity.
         Options:
         1. fivedB(1)    -indicates 5 dB 
         2. tendB(2)     -indicates 10 dB 
         3. fifteendB(3) -indicates 15 dB
        "
    ::= { hwLoopLineToneOprEntry 2 }
    
  hwLoopLineToneBusyFlag    OBJECT-TYPE
    SYNTAX INTEGER
        {
        busynotest(1),
        busystrentest(2)
        }
    MAX-ACCESS read-create
    STATUS current
    DESCRIPTION
        "Busy control flag.
         Options:
         1. busynotest(1)    -indicates no test when busy
         2. busystrentest(2) -indicates Forced test when busy
        "
    ::= { hwLoopLineToneOprEntry 3 }

  hwLoopLineToneResult  OBJECT-TYPE
    SYNTAX INTEGER
        {
        succeed(1),
        failed(2)
        }
    MAX-ACCESS read-only
    STATUS current
    DESCRIPTION
        "Operation result.
         Options:
         1. succeed(1)  -indicates successful
         2. failed(2)   -indicates failed
        "
    ::= { hwLoopLineToneOprEntry 4 }
    

  hwPotsSelfCircuitTestOprTable OBJECT-TYPE
    SYNTAX      SEQUENCE OF HwPotsSelfCircuitTestOprEntry
    MAX-ACCESS  not-accessible
    STATUS      current
    DESCRIPTION
      "Operation table for the PSTN subscriber circuit test.
       The index of this table is ifIndex."
    ::= { hwNTestMIBObjects 27 }

  hwPotsSelfCircuitTestOprEntry OBJECT-TYPE
    SYNTAX      HwPotsSelfCircuitTestOprEntry
    MAX-ACCESS  not-accessible
    STATUS      current
    DESCRIPTION
      "Operation table for the PSTN subscriber circuit test.
       The index of this entry is ifIndex."
    INDEX    {  
              ifIndex
             }
    ::= { hwPotsSelfCircuitTestOprTable 1 }

  HwPotsSelfCircuitTestOprEntry ::=
    SEQUENCE
    {
      hwPotsSelfCircuitTestOprType          INTEGER,  
      hwPotsSelfCircuitTestBusyProcFlag     INTEGER, 
      hwPotsSelfCircuitTestStatus           INTEGER, 
      hwPotsSelfCircuitTestVDDResult        INTEGER, 
      hwPotsSelfCircuitTestVBATLResult      INTEGER, 
      hwPotsSelfCircuitTestVBATHResult      INTEGER, 
      hwPotsSelfCircuitTestVBATRResult      INTEGER, 
      hwPotsSelfCircuitTestLoopCurrentResult  INTEGER, 
      hwPotsSelfCircuitTestFeedVResult      INTEGER, 
      hwPotsSelfCircuitTestRingVResult      INTEGER, 
      hwPotsSelfCircuitTestRingFResult      INTEGER,
      hwPotsSelfCircuitTestVAGResult        INTEGER,
      hwPotsSelfCircuitTestVBGResult        INTEGER,
      hwPotsSelfCircuitTestDeferredTime     Integer32,
      hwPotsSelfCircuitTestTimeoutProc      INTEGER,
      hwPotsSelfCircuitTestFeedVValue       Integer32,
      hwPotsSelfCircuitTestRingVValue       Integer32,
      hwPotsSelfCircuitTestLoopCurrentValue Integer32,
      hwPotsSelfCircuitTestLoopIfIndex      Integer32,
      hwPotsSelfCircuitTestLoopRequestID    Integer32,
      hwPotsSelfCircuitTestOnHookDetectResult   INTEGER,  
      hwPotsSelfCircuitTestOffHookDetectResult  INTEGER,  
      hwPotsSelfCircuitTestStopRingResult       INTEGER,  
      hwPotsSelfCircuitTestVPoleResult          INTEGER,  
      hwPotsSelfCircuitTestVBATLValue           Integer32,
      hwPotsSelfCircuitTestVBATHValue           Integer32,
      hwPotsSelfCircuitTestVBATRValue           Integer32,
      hwPotsSelfCircuitTestRingFValue           Integer32,
      hwPotsSelfCircuitTestVAGValue             Integer32,
      hwPotsSelfCircuitTestVBGValue             Integer32,
      hwPotsSelfCircuitTestVABPoleValue         Integer32,
      hwPotsSelfCircuitTestABLCurrentValue      Integer32,
      hwPotsSelfCircuitTestSLICTempValue        Integer32
    }

  hwPotsSelfCircuitTestOprType OBJECT-TYPE
    SYNTAX      INTEGER{stop(1),start(2)}
    MAX-ACCESS  read-create
    STATUS      current
    DESCRIPTION
        "Circuit test-Operation type.
         Options:
         1. stop(1)  -stop the test
         2. start(2) -start the test
        "
    ::= { hwPotsSelfCircuitTestOprEntry 1 }

  hwPotsSelfCircuitTestBusyProcFlag OBJECT-TYPE
    SYNTAX      INTEGER{busynotest(1),busytest(2),busystrentest(3),deferredtest(4)}
    MAX-ACCESS  read-create
    STATUS      current
    DESCRIPTION
        "Circuit test-Busy control.
         Options: 
          1. busynotest(1)    -indicates no test when busy 
          2. busytest(2)      -indicates remedy test when busy 
          3. busystrentest(3) -indicates force to test when busy 
          4. deferredtest(4)  -indicates defer test when busy:
           If the port is busy, the test operation will be deferred. If the port changes to idle state before 
         time out, circuit test will be executed immediately. If the port keeps busy by the time out, 
         the system will excecute a corresponding operation according to what the user specified: canceling 
         the test or forcing to test.
           If the value of this leaf node is deferredtest(4), both hwPotsSelfCircuitTestDeferredTime and 
         hwPotsSelfCircuitTestTimeoutProc must be set."
    ::= { hwPotsSelfCircuitTestOprEntry 2 }
    
  hwPotsSelfCircuitTestStatus OBJECT-TYPE
    SYNTAX      INTEGER{normal(1),testfail(2),portbusy(3),outoftime(4),testingAbnormal(5),testcanceled(6)}
    MAX-ACCESS  read-only
    STATUS      current
    DESCRIPTION
        "Circuit test-Test status.
         Options:
         1. normal(1)          -indicates Normal
         2. testfail(2)        -indicates Abnormal 
         3. portbusy(3)        -indicates Busy port
         4. outoftime(4)       -indicates Timed-out
         5. testingAbnormal(5) -indicates Test abnormal
         6. testcanceled(6)    -indicates Test is canceled
        "
    ::= { hwPotsSelfCircuitTestOprEntry 3 }
    
  hwPotsSelfCircuitTestVDDResult OBJECT-TYPE
    SYNTAX      INTEGER{normal(1),abnormal(2),notsupport(3)}
    MAX-ACCESS  read-only
    STATUS      current
    DESCRIPTION
        "Circuit test result-VDD result.
         Options: 
         1. normal(1)      -indicates the test result is normal
         2. abnormal(2)    -indicates the test result is abnormal   
         3. notsupport(3)  -indicates the test result is notsupport 
        "
    ::= { hwPotsSelfCircuitTestOprEntry 4 }
    
  hwPotsSelfCircuitTestVBATLResult OBJECT-TYPE
    SYNTAX      INTEGER{normal(1),abnormal(2),notsupport(3)}
    MAX-ACCESS  read-only
    STATUS      current
    DESCRIPTION
        "Circuit test result-VBATL result.
         Options: 
         1. normal(1)      -indicates the test result is normal
         2. abnormal(2)    -indicates the test result is abnormal
         3. notsupport(3)  -indicates the test result is notsupport
        "
    ::= { hwPotsSelfCircuitTestOprEntry 5 }
    
  hwPotsSelfCircuitTestVBATHResult OBJECT-TYPE
    SYNTAX      INTEGER{normal(1),abnormal(2),notsupport(3)}
    MAX-ACCESS  read-only
    STATUS      current
    DESCRIPTION
        "Circuit test result-VBATH result.
         Options: 
         1. normal(1)      -indicates the test result is normal
         2. abnormal(2)    -indicates the test result is abnormal 
         3. notsupport(3)  -indicates the test result is notsupport
        "
    ::= { hwPotsSelfCircuitTestOprEntry 6 }
    
  hwPotsSelfCircuitTestVBATRResult OBJECT-TYPE
    SYNTAX      INTEGER{normal(1),abnormal(2),notsupport(3)}
    MAX-ACCESS  read-only
    STATUS      current
    DESCRIPTION
        "Circuit test result-VBATR result.
         Options: 
         1. normal(1)      -indicates the test result is normal
         2. abnormal(2)    -indicates the test result is abnormal 
         3. notsupport(3)  -indicates the test result is notsupport
        "
    ::= { hwPotsSelfCircuitTestOprEntry 7 }

  hwPotsSelfCircuitTestLoopCurrentResult OBJECT-TYPE
    SYNTAX      INTEGER{normal(1),abnormal(2),notsupport(3)}
    MAX-ACCESS  read-only
    STATUS      current
    DESCRIPTION
        "Circuit test result-Loop current result.
         Options: 
         1. normal(1)      -indicates the test result is normal
         2. abnormal(2)    -indicates the test result is abnormal  
         3. notsupport(3)  -indicates the test result is notsupport
        "
    ::= { hwPotsSelfCircuitTestOprEntry 8 }

  hwPotsSelfCircuitTestFeedVResult OBJECT-TYPE
    SYNTAX      INTEGER{normal(1),abnormal(2),notsupport(3)}
    MAX-ACCESS  read-only
    STATUS      current
    DESCRIPTION
        "Circuit test result-Feeder voltage result.
         Options: 
         1. normal(1)      -indicates the test result is normal
         2. abnormal(2)    -indicates the test result is abnormal 
         3. notsupport(3)  -indicates the test result is notsupport
        "
    ::= { hwPotsSelfCircuitTestOprEntry 9 }

  hwPotsSelfCircuitTestRingVResult OBJECT-TYPE
    SYNTAX      INTEGER{normal(1),abnormal(2),notsupport(3)}
    MAX-ACCESS  read-only
    STATUS      current
    DESCRIPTION
        "Circuit test result-Ring voltage result.
         Options: 
         1. normal(1)      -indicates the test result is normal
         2. abnormal(2)    -indicates the test result is abnormal
         3. notsupport(3)  -indicates the test result is notsupport
        "
    ::= { hwPotsSelfCircuitTestOprEntry 10 }

  hwPotsSelfCircuitTestRingFResult OBJECT-TYPE
    SYNTAX      INTEGER{normal(1),abnormal(2),notsupport(3)}
    MAX-ACCESS  read-only
    STATUS      current
    DESCRIPTION
        "Circuit test result-Ring frequency result.
         Options: 
         1. normal(1)      -indicates the test result is normal
         2. abnormal(2)    -indicates the test result is abnormal
         3. notsupport(3)  -indicates the test result is notsupport
        "
    ::= { hwPotsSelfCircuitTestOprEntry 11 }
    
  hwPotsSelfCircuitTestVAGResult OBJECT-TYPE
    SYNTAX      INTEGER{normal(1),abnormal(2),notsupport(3)}
    MAX-ACCESS  read-only
    STATUS      current
    DESCRIPTION
        "Circuit test result-A->ground voltage result.
         Options: 
         1. normal(1)      -indicates the test result is normal
         2. abnormal(2)    -indicates the test result is abnormal
         3. notsupport(3)  -indicates the test result is notsupport
        "
    ::= { hwPotsSelfCircuitTestOprEntry 12 }
    
  hwPotsSelfCircuitTestVBGResult OBJECT-TYPE
    SYNTAX      INTEGER{normal(1),abnormal(2),notsupport(3)}
    MAX-ACCESS  read-only
    STATUS      current
    DESCRIPTION
        "Circuit test result-B->ground voltage result.
         Options: 
         1. normal(1)      -indicates the test result is normal
         2. abnormal(2)    -indicates the test result is abnormal 
         3. notsupport(3)  -indicates the test result is notsupport
        "
    ::= { hwPotsSelfCircuitTestOprEntry 13 }
    
  hwPotsSelfCircuitTestDeferredTime OBJECT-TYPE
    SYNTAX      Integer32(-1 | 1..1440)
    MAX-ACCESS  read-create
    STATUS      current
    DESCRIPTION
      "deferred time
       Unit: minute
         this leaf node is valid only when the value of hwPotsSelfCircuitTestBusyProcFlag is deferredtest(4).
       Default: 30(minute).     
      "
    DEFVAL { 30 }
            ::= { hwPotsSelfCircuitTestOprEntry 14 }
            
  hwPotsSelfCircuitTestTimeoutProc OBJECT-TYPE
    SYNTAX INTEGER
        {
        notest(1),
        test(2)
        }
    MAX-ACCESS read-create
    STATUS current
    DESCRIPTION
        "timeout proc:
         Options: 
          1. notest(1) -indicates when deferred time out, if the port is still busy, test will be canceled 
          2. test(2)   -indicates when deferred time out, if the port is still busy, test will be preformed by force.
        this leaf node is valid only when the value of hwPotsSelfCircuitTestBusyProcFlag is deferredtest(4).
        Default: notest(1)."
    DEFVAL { 1 }
    ::= { hwPotsSelfCircuitTestOprEntry 15 }     

  hwPotsSelfCircuitTestFeedVValue OBJECT-TYPE
    SYNTAX      Integer32
    MAX-ACCESS  read-only
    STATUS      current
    DESCRIPTION
        "Circuit Test Result-Feeder voltage 
         Unit: millivolt, mV
        "
    ::= { hwPotsSelfCircuitTestOprEntry 16 }

  hwPotsSelfCircuitTestRingVValue OBJECT-TYPE
    SYNTAX      Integer32
    MAX-ACCESS  read-only
    STATUS      current
    DESCRIPTION
        "Circuit Test Result-Ringing current voltage 
         Unit: millivolt, mV
        "
    ::= { hwPotsSelfCircuitTestOprEntry 17 }

  hwPotsSelfCircuitTestLoopCurrentValue OBJECT-TYPE
    SYNTAX      Integer32
    MAX-ACCESS  read-only
    STATUS      current
    DESCRIPTION
        "Circuit Test Result-Loop current 
         Unit: millivolt, mV
        "
    ::= { hwPotsSelfCircuitTestOprEntry 18 }
    
  hwPotsSelfCircuitTestLoopIfIndex OBJECT-TYPE
    SYNTAX      Integer32
    MAX-ACCESS  read-only
    STATUS      current
    DESCRIPTION
        "Port Index"
    ::= { hwPotsSelfCircuitTestOprEntry 19 }
    
  hwPotsSelfCircuitTestLoopRequestID OBJECT-TYPE
    SYNTAX      Integer32
    MAX-ACCESS  read-only
    STATUS      current
    DESCRIPTION
        "Request ID"
    ::= { hwPotsSelfCircuitTestOprEntry 20 }
 
   hwPotsSelfCircuitTestOnHookDetectResult OBJECT-TYPE
    SYNTAX      INTEGER{normal(1),abnormal(2),notsupport(3)}
    MAX-ACCESS  read-only
    STATUS      current
    DESCRIPTION
        "Circuit test OnHookDetect result.
         Options: 
         1. normal(1)      -indicates the test result is normal
         2. abnormal(2)    -indicates the test result is abnormal
         3. notsupport(3)  -indicates the test result is notsupport
        "
    ::= { hwPotsSelfCircuitTestOprEntry 21 }
    
   hwPotsSelfCircuitTestOffHookDetectResult OBJECT-TYPE
    SYNTAX      INTEGER{normal(1),abnormal(2),notsupport(3)}
    MAX-ACCESS  read-only
    STATUS      current
    DESCRIPTION
        "Circuit test OffHookDetect result.
         Options: 
         1. normal(1)      -indicates the test result is normal
         2. abnormal(2)    -indicates the test result is abnormal 
         3. notsupport(3)  -indicates the test result is notsupport
        "
    ::= { hwPotsSelfCircuitTestOprEntry 22 }    
 
    hwPotsSelfCircuitTestStopRingResult OBJECT-TYPE
    SYNTAX      INTEGER{normal(1),abnormal(2),notsupport(3)}
    MAX-ACCESS  read-only
    STATUS      current
    DESCRIPTION
        "Circuit test StopRing result.
         Options: 
         1. normal(1)      -indicates the test result is normal
         2. abnormal(2)    -indicates the test result is abnormal 
         3. notsupport(3)  -indicates the test result is notsupport
        "
    ::= { hwPotsSelfCircuitTestOprEntry 23 }

    hwPotsSelfCircuitTestVPoleResult OBJECT-TYPE
    SYNTAX      INTEGER{normal(1),abnormal(2),notsupport(3)}
    MAX-ACCESS  read-only
    STATUS      current
    DESCRIPTION
        "Circuit test VPole result.
         Options: 
         1. normal(1)      -indicates the test result is normal
         2. abnormal(2)    -indicates the test result is abnormal 
         3. notsupport(3)  -indicates the test result is notsupport
        "
    ::= { hwPotsSelfCircuitTestOprEntry 24 }
    
   hwPotsSelfCircuitTestVBATLValue OBJECT-TYPE
    SYNTAX      Integer32
    MAX-ACCESS  read-only
    STATUS      current
    DESCRIPTION
        "Circuit Test VBATL Value 
         Unit: mV
        "
    ::= { hwPotsSelfCircuitTestOprEntry 25 }
 
    hwPotsSelfCircuitTestVBATHValue OBJECT-TYPE
    SYNTAX      Integer32
    MAX-ACCESS  read-only
    STATUS      current
    DESCRIPTION
        "Circuit Test VBATH Value 
         Unit: mV
        "
    ::= { hwPotsSelfCircuitTestOprEntry 26 } 
    
    hwPotsSelfCircuitTestVBATRValue OBJECT-TYPE
    SYNTAX      Integer32
    MAX-ACCESS  read-only
    STATUS      current
    DESCRIPTION
        "Circuit Test VBATR Value 
         Unit: mV
        "
    ::= { hwPotsSelfCircuitTestOprEntry 27 }
    
    hwPotsSelfCircuitTestRingFValue OBJECT-TYPE
    SYNTAX      Integer32
    MAX-ACCESS  read-only
    STATUS      current
    DESCRIPTION
        "Circuit Test Ring Frequency Value 
         Unit: HZ
        "
    ::= { hwPotsSelfCircuitTestOprEntry 28 }   
    
    hwPotsSelfCircuitTestVAGValue OBJECT-TYPE
    SYNTAX      Integer32
    MAX-ACCESS  read-only
    STATUS      current
    DESCRIPTION
        "Circuit Test A->Ground Value 
         Unit: mV
        "
    ::= { hwPotsSelfCircuitTestOprEntry 29 } 
    
    hwPotsSelfCircuitTestVBGValue OBJECT-TYPE
    SYNTAX      Integer32
    MAX-ACCESS  read-only
    STATUS      current
    DESCRIPTION
        "Circuit Test B->Ground Value 
         Unit: mV
        "
    ::= { hwPotsSelfCircuitTestOprEntry 30 } 
    
    hwPotsSelfCircuitTestVABPoleValue OBJECT-TYPE
    SYNTAX      Integer32
    MAX-ACCESS  read-only
    STATUS      current
    DESCRIPTION
        "Circuit Test A->B Pole Voltage Value 
         Unit: mV
        "
    ::= { hwPotsSelfCircuitTestOprEntry 31 }
    
    hwPotsSelfCircuitTestABLCurrentValue OBJECT-TYPE
    SYNTAX      Integer32
    MAX-ACCESS  read-only
    STATUS      current
    DESCRIPTION
        "Circuit Test A->B Current  Value 
         Unit: uA
        "
    ::= { hwPotsSelfCircuitTestOprEntry 32 } 
    
    hwPotsSelfCircuitTestSLICTempValue OBJECT-TYPE
    SYNTAX      Integer32
    MAX-ACCESS  read-only
    STATUS      current
    DESCRIPTION
        "Circuit SLIC Temp  Value 
         Unit: oC
        "
    ::= { hwPotsSelfCircuitTestOprEntry 33 }
                                   
                            
  hwPstnCircuitTestTrap NOTIFICATION-TYPE
    OBJECTS { hwPstnCircuitTestStatus,
              hwPstnCircuitTestOffHookResult,
              hwPstnCircuitTestDialToneResult,
              hwPstnCircuitTestReceivePulseResult,
              hwPstnCircuitTestReceiveDTMFResult,
              hwPstnCircuitTestRingBackResult,
              hwPstnCircuitTestBusyToneResult,
              hwPstnCircuitTestBatteryFeedResult,
              hwPstnCircuitTestPoleDetectResult,
              hwPstnCircuitTestOnHookResult,
              hwPstnCircuitTestRingResult,
              hwPstnCircuitTestStopRingResult,
              hwPstnCircuitTestFeedVValue,
              hwPstnCircuitTestFeedVResult,
              hwPstnCircuitTestRingVValue,
              hwPstnCircuitTestRingVResult,
              hwPstnCircuitTestLoopCurrentValue,
              hwPstnCircuitTestLoopCurrentResult }
    STATUS current
    DESCRIPTION
            "PSTN subscriber circuit test result trap:
             1. hwPstnCircuitTestStatus 
             2. hwPstnCircuitTestOffHookResult 
             3. hwPstnCircuitTestDialToneResult 
             4. hwPstnCircuitTestReceivePulseResult 
             5. hwPstnCircuitTestReceiveDTMFResult 
             6. hwPstnCircuitTestRingBackResult 
             7. hwPstnCircuitTestBusyToneResult 
             8. hwPstnCircuitTestBatteryFeedResult 
             9. hwPstnCircuitTestPoleDetectResult 
             10. hwPstnCircuitTestOnHookResult 
             11. hwPstnCircuitTestRingResult 
             12. hwPstnCircuitTestStopRingResult 
             13. hwPstnCircuitTestFeedVValue 
             14. hwPstnCircuitTestFeedVResult 
             15. hwPstnCircuitTestRingVValue 
             16. hwPstnCircuitTestRingVResult 
             17. hwPstnCircuitTestLoopCurrentValue 
             18. hwPstnCircuitTestLoopCurrentResult"
    ::= { hwNTestGeneralTrapsOIDs 50 }
    
  hw112UserRingTestTrap NOTIFICATION-TYPE
    OBJECTS { hw112UserRingTestResult }
    STATUS current
    DESCRIPTION                
            "This notification indicates that the 112 PSTN subscriber ring test result trap: 1: hw112UserRingTestResult"
    ::= { hwNTestGeneralTrapsOIDs 51 }
    
  hw112UserDialTestTrap NOTIFICATION-TYPE
    OBJECTS { hw112UserDialTestResult,hw112UserDialTestDigit,hw112UserDialTestLowLevel,hw112UserDialTestHighLevel,hw112UserDialTestLowFreq,hw112UserDialTestHighFreq,hw112UserDialTestPulseLen,hw112UserDialTestMakeDur,hw112UserDialTestBreakDur }
    STATUS current
    DESCRIPTION
            "This notification indicates the 112 PSTN subscriber dial test result trap:
             1: hw112UserDialTestResult; 
             2: hw112UserDialTestDigit; 
             3: hw112UserDialTestLowLevel; 
             4: hw112UserDialTestHighLevel; 
             5: hw112UserDialTestLowFreq; 
             6: hw112UserDialTestHighFreq; 
             7: hw112UserDialTestPulseLen; 
             8: hw112UserDialTestMakeDur; 
             9: hw112UserDialTestBreakDur"
    ::= { hwNTestGeneralTrapsOIDs 52 }
        
  hw112UserHowlerTestTrap NOTIFICATION-TYPE
    OBJECTS { hw112UserHowlerTestResult }
    STATUS current
    DESCRIPTION
            "This notification indicates that the 112 PSTN subscriber howler test result trap: 1:hw112UserHowlerTestResult"
    ::= { hwNTestGeneralTrapsOIDs 53 }

        
  hwIsdnUserInTestTrap NOTIFICATION-TYPE
    OBJECTS { hwIsdnUserInTestStatus,hwIsdnUserInTestActiveResult,hwIsdnUserInTestDeactiveResult,hwIsdnUserInTestLtSupplyPowerCap,hwIsdnUserInTestLtSupplyPowerCapResult,hwIsdnUserInTestLtCurrentProctectResult,hwIsdnUserInTestCutLineVolVal,hwIsdnUserInTestCutLineVolResult,hwIsdnUserInTestSwitchOnVolVal,hwIsdnUserInTestSwitchOnVolResult }
    STATUS current
    DESCRIPTION
            "This notification indicates the ISDN subscriber circuit test result trap:
             1: hwIsdnUserInTestStatus; 
             2: hwIsdnUserInTestActiveResult; 
             3: hwIsdnUserInTestDeactiveResult; 
             4: hwIsdnUserInTestLtSupplyPowerCap; 
             5: hwIsdnUserInTestLtSupplyPowerCapResult; 
             6: hwIsdnUserInTestLtCurrentProctectResult; 
             7: hwIsdnUserInTestCutLineVolVal; 
             8: hwIsdnUserInTestCutLineVolResult; 
             9: hwIsdnUserInTestSwitchOnVolVal; 
             10: hwIsdnUserInTestSwitchOnVolResult
             "
    ::= { hwNTestGeneralTrapsOIDs 54 }
        
  hwIsdnUserOutTestTrap NOTIFICATION-TYPE
    OBJECTS { hwIsdnUserOutTestStatus,hwIsdnUserOutTestActNT1Result,hwIsdnUserOutTestDeactNT1Result,hwIsdnUserOutTestTransBitErrorResult,hwIsdnUserOutTestTotalSend,hwIsdnUserOutTestCodeErrorNumber,hwIsdnUserOutTestCodeErrorRate }
    STATUS current
    DESCRIPTION
            "This notification indicates that the ISDN subscriber loop-line test result trap:
             1: hwIsdnUserOutTestStatus; 
             2: hwIsdnUserOutTestActNT1Result; 
             3: hwIsdnUserOutTestDeactNT1Result; 
             4: hwIsdnUserOutTestTransBitErrorResult; 
             5: hwIsdnUserOutTestTotalSend; 
             6: hwIsdnUserOutTestCodeErrorNumber; 
             7: hwIsdnUserOutTestCodeErrorRate"
    ::= { hwNTestGeneralTrapsOIDs 55 }
        
  hwIsdnUserOutLineTestTrap NOTIFICATION-TYPE
    OBJECTS { hwIsdnUserOutLineTestStatus,hwIsdnUserOutLineTestConclusion,hwIsdnUserOutLineTestACAG,hwIsdnUserOutLineTestACBG,hwIsdnUserOutLineTestACAB,hwIsdnUserOutLineTestDCAG,hwIsdnUserOutLineTestDCBG,hwIsdnUserOutLineTestDCAB,hwIsdnUserOutLineTestRAG,hwIsdnUserOutLineTestRBG,hwIsdnUserOutLineTestRAB,hwIsdnUserOutLineTestCapAG,hwIsdnUserOutLineTestCapBG,hwIsdnUserOutLineTestCapAB,hwIsdnUserOutLineTestImpedanceAB,hwIsdnUserOutLineTestImpedanceBA,hwIsdnUserOutLineTestImpedanceAG,hwIsdnUserOutLineTestImpedanceBG,hwIsdnUserOutLineTestACCurrentAG,hwIsdnUserOutLineTestACCurrentBG,hwIsdnUserOutLineTestACCurrentAB,hwIsdnUserOutLineTestDCCurrentAG,hwIsdnUserOutLineTestDCCurrentBG,hwIsdnUserOutLineTestDCCurrentAB,hwIsdnUserOutLineTestLC,hwIsdnUserOutLineTestN }
    STATUS current
    DESCRIPTION
            "This notification indicates that the ISDN subscriber loop-line test result trap:
             1: hwIsdnUserOutLineTestStatus; 
             2: hwIsdnUserOutLineTestConclusion; 
             3: hwIsdnUserOutLineTestACAG; 
             4: hwIsdnUserOutLineTestACBG; 
             5: hwIsdnUserOutLineTestACAB; 
             6: hwIsdnUserOutLineTestDCAG; 
             7: hwIsdnUserOutLineTestDCBG; 
             8: hwIsdnUserOutLineTestDCAB; 
             9: hwIsdnUserOutLineTestRAG; 
             10: hwIsdnUserOutLineTestRBG; 
             11: hwIsdnUserOutLineTestRAB; 
             12: hwIsdnUserOutLineTestCapAG; 
             13: hwIsdnUserOutLineTestCapBG; 
             14: hwIsdnUserOutLineTestCapAB; 
             15: hwIsdnUserOutLineTestImpedanceAB; 
             16: hwIsdnUserOutLineTestImpedanceBA; 
             17: hwIsdnUserOutLineTestImpedanceAG; 
             18: hwIsdnUserOutLineTestImpedanceBG; 
             19: hwIsdnUserOutLineTestACCurrentAG; 
             20: hwIsdnUserOutLineTestACCurrentBG; 
             21: hwIsdnUserOutLineTestACCurrentAB; 
             22: hwIsdnUserOutLineTestDCCurrentAG; 
             23: hwIsdnUserOutLineTestDCCurrentBG; 
             24: hwIsdnUserOutLineTestDCCurrentAB; 
             25: hwIsdnUserOutLineTestLC; 
             26: hwIsdnUserOutLineTestN"
    ::= { hwNTestGeneralTrapsOIDs 56 }
    
  hwIsdnPortStateSwitchTestTrap NOTIFICATION-TYPE
    OBJECTS { hwIsdnPortStateSwitchTestStatus }
    STATUS current
    DESCRIPTION
            "This notification indicates that the trap for the result of switching the ISDN subscriber port: 1: hwIsdnPortStateSwitchTestStatus"
    ::= { hwNTestGeneralTrapsOIDs 57 }
        
  hw112IsdnDiagnoseTrap NOTIFICATION-TYPE
    OBJECTS { hw112IsdnDiagnoseTestRequestID, hw112IsdnDiagnoseTestResult, hw112IsdnDiagnoseTestIfIndex }
    STATUS current
    DESCRIPTION
            "This notification indicates that the trap for the result of 112 ISDN subscriber diagnosis test: 
            1: hw112IsdnDiagnoseTestRequestID; 
            2: hw112IsdnDiagnoseTestResult;
            3: hw112IsdnDiagnoseTestIfIndex"                
    ::= { hwNTestGeneralTrapsOIDs 58 }
        
  hwPstnCallerEmulateOperatorTrap NOTIFICATION-TYPE
    OBJECTS { hwPstnCallerEmulateTestRequestID,hwPstnCallerEmulateTestStatus,hwPstnCallerEmulateTestResult,ifIndex }
    STATUS current
    DESCRIPTION
            "This notification indicates that the trap for the result of the PSTN call emulation test (calling party): 
            1: hwPstnCallerEmulateTestRequestID
            2: hwPstnCallerEmulateTestStatus
            3: hwPstnCallerEmulateTestResult
            4: ifIndex"
    ::= { hwNTestGeneralTrapsOIDs 59 }
    
  hwPstnCalledEmulateOperatorTrap NOTIFICATION-TYPE
    OBJECTS { hwPstnCalledEmulateTestRequestID,hwPstnCalledEmulateTestStatus,hwPstnCalledEmulateTestResult,ifIndex }
    STATUS current
    DESCRIPTION
            "This notification indicates that the trap for the result of the PSTN call emulation test (called party): 
            1: hwPstnCalledEmulateTestRequestID            
            2: hwPstnCalledEmulateTestStatus
            3: hwPstnCalledEmulateTestResult
            4: ifIndex"
    ::= { hwNTestGeneralTrapsOIDs 60 }
        
  hwPstnTelephoneTestOperatorTrap NOTIFICATION-TYPE
    OBJECTS { hwPstnTelephoneTestStatus,hwPstnTelephoneTestLoopResist,hwPstnTelephoneTestHookingTime,hwPstnTelephoneTestReverse,hwPstnTelephoneTestDialDigit,hwPstnTelephoneTestPulseLen,hwPstnTelephoneTestMakeDur,hwPstnTelephoneTestBreakDur,hwPstnTelephoneTestAssisTelno }
    STATUS current
    DESCRIPTION
            "This notification indicates that the trap for the result of the PSTN telephone test:
             1: hwPstnTelephoneTestStatus; 
             2: hwPstnTelephoneTestLoopResist; 
             3: hwPstnTelephoneTestHookingTime; 
             4: hwPstnTelephoneTestReverse; 
             5: hwPstnTelephoneTestDialDigit; 
             6: hwPstnTelephoneTestPulseLen; 
             7: hwPstnTelephoneTestMakeDur; 
             8: hwPstnTelephoneTestBreakDur; 
             9: hwPstnTelephoneTestAssisTelno"
    ::= { hwNTestGeneralTrapsOIDs 61 }
    
  hwIsdnUserDiagnoseTestOperatorTrap NOTIFICATION-TYPE
    OBJECTS { hwIsdnUserDiagnoseTestStatus }
    STATUS current
    DESCRIPTION
            "This notification indicates that the trap for the ISDN subscriber diagnosis test: 
            1: hwIsdnUserDiagnoseTestStatus"
    ::= { hwNTestGeneralTrapsOIDs 62 }
        
  hwPstnSignalToneTestOperatorTrap NOTIFICATION-TYPE
    OBJECTS { hwPstnSignalToneTestRequestID, hwPstnSignalToneTestResult, hwPstnSignalToneTestDTDelayTime, ifIndex, hwPstnSignalToneActualDeferTime, hwPstnSignalToneTestDTStop }
    STATUS current
    DESCRIPTION
            "This notification indicates that the trap for the result of the PSTN signal tone test: 
            1: hwPstnSignalToneTestRequestID;
            2: hwPstnSignalToneTestResult; 
            3: hwPstnSignalToneTestDTDelayTime;
            4: ifIndex;
            5: hwPstnSignalToneActualDeferTime;
            6: hwPstnSignalToneTestDTStop"
    ::= { hwNTestGeneralTrapsOIDs 63 }
        
  hwIsdnMeterTestOperatorTrap NOTIFICATION-TYPE
    OBJECTS { hwIsdnMeterTestStatus }
    STATUS current
    DESCRIPTION 
        "This notification indicates that the trap for the result of the ISDN meter test: 
        1: hwIsdnMeterTestStatus"
    ::= { hwNTestGeneralTrapsOIDs 64 }


  hwTestBusTestTrap NOTIFICATION-TYPE
    OBJECTS { hwTestBusTestResult, hwTestBusTestVoltage, hwTestBusTestResistance, hwTestBusTestCapacitance }
    STATUS current
    DESCRIPTION
            "This notification indicates that the trap for the result of the bus test: 
            1: hwTestBusTestResult; 
            2: hwTestBusTestVoltage; 
            3: hwTestBusTestResistance; 
            4: hwTestBusTestCapacitance"
    ::= { hwNTestGeneralTrapsOIDs 65 }     

  hwFrameLooplineAdjustTrap NOTIFICATION-TYPE
    OBJECTS { 
             hwFrameLooplineAdjustRequestID, 
             hwFrameLooplineAdjustResult, 
             hwFrameLooplineAdjustOprCab, 
             hwFrameLooplineAdjustOprCag, 
             hwFrameLooplineAdjustOprCbg, 
             hwFrameLooplineAdjustOprRab,
             hwFrameLooplineAdjustFrameIndex
            }
    STATUS current
    DESCRIPTION
           "This notification indicates that the trap for the result of the loop-line test calibration value: 
           1: hwFrameLooplineAdjustRequestID; 
           2: hwFrameLooplineAdjustResult; 
           3: hwFrameLooplineAdjustOprCab; 
           4: hwFrameLooplineAdjustOprCag; 
           5: hwFrameLooplineAdjustOprCbg; 
           6: hwFrameLooplineAdjustOprRab;
           7: hwFrameLooplineAdjustFrameIndex"
    ::= { hwNTestGeneralTrapsOIDs 66 }

  hwSDLMeterTestOperatorTrap NOTIFICATION-TYPE
    OBJECTS { hwSDLMeterTestStatus }
    STATUS current
    DESCRIPTION 
        "This notification indicates that the trap for the result of the SDL meter test: 1: hwSDLMeterTestStatus"
    ::= { hwNTestGeneralTrapsOIDs 67 }

  hwSDLDMMTestTrap NOTIFICATION-TYPE
    OBJECTS { hwSDLDMMTestStatus,hwSDLDMMTestConclusion,hwSDLDMMTestACAG,hwSDLDMMTestACBG,hwSDLDMMTestACAB,hwSDLDMMTestDCAG,hwSDLDMMTestDCBG,hwSDLDMMTestDCAB,hwSDLDMMTestRAG,hwSDLDMMTestRBG,hwSDLDMMTestRAB,hwSDLDMMTestCapAG,hwSDLDMMTestCapBG,hwSDLDMMTestCapAB }
    STATUS current
    DESCRIPTION
            "This notification indicates that the trap for the result of the SDL DMM test:
             1:hwSDLDMMTestStatus; 
             2: hwSDLDMMTestConclusion; 
             3: hwSDLDMMTestACAG; 
             4: hwSDLDMMTestACBG; 
             5: hwSDLDMMTestACAB; 
             6: hwSDLDMMTestDCAG; 
             7: hwSDLDMMTestDCBG;
             8: hwSDLDMMTestDCAB; 
             9: hwSDLDMMTestRAG; 
             10: hwSDLDMMTestRBG; 
             11: hwSDLDMMTestRAB; 
             12: hwSDLDMMTestCapAG; 
             13: hwSDLDMMTestCapBG; 
             14: hwSDLDMMTestCapAB"
    ::= { hwNTestGeneralTrapsOIDs 68 }

  hwQosTestOperatorTrap NOTIFICATION-TYPE
    OBJECTS { hwQosTestIndex, hwQosTestGWAddr, hwQosTestPeerAddr, 
             hwQosTestInPkts, hwQosTestOutPkts, hwQosTestInOctets, hwQosTestOutOctets, hwQosTestInDropPkts,
             hwQosTestStatsMaxDropPktsRate, hwQosTestStatsMaxDropPktsPort,
             hwQosTestStatsMinDropPktsRate, hwQosTestStatsMinDropPktsPort,
             hwQosTestStatsMaxDitherDelay, hwQosTestStatsMaxDitherPort,
             hwQosTestStatsMinDitherDelay, hwQosTestStatsMinDitherPort,
             hwQosTestStatsMaxLoopDelay, hwQosTestStatsMaxLoopPort,
             hwQosTestStatsMinLoopDelay, hwQosTestStatsMinLoopPort
            }
    STATUS current
    DESCRIPTION 
        "This notification indicates that the trap for the QoS test result"
    ::= { hwNTestGeneralTrapsOIDs 69 }

  hwLoopLineToneOperatorTrap NOTIFICATION-TYPE
    OBJECTS { hwLoopLineToneResult }
    STATUS current
    DESCRIPTION 
        "This notification indicates that the trap for the result of the signal tone test: 1: hwLoopLineToneResult"
    ::= { hwNTestGeneralTrapsOIDs 70 }

  hwPotsSelfCircuitTestTrap NOTIFICATION-TYPE
    OBJECTS { hwPotsSelfCircuitTestLoopRequestID, 
              hwPotsSelfCircuitTestStatus,
              hwPotsSelfCircuitTestVDDResult,
              hwPotsSelfCircuitTestVBATLResult,
              hwPotsSelfCircuitTestVBATHResult,
              hwPotsSelfCircuitTestVBATRResult,
              hwPotsSelfCircuitTestLoopCurrentResult,
              hwPotsSelfCircuitTestFeedVResult,
              hwPotsSelfCircuitTestRingVResult,
              hwPotsSelfCircuitTestRingFResult,
              hwPotsSelfCircuitTestVAGResult,
              hwPotsSelfCircuitTestVBGResult,
              hwPotsSelfCircuitTestFeedVValue,
              hwPotsSelfCircuitTestRingVValue,
              hwPotsSelfCircuitTestLoopCurrentValue,
              hwPotsSelfCircuitTestLoopIfIndex  ,
              hwPotsSelfCircuitTestOnHookDetectResult  ,
              hwPotsSelfCircuitTestOffHookDetectResult ,
              hwPotsSelfCircuitTestStopRingResult      ,
              hwPotsSelfCircuitTestVPoleResult         ,
              hwPotsSelfCircuitTestVBATLValue          ,
              hwPotsSelfCircuitTestVBATHValue          ,
              hwPotsSelfCircuitTestVBATRValue          ,
              hwPotsSelfCircuitTestRingFValue          ,
              hwPotsSelfCircuitTestVAGValue            ,
              hwPotsSelfCircuitTestVBGValue            ,
              hwPotsSelfCircuitTestVABPoleValue        ,
              hwPotsSelfCircuitTestABLCurrentValue     ,
              hwPotsSelfCircuitTestSLICTempValue       
            }
    STATUS current
    DESCRIPTION
            "Trap for the result of the PSTN circuit test:
             1: hwPotsSelfCircuitTestLoopRequestID; 
             2: hwPotsSelfCircuitTestStatus; 
             3: hwPotsSelfCircuitTestVDDResult; 
             4: hwPotsSelfCircuitTestVBATLResult; 
             5: hwPotsSelfCircuitTestVBATHResult; 
             6: hwPotsSelfCircuitTestVBATRResult; 
             7: hwPotsSelfCircuitTestLoopCurrentResult; 
             8: hwPotsSelfCircuitTestFeedVResult; 
             9: hwPotsSelfCircuitTestRingVResult; 
             10: hwPotsSelfCircuitTestRingFResult;
             11: hwPotsSelfCircuitTestVAGResult;
             12: hwPotsSelfCircuitTestVBGResult;
             13: hwPotsSelfCircuitTestFeedVValue;
             14: hwPotsSelfCircuitTestRingVValue;
             15: hwPotsSelfCircuitTestLoopCurrentValue;
             16: hwPotsSelfCircuitTestLoopIfIndex;
             17:hwPotsSelfCircuitTestOnHookDetectResult  ;
             18:hwPotsSelfCircuitTestOffHookDetectResult ;
             19:hwPotsSelfCircuitTestStopRingResult      ;
             20:hwPotsSelfCircuitTestVPoleResult         ;
             21:hwPotsSelfCircuitTestVBATLValue          ;
             22:hwPotsSelfCircuitTestVBATHValue          ;
             23:hwPotsSelfCircuitTestVBATRValue          ;
             24:hwPotsSelfCircuitTestRingFValue          ;
             25:hwPotsSelfCircuitTestVAGValue            ;
             26:hwPotsSelfCircuitTestVBGValue            ;
             27:hwPotsSelfCircuitTestVABPoleValue        ;
             28:hwPotsSelfCircuitTestABLCurrentValue     ;
             29:hwPotsSelfCircuitTestSLICTempValue       ;
             "
    ::= { hwNTestGeneralTrapsOIDs 71 }
        
  hwPstnCallEmulateOperatorTrap NOTIFICATION-TYPE
    OBJECTS { hwPstnCallEmulateTestRequestID, hwPstnCallEmulateTestStatus, hwPstnCallEmulateTestResult, hwPstnCallEmulateIndex }
    STATUS current
    DESCRIPTION
            "PSTN call emulation test: 
            1: hwPstnCallEmulateTestRequestID; 
            2: Test status (Enumerated type. 1: No dial tone; 2: Dialup fails; 3: The called number does not match; 4: The called party does not take the phone off the hook; 5: Communication is normal; 6: Test fails);
            3: Test result (Enumerated type. 1: No dial tone; 2: Caller not dialed; 3: Tel-num not matched; 4: Caller released;5: Test succeeds; 6: Call released; 
                                             7: Callee released; 8: Caller matching not completed; 9: Caller sending not completed; 10: Callee matching not completed; 11: Callee sending not completed; 12: Caller offHook busy; 
                                             13: Caller dialoging busy; 14: Caller match failed; 15: Callee match failed; 16: Caller port abnormal; 17: Callee port abnormal );
            4: hwPstnCallEmulateIndex"        
    ::= { hwNTestGeneralTrapsOIDs 72 }

  hwISDNDiagnoseTestTrap NOTIFICATION-TYPE
    OBJECTS { hwISDNDiagnoseTestRequestID, hwISDNDiagnoseTestResult, hwISDNDiagnoseTestCRCErrNum, hwISDNDiagnoseTestPortIndex }
    STATUS current
    DESCRIPTION
            "This notification indicates that the trap for the result of the ISDN diagnose test: 
            1: hwISDNDiagnoseTestRequestID; 
            2: hwISDNDiagnoseTestResult; 
            3: hwISDNDiagnoseTestCRCErrNum;
            4: hwISDNDiagnoseTestPortIndex"                
    ::= { hwNTestGeneralTrapsOIDs 73 } 
  
  hwPstnLoopTestTrap NOTIFICATION-TYPE
    OBJECTS { hwPstnLoopTestRequestID, hwPstnLoopTestResult, hwPstnLoopTestAssistIfIndex, hwPstnLoopTestSerialNo }
    STATUS current
    DESCRIPTION
            "This notification indicates that the trap for the result of the PSTN loop test: 
            1: hwPstnLoopTestRequestID; 
            2: hwPstnLoopTestResult; 
            3: hwPstnLoopTestAssistIfIndex;
            4: hwPstnLoopTestSerialNo"            
    ::= { hwNTestGeneralTrapsOIDs 74 }

    
        
  hwPstnCallTestOprTable OBJECT IDENTIFIER ::= { hwNTestMIBObjects 28 }
    
  
  hwPstnCallTestSerialNo OBJECT-TYPE
    SYNTAX Integer32
    MAX-ACCESS read-only
    STATUS current
    DESCRIPTION
        "Serial number of the test"
    ::= { hwPstnCallTestOprTable 1 }

  hwPstnCallTestCommand OBJECT-TYPE
    SYNTAX INTEGER
        {
        start(1),
        stop(2)
                }
    MAX-ACCESS read-write
    STATUS current
    DESCRIPTION
        "Test command.
         Options:
         1. start(1)  -start the test
         2. stop(2) -stop the test
        "
    ::= { hwPstnCallTestOprTable 2 }
        
  hwPstnCallTestCmdType OBJECT-TYPE
    SYNTAX INTEGER
        {
        fsp(1),
        telno(2),
        mgif(3),
        v5if(4),
        result(5)
        }
        
    MAX-ACCESS read-write
    STATUS current
    DESCRIPTION
        "Specifying the test range.
         Options:
         1. fsp(1)    -indicates By the shelf/slot/port
         2. telno(2)  -indicates By the telephone number
         3. mgif(3)   -indicates By the MG interface
         4. v5if(4)   -indicates By the V5 interface
         5. result(5) -indicates Result of the last test
        "
        ::= { hwPstnCallTestOprTable 3 }
    
  hwPstnCallTestStartFsp    OBJECT-TYPE
    SYNTAX Integer32(0..65536)
            MAX-ACCESS read-write
    STATUS current
    DESCRIPTION
        "Start shelf number/slot number/port number
        Range:0-65536"
    ::= { hwPstnCallTestOprTable 4 }

  hwPstnCallTestEndFsp  OBJECT-TYPE
    SYNTAX Integer32
  
            MAX-ACCESS read-only
    STATUS current
    DESCRIPTION
        "End shelf number/slot number/port number"
    ::= { hwPstnCallTestOprTable 5 }
    
    hwPstnCallTestStartTelNo    OBJECT-TYPE
    SYNTAX OCTET STRING(SIZE(16))
            MAX-ACCESS read-write
    STATUS current
    DESCRIPTION
        "Start telephone number"
    ::= { hwPstnCallTestOprTable 6 }

  hwPstnCallTestEndTelNo    OBJECT-TYPE
    SYNTAX OCTET STRING(SIZE(16))
            MAX-ACCESS read-write
    STATUS current
    DESCRIPTION
        "End telephone number"
    ::= { hwPstnCallTestOprTable 7 }
    
    hwPstnCallTestIfId  OBJECT-TYPE
    SYNTAX Integer32(0..7)
            MAX-ACCESS read-write
    STATUS current
    DESCRIPTION
        "Interface ID
        Range: 0-7"
    ::= { hwPstnCallTestOprTable 8 }

  hwPstnCallTestDualCallFlag    OBJECT-TYPE
    SYNTAX INTEGER
    {dualcall(1),
    notdualcall(2)
    }
            MAX-ACCESS read-write
    STATUS current
    DESCRIPTION
        "Bi-directional call test flag.
         Options:
         1. dualcall(1)    -indicates Start the bi-directional call
         2. notdualcall(2) -indicates Disable the bi-directional call"
            ::= { hwPstnCallTestOprTable 9 }
    
  hwPstnCallTestCalledTelNo   OBJECT-TYPE
    SYNTAX OCTET STRING(SIZE(16))
            MAX-ACCESS read-write
    STATUS current
    DESCRIPTION
        "Telephone number of the called party"
    ::= { hwPstnCallTestOprTable 10 }
    
  hwPstnCallTestCallerId  OBJECT-TYPE
    SYNTAX Integer32(0..32767)
            MAX-ACCESS read-write
    STATUS current
    DESCRIPTION
        "ID of the subscriber under an interface. The subscriber under the MG interface uses the TID as its ID and the subscriber under the V5 interface uses the L3 address as its ID."
        
    ::= { hwPstnCallTestOprTable 11 }
        
  hwPstnCallTestResultTable OBJECT-TYPE
    SYNTAX SEQUENCE OF HwPstnCallTestResultEntry
    MAX-ACCESS not-accessible
    STATUS current
    DESCRIPTION          
    "Table for the result of the query test
    The index of this table is hwPstnCallTestResultIndex"
    ::= { hwNTestMIBObjects 29 }


        
  hwPstnCallTestResultEntry OBJECT-TYPE
    SYNTAX HwPstnCallTestResultEntry
    MAX-ACCESS not-accessible
    STATUS current
    DESCRIPTION          
    "Table for the result of the query test
    The index of this entry is hwPstnCallTestResultIndex"
        INDEX{  
                 hwPstnCallTestResultIndex 
                 }
    ::= { hwPstnCallTestResultTable 1 }
    
  HwPstnCallTestResultEntry ::=
    SEQUENCE { 
                 hwPstnCallTestResultIndex   Integer32,
                 hwPstnCallTestResultSerialNo Integer32,
                 hwPstnCallTestResultFrameid Integer32,
                 hwPstnCallTestResultSlotid Integer32,
                 hwPstnCallTestResultPortid Integer32,
                 hwPstnCallTestResult Integer32,
                 hwPstnCallTestResultIfId Integer32,
                 hwPstnCallTestResultCallerId Integer32,
                 hwPstnCallTestResultTelNo OCTET STRING
             }
                              
  hwPstnCallTestResultIndex OBJECT-TYPE
    SYNTAX Integer32(0..8000)
    MAX-ACCESS not-accessible
    STATUS current
    DESCRIPTION
    "Index.
    Range: 0-8000"
    ::= { hwPstnCallTestResultEntry 1 }
              
  hwPstnCallTestResultSerialNo OBJECT-TYPE
    SYNTAX Integer32
    MAX-ACCESS read-only
    STATUS current
    DESCRIPTION
    "Serial number of the test"
    ::= { hwPstnCallTestResultEntry 2 }
                
  hwPstnCallTestResultFrameid OBJECT-TYPE
    SYNTAX Integer32
    MAX-ACCESS read-only
    STATUS current
    DESCRIPTION
    "ID of the shelf where the tested port is located"
    ::= { hwPstnCallTestResultEntry 3 }
              
  hwPstnCallTestResultSlotid OBJECT-TYPE
    SYNTAX Integer32
    MAX-ACCESS read-only
    STATUS current
    DESCRIPTION
    "ID of the slot where the tested port is located"
    ::= { hwPstnCallTestResultEntry 4 }
              
  hwPstnCallTestResultPortid OBJECT-TYPE
    SYNTAX Integer32
    MAX-ACCESS read-only
    STATUS current
    DESCRIPTION
    "ID of the tested port"
    ::= { hwPstnCallTestResultEntry 5 }

  hwPstnCallTestResult OBJECT-TYPE
    SYNTAX Integer32
    MAX-ACCESS read-only
    STATUS current
    DESCRIPTION
    "Test result: 
    1. Normal 
    2. No dial tone 
    3. The called telephone does not ring 
    4. The voice circuit cannot get through 
    5. TSS is abnormal 
    6. The tested port is not correctly configured 
    7. The port is faulty 
    8. Skip the test 
    9. Other unknown cases"
    ::= { hwPstnCallTestResultEntry 6 }
    
  hwPstnCallTestResultIfId OBJECT-TYPE
    SYNTAX Integer32
    MAX-ACCESS read-only
    STATUS current
    DESCRIPTION
    "Interface ID"
    ::= { hwPstnCallTestResultEntry 7 }

  hwPstnCallTestResultCallerId OBJECT-TYPE
    SYNTAX Integer32
    MAX-ACCESS read-only
    STATUS current
    DESCRIPTION
    "Caller ID"
    ::= { hwPstnCallTestResultEntry 8 }
    
  hwPstnCallTestResultTelNo OBJECT-TYPE
    SYNTAX OCTET STRING(SIZE(16))
    MAX-ACCESS read-only
    STATUS current
    DESCRIPTION
    "Telephone number of the tested port"
    ::= { hwPstnCallTestResultEntry 9 }

  hw112UserInDialTestOprTable OBJECT-TYPE
    SYNTAX      SEQUENCE OF Hw112UserInDialTestOprEntry
    MAX-ACCESS  not-accessible
    STATUS      current
    DESCRIPTION
      "
      This table is used to check whether a subscriber telephone can work in the normal state. The method is that the operator emulates a tested port to make calls.
      The index of this table is ifIndex."
    ::= { hwNTestMIBObjects 30 }

  hw112UserInDialTestOprEntry OBJECT-TYPE
    SYNTAX      Hw112UserInDialTestOprEntry
    MAX-ACCESS  not-accessible
    STATUS      current
    DESCRIPTION
      "
      This table is used to check whether a subscriber telephone can work in the normal state. The method is that the operator emulates a tested port to make calls.
      The index of this entry is ifIndex."

    INDEX    {  
              ifIndex
             }
    ::= { hw112UserInDialTestOprTable 1 }

  Hw112UserInDialTestOprEntry ::=
    SEQUENCE
    {
      hw112UserInDialTestOprType    INTEGER,
      hw112UserInDialTestTime       Integer32,
      hw112UserInDialTestResult     INTEGER
    }

  hw112UserInDialTestOprType OBJECT-TYPE
    SYNTAX      INTEGER{stop(1),start(2)}
    MAX-ACCESS  read-create
    STATUS      current
    DESCRIPTION
        "Operation type. 
         Options:
         1. stop(1)  -stop the test 
         2. start(2) -start the test
         The 112 protocol does not define the stop command."
    ::= { hw112UserInDialTestOprEntry 1 }

  hw112UserInDialTestTime OBJECT-TYPE
    SYNTAX      Integer32(1..5)
    MAX-ACCESS  read-create
    STATUS      current
    DESCRIPTION
        "Test duration 
         Unit: second"
    DEFVAL      { 5 }
    ::= { hw112UserInDialTestOprEntry 2 }

  hw112UserInDialTestResult OBJECT-TYPE
    SYNTAX      INTEGER{over(1)}
    MAX-ACCESS  read-only
    STATUS      current
    DESCRIPTION
        "Operation result.
         Options:
         1. over(1) -indicates Success"
    ::= { hw112UserInDialTestOprEntry 3 }  

  hwISDNDiagnoseTestTable OBJECT-TYPE
    SYNTAX      SEQUENCE OF HwISDNDiagnoseTestEntry
    MAX-ACCESS  not-accessible
    STATUS      current
    DESCRIPTION
      "
      User fault test table.
      The index of this table is ifIndex.
      "
    ::= { hwNTestMIBObjects 31 }

  hwISDNDiagnoseTestEntry OBJECT-TYPE
    SYNTAX      HwISDNDiagnoseTestEntry
    MAX-ACCESS  not-accessible
    STATUS      current
    DESCRIPTION
       "
      User fault test table.
      The index of this entry is ifIndex.
      "
    INDEX    {  
              hwISDNDiagnoseTestPortIndex
             }
    ::= { hwISDNDiagnoseTestTable 1 }

  HwISDNDiagnoseTestEntry ::=
    SEQUENCE
    {
      hwISDNDiagnoseTestPortIndex        Integer32,
      hwISDNDiagnoseTestOprType          INTEGER,
      hwISDNDiagnoseTestType             INTEGER,
      hwISDNDiagnoseTestItemType         INTEGER,
      hwISDNDiagnoseTestResult           INTEGER,
      hwISDNDiagnoseTestCRCErrNum        Integer32,
      hwISDNDiagnoseTestDeferredTestFlag INTEGER,      
      hwISDNDiagnoseTestDeferredTime     Integer32,     
      hwISDNDiagnoseTestTimeoutProc      INTEGER,
      hwISDNDiagnoseTestCrcDetectPeriod  Integer32,
      hwISDNDiagnoseTestRequestID        Integer32
    }

  hwISDNDiagnoseTestPortIndex OBJECT-TYPE
    SYNTAX      Integer32
    MAX-ACCESS  accessible-for-notify
    STATUS      current
    DESCRIPTION
        "
        Port index
        "
    ::= { hwISDNDiagnoseTestEntry 1 }

  hwISDNDiagnoseTestOprType OBJECT-TYPE
    SYNTAX      INTEGER{start(1),stop(2)}
    MAX-ACCESS  read-create
    STATUS      current
    DESCRIPTION
        "
        Test operation .
        Options:
        1. start(1) -indicates start the test
        2. stop(2)  -indicates stop the test
        "
    ::= { hwISDNDiagnoseTestEntry 2 }

  hwISDNDiagnoseTestType OBJECT-TYPE
    SYNTAX      INTEGER{routinetest(1),diagnosestest(2)}
    MAX-ACCESS  read-create
    STATUS      current
    DESCRIPTION
        "
        Test type.
        Options: 
        1. routinetest(1)   -indicates routine test needs the port must be IS state, it only supports immediate test mode;
        2. diagnosestest(2) -indicates diagnoses test needs the port must be OOS state, and Diagnose test supports deferred test mode.
        "
    ::= { hwISDNDiagnoseTestEntry 3 }

  hwISDNDiagnoseTestItemType OBJECT-TYPE
    SYNTAX      INTEGER{lineActiveTest(1),lineActiveAndCRCSendTest(2)}
    MAX-ACCESS  read-create
    STATUS      current
    DESCRIPTION
        "
        Test item.
        Options:
        1. lineActiveTest(1)           -indicates line active test
        2. lineActiveAndCRCSendTest(2) -indicates line active test and CRC send test
        "
    ::= { hwISDNDiagnoseTestEntry 4 }
    
    hwISDNDiagnoseTestResult OBJECT-TYPE
    SYNTAX  INTEGER
                {
                activeok(1),
                selfcheckfault(2),
                loopback1operfault(3),
                loopback1cancelfault(4),
                loopback1crccheckfault(5),
                activent1fault(6),
                nt1crccheckfault(7),
                ufaultloopback0succ(8),
                loopback2operfault(9),
                loopbackcancelfault(10),
                loopback2crccheckfault(11),
                noterminal(12),
                timeout(13),
                userstopsucc(14),
                exceptstop(15),
                nt1fault(16),
                testcanceled(17)
                }
    MAX-ACCESS  read-only
    STATUS      current
    DESCRIPTION
        "
        Test Result. 
        Options:
        1. activeok(1)                  -indicates line active ok 
        2. selfcheckfault(2)            -indicates board selfcheck fault 
        3. loopback1operfault(3)        -indicates loopback1 operation fault
        4. loopback1cancelfault(4)      -indicates loopback1 cancel fault
        5. loopback1crccheckfault(5)    -indicates loopback1 crc check fault
        6. activent1fault(6)            -indicates active nt1 fault
        7. nt1crccheckfault(7)          -indicates nt1 crc check fault
        8. ufaultloopback0succ(8)       -indicates  u fault loopback0 success
        9. loopback2operfault(9)        -indicates loopback2 operation fault
        10. loopbackcancelfault(10)     -indicates loopback2 cancel fault
        11. loopback2crccheckfault(11)  -indicates loopback2 crc check fault
        12. noterminal(12)              -indicates no terminal
        13. timeout(13)                 -indicates time out
        14. userstopsucc(14)            -indicates user stop test success
        15. exceptstop(15)              -indicates except stop
        16. nt1fault(16)                -indicates nt1 fault
        17. testcanceled(17)            -indicates test is canceled;
        "
    ::= { hwISDNDiagnoseTestEntry 5 }
    
    hwISDNDiagnoseTestCRCErrNum OBJECT-TYPE
    SYNTAX      Integer32
    MAX-ACCESS  read-only
    STATUS      current
    DESCRIPTION
        "
        Indicates the CRC error's number.
        "
    ::= { hwISDNDiagnoseTestEntry 6 }
    
    hwISDNDiagnoseTestDeferredTestFlag OBJECT-TYPE
    SYNTAX      INTEGER{immediatetest(1),deferredtest(2)}
    MAX-ACCESS  read-create
    STATUS      current
    DESCRIPTION
        "
        deferred test flag.
        Options: 
        1. immediatetest(1) -indicates immediate test; 
        2. deferredtest(2)  -indicates deferred test: Initiated when the port is in service. If the port is busy, the test operation 
                            will be deferred. If the port changes to idle state before time out, the test will be executed 
                            immediately. If the port keeps busy by the time out, the system will excecute a corresponding 
                            operation according to what the user specified: canceling the test or forcing to test.
                            If the value of this leaf node is deferredtest(2), both hwISDNDiagnoseTestDeferredTime and 
                            hwISDNDiagnoseTestTimeoutProc must be set. Only line diagnose test supports deferred test.
                            default test flag: immediatetest(1).
        Default: immediatetest(1)
        "
    DEFVAL { 1 }
    ::= { hwISDNDiagnoseTestEntry 7 }
    
  hwISDNDiagnoseTestDeferredTime OBJECT-TYPE
    SYNTAX      Integer32(1..1440)
    MAX-ACCESS  read-create
    STATUS      current
    DESCRIPTION
        "
        Deferred time(Unit: minute):
          this leaf node is valid only when the value of hwISDNDiagnoseTestDeferredTestFlag is deferredtest(2).
        Range: 1-1440
        Default: 30(minute)
        "
    DEFVAL { 30 }
    ::= { hwISDNDiagnoseTestEntry 8 }
    
  hwISDNDiagnoseTestTimeoutProc OBJECT-TYPE
    SYNTAX      INTEGER{notest(1),test(2)}
    MAX-ACCESS  read-create
    STATUS      current
    DESCRIPTION
        "
        timeout proc:
        Options: 
        1. notest(1) -when deferred time out, if the port is still in service, line diagnose test will be canceled; 
        2. test(2)   -when deferred time out, if the port is still in service, line diagnose test will be preformed by force.
        this leaf node is valid only when the value of hwISDNDiagnoseTestDeferredTestFlag is deferredtest(2).
        Default: notest(1).
        "
    DEFVAL { 1 }
    ::= { hwISDNDiagnoseTestEntry 9 }

    hwISDNDiagnoseTestCrcDetectPeriod OBJECT-TYPE
    SYNTAX      Integer32(10..86400)
    MAX-ACCESS  read-create
    STATUS      current
    DESCRIPTION
        "
        The CRC Check Period in Test.
        Unit:second 
        Range:10-86400
        "
    DEFVAL      { 10 }

    ::= { hwISDNDiagnoseTestEntry 10 }

    hwISDNDiagnoseTestRequestID OBJECT-TYPE
    SYNTAX      Integer32
    MAX-ACCESS  read-only
    STATUS      current
    DESCRIPTION
        "
        Request ID
        "
    ::= { hwISDNDiagnoseTestEntry 11 }
    
  hwPstnCallEmulateOprTable OBJECT-TYPE
    SYNTAX      SEQUENCE OF HwPstnCallEmulateOprEntry
    MAX-ACCESS  not-accessible
    STATUS      current
    DESCRIPTION
      "
      Operation table for the PSTN call emulation test (called party). It realizes the 
      function of the PSTN call emulation test (called party). This test helps check whether a subscriber port can 
      make calls normally as a called party.
      The index of this table is hwPstnCallEmulateIndex"
    ::= { hwNTestMIBObjects 32 }

  hwPstnCallEmulateOprEntry OBJECT-TYPE
    SYNTAX      HwPstnCallEmulateOprEntry
    MAX-ACCESS  not-accessible
    STATUS      current
    DESCRIPTION
      "
      Operation table for the PSTN call emulation test (called party). It realizes the 
      function of the PSTN call emulation test (called party). This test helps check whether a subscriber port can 
      make calls normally as a called party.
      The index of this entry is hwPstnCallEmulateIndex"
    INDEX {
            hwPstnCallEmulateIndex
           }  
    ::= { hwPstnCallEmulateOprTable 1 }
    

  HwPstnCallEmulateOprEntry ::=
    SEQUENCE
    {
      hwPstnCallEmulateIndex                    Integer32,
      hwPstnCallEmulateOprType                  INTEGER,
      hwPstnCallEmulateCallerIfindex            Integer32,
      hwPstnCallEmulateCalledIfindex            Integer32,
      hwPstnCallEmulateCalledTelNo              OCTET STRING,
      hwPstnCallEmulateTestStatus               INTEGER,
      hwPstnCallEmulateTestResult               INTEGER,
      hwPstnCallEmulateTestCallerDTMFDetected   OCTET STRING,
      hwPstnCallEmulateTestCalleeDTMFDetected   OCTET STRING,
      hwPstnCallEmulateTestRequestID            Integer32,
      hwPstnCallEmulateTestCallerFailReason     Unsigned32,
      hwPstnCallEmulateTestCalledFailReason     Unsigned32
   }
   
  hwPstnCallEmulateIndex OBJECT-TYPE
    SYNTAX      Integer32
    MAX-ACCESS  read-create
    STATUS      current
    DESCRIPTION
        "Call emulation index"
    ::= { hwPstnCallEmulateOprEntry 1 }
   

  hwPstnCallEmulateOprType OBJECT-TYPE
    SYNTAX      INTEGER{stop(1),start(2)}
    MAX-ACCESS  read-create
    STATUS      current
    DESCRIPTION
        "Operation type.
         Options:
         1. stop(1)  -stop the test
         2. start(2) -start the test"
    ::= { hwPstnCallEmulateOprEntry 2 }
  
  hwPstnCallEmulateCallerIfindex OBJECT-TYPE
    SYNTAX      Integer32
    MAX-ACCESS  read-create
    STATUS      current
    DESCRIPTION
        "Calling port of the call emulation test"
    ::= { hwPstnCallEmulateOprEntry 3 }
  
   hwPstnCallEmulateCalledIfindex OBJECT-TYPE
    SYNTAX      Integer32
    MAX-ACCESS  read-create
    STATUS      current
    DESCRIPTION
        "Called port of the call emulation test"
    ::= { hwPstnCallEmulateOprEntry 4 }
  
    hwPstnCallEmulateCalledTelNo OBJECT-TYPE
    SYNTAX      OCTET STRING(SIZE(32))
    MAX-ACCESS  read-create
    STATUS      current
    DESCRIPTION
        "Called telephone number (max length: 32)"
    ::= { hwPstnCallEmulateOprEntry 5 }

   hwPstnCallEmulateTestStatus OBJECT-TYPE
    SYNTAX      INTEGER{nodialtone(1), dialfailed(2), callednumbernotmatch(3), callednotpickupphone(4), testOK(5), testfailed(6)}
    MAX-ACCESS  read-only
    STATUS      current
    DESCRIPTION
        "Test Status.
         Options:
         1. nodialtone(1)           -indicates No dial tone 
         2. dialfailed(2)           -indicates Dialup fails 
         3. callednumbernotmatch(3) -indicates The called number does not match 
         4. callednotpickupphone(4) -indicates The called party does not take the phone off the hook 
         5. testOK(5)               -indicates Communication is normal 
         6. testfailed(6)           -indicates Test fails
        "
    ::= { hwPstnCallEmulateOprEntry 6 }

   hwPstnCallEmulateTestResult OBJECT-TYPE
    SYNTAX      INTEGER{callerNoDialTone(1), callerNoDial(2), telNumNoMatch(3), callerRelease(4), testSucceed(5), callRelease(6), calledRelease(7), callerMatchNoCompleted(8), callerSendNoCompleted(9), calledMatchNoCompleted(10), calledSendNoCompleted(11), callerOffHookingBusy(12), callerDialogingBusy(13), callerMatchFailed(14), calledMatchFailed(15), callerPortAbnormal(16), calledPortAbnormal(17)}
    MAX-ACCESS  read-only
    STATUS      current
    DESCRIPTION
        "Emulational Call Test Result
         Options:
         1. callerNoDialTone(1)          -indicates the caller does not have dial tone
         2. callerNoDial(2)              -indicates the caller does not dial             
         3. telNumNoMatch(3)             -indicates the telephone numbers are not matched
         4. callerRelease(4)             -indicates the caller release
         5. testSucceed(5)               -indicates the test succeed
         6. callRelease(6)               -indicates the call is released 
         7. calledRelease(7)             -indicates the called is released
         8. callerMatchNoCompleted(8)    -indicates the caller's match is not completed 
         9. callerSendNoCompleted(9)     -indicates the caller's sending is not completed
         10.calledMatchNoCompleted(10)   -indicates the called's match is not completed 
         11.calledSendNoCompleted(11)    -indicates the called's sending is not completed
         12.callerOffHookingBusy(12)     -indicates the caller is busy in off-hooking
         13.callerDialogingBusy(13)      -indicates the caller is busy in dialogging
         14.callerMatchFailed(14)        -indicates the caller match failed
         15.calledMatchFailed(15)        -indicates the called match failed
         16.callerPortAbnormal(16)       -indicates the caller's port is abnormal
         17.calledPortAbnormal(17)       -indicates the called's port is abnormal
        "
    ::= { hwPstnCallEmulateOprEntry 7 }
    
   hwPstnCallEmulateTestCallerDTMFDetected OBJECT-TYPE
    SYNTAX      OCTET STRING (SIZE(64))
    MAX-ACCESS  read-only
    STATUS      current
    DESCRIPTION
        "Emulational Call Test Caller Detected Dtmf Num List"
    ::= { hwPstnCallEmulateOprEntry 8 }
    
   hwPstnCallEmulateTestCalleeDTMFDetected OBJECT-TYPE
    SYNTAX      OCTET STRING (SIZE(64))
    MAX-ACCESS  read-only
    STATUS      current
    DESCRIPTION
        "Emulational Call Test Callee Detected Dtmf Num List"
    ::= { hwPstnCallEmulateOprEntry 9 } 
           
   hwPstnCallEmulateTestRequestID OBJECT-TYPE
    SYNTAX      Integer32
    MAX-ACCESS  read-only
    STATUS      current
    DESCRIPTION
        "Request ID"
    ::= { hwPstnCallEmulateOprEntry 10 }
    
    
  hwPstnCallEmulateTestCallerFailReason OBJECT-TYPE
    SYNTAX      Unsigned32
    MAX-ACCESS  read-only
    STATUS      current
    DESCRIPTION
        "The caller's fail reasons in Emulational test .
         Options:
        1.noreason(0)                           -indicates no reason, means normal                                                                                                                                                                                                                                                          
        2.otherproblem(1)                       -indicates other problem:other reason                                                                                                                                                                                                                               
        3.interfaceclose(65536)                 -indicates The config of AG is abnormal:interface is closed                                                                                                                                                                                                             
        4.theSALnodigimap(65537)                -indicates The config of AG is abnormal:SAL service has no digimap                                                                                                                                                                                                      
        5.emergencycallnodigimap(65538)         -indicates The config of AG is abnormal:emergency call has no digimap                                                                                                                                                                                                   
        6.novaliddigimapSIP(65539)              -indicates The config of AG is abnormal:no valid digimap(SIP)                                                                                                                                                                                                       
        7.noSALservice(65540)                   -indicates The config of AG is abnormal:no SAL service                                                                                                                                                                                                                  
        8.portloop(69632)                       -indicates The config of AG is abnormal:port is loop                                                                                                                                                                                                                    
        9.portprohibited(69633)                 -indicates The config of AG is abnormal:port is prohibited                                                                                                                                                                                                              
        10.usertypeerror(73728)                 -indicates The config of AG is abnormal:type of user is error                                                                                                                                                                                                           
        11.localendservice(73729)               -indicates The config of AG is abnormal:local party ends service                                                                                                                                                                                                        
        12.portnouser(73730)                    -indicates The config of AG is abnormal:port has no user                                                                                                                                                                                                                
        13.notelnum(73731)                      -indicates The config of AG is abnormal:no telephone number                                                                                                                                                                                                             
        14.localnocalledtelnum(73732)           -indicates The config of AG is abnormal:local party has no called telephone number                                                                                                                                                                                                     
        15.deluserendservice(73733)             -indicates The config of AG is abnormal:end service by deleting user                                                                                                                                                                                                    
        16.teststop(77824)                      -indicates The config of AG is abnormal:emulational test is stoped                                                                                                                                                                                                      
        17.userLicnotenough(77825)              -indicates The config of AG is abnormal:user License is not enough                                                                                                                                                                                                      
        18.theASLLicnotenough(77826)            -indicates The config of AG is abnormal:ASL License is not enough                                                                                                                                                                                                               
        19.calledpartynotexist(77827)           -indicates The config of AG is abnormal:called party is not exist                                                                                                                                                                                                                   
        20.calledpartynoestmismatchdmap(77828)  -indicates The config of AG is abnormal:called party is not exist or mismatch the digital map                                                                                                                                                                                                                  
        21.otherreasonAGconfigabnormal(131071)  -indicates The config of AG is abnormal:other reason                                                                                                                                                                                                                                
        22.userremoteblock(131072)              -indicates The state of AG is abnormal:user port is remote block                                                                                                                                                                                                            
        23.userremoteunblock(131073)            -indicates The state of AG is abnormal:user port is remote unblock                                                                                                                                                                                                          
        24.userendservieauto(131074)            -indicates The state of AG is abnormal:user ends servie automatically                                                                                                                                                                                                       
        25.useroffhook(131075)                  -indicates The state of AG is abnormal:user is offhook                                                                                                                                                                                                                  
        26.useroffhookPowerDailer(131076)       -indicates The state of AG is abnormal:user offhook PowerDailer                                                                                                                                                                                                                 
        27.userringing(131077)                  -indicates The state of AG is abnormal:user is ringing                                                                                                                                                                                                                      
        28.userlocke(131078)                    -indicates The state of AG is abnormal:user is locked                                                                                                                                                                                                                       
        29.useroutofservice(131079)             -indicates The state of AG is abnormal:user is out of service                                                                                                                                                                                                               
        30.userregisterexpire(131080)           -indicates The state of AG is abnormal:user's register time is expired                                                                                                                                                                                                      
        31.calledpartybusy(131081)              -indicates The state of AG is abnormal:called party is busy                                                                                                                                                                                                                 
        32.vaginterfacefault(135168)            -indicates The state of AG is abnormal:VAG interface is fault                                                                                                                                                                                                               
        33.bandoverload(135169)                 -indicates The state of AG is abnormal:the band is overloaded                                                                                                                                                                                                                   
        34.mgcoverloade(135170)                 -indicates The state of AG is abnormal:MGC is overloaded                                                                                                                                                                                                                    
        35.mgoverload(135171)                   -indicates The state of AG is abnormal:MG is overloaded                                                                                                                                                                                                                     
        36.poweroverload(139264)                -indicates The state of AG is abnormal:the power is overloaded                                                                                                                                                                                                                  
        37.innerresourceabnormal(139265)        -indicates The state of AG is abnormal:inner resource is abnormal                                                                                                                                                                                                           
        38.normalservicebrokenSAL(139266)       -indicates The state of AG is abnormal:SAL is broken by normal service                                                                                                                                                                                                      
        39.DSPfault(139267)                     -indicates The state of AG is abnormal:DSP is fault                                                                                                                                                                                                                         
        40.DSPresourcelack(139268)              -indicates The state of AG is abnormal:DSP's resource is not enough                                                                                                                                                                                                         
        41.mainbackupswitching(139269)          -indicates The state of AG is abnormal:main and backup board is switchi                                                                                                                                                                                                         
        42.portpowerdown(143360)                -indicates The state of AG is abnormal:port is power down                                                                                                                                                                                                               
        43.portnotexist(143361)                 -indicates The state of AG is abnormal:port is not exist                                                                                                                                                                                                                    
        44.porttesting(143362)                  -indicates The state of AG is abnormal:port is testing                                                                                                                                                                                                                              
        45.portfault(143363)                    -indicates The state of AG is abnormal:port is fault                                                                                                                                                                                                                                
        46.portoffhookPowerDailer(143364)       -indicates The state of AG is abnormal:port offhook PowerDailer                                                                                                                                                                                                                 
        47.portoffhookfailed(143365)            -indicates The state of AG is abnormal:port offhook failed                                                                                                                                                                                                                          
        48.agdialingunfinish(143366)            -indicates The state of AG is abnormal:AG's dialing is unfinished                                                                                                                                                                                                               
        49.otherreasonAGstateabnormal(196607)   -indicates The state of AG is abnormal:other reason                                                                                                                                                                                                                             
        50.localrefusecall(196608)              -indicates The interaction of signaling is abnormal:loacl party refuse                                                                                                                                                                                                      
        51.serviceflowabnormal(196609)          -indicates The interaction of signaling is abnormal:service flow is abn                                                                                                                                                                                                         
        52.remoterefusecall(200704)             -indicates The interaction of signaling is abnormal:remote party refuse                                                                                                                                                                                                     
        53.localnotsupport(204800)              -indicates The interaction of signaling is abnormal:local party dose no                                                                                                                                                                                                     
        54.remoteRTPmodeabnormal(208896)        -indicates The interaction of signaling is abnormal:RTP mode appointed by remote party is abnormal
        55.sdpnegotiatefail(208897)             -indicates The interaction of signaling is abnormal:SDP negotiate failed
        56.mgccontextmismatch(208898)           -indicates The interaction of signaling is abnormal:MGC's context is mismatch
        57.MGCnotcheckevent(208899)             -indicates The interaction of signaling is abnormal:MGC dose not appoint to check events
        58.novaliddigimapH248MGCP(208900)       -indicates The interaction of signaling is abnormal:no valid digimap(H248/MGCP)
        59.remotewrongrespond(208901)           -indicates The interaction of signaling is abnormal:the other party dose not respond correctly after dialing
        60.remotewrongrespondsignaling(208902)  -indicates The interaction of signaling is abnormal:the other party does not respond the signaling correctly 
        61.notstarttalk(208903)                 -indicates The interaction of signaling is abnormal:have not started talking
        62.notappointring(208904)               -indicates The interaction of signaling is abnormal:dose not appoint to ring
        63.remotenotcalllocal(208905)           -indicates The interaction of signaling is abnormal:remote party does not call local remote
        64.remoterealsecall(208906)             -indicates The interaction of signaling is abnormal:remote party realse the call
        65.remoterefusecallbt(208907)           -indicates The interaction of signaling is abnormal:remote party refuse call by busy tone
        66.unexpectedsignaling(208908)          -indicates The interaction of signaling is abnormal:unexpected signaling
        67.otherreasonsignalabnormal(262143)    -indicates The interaction of signaling is abnormal:other reason                                                                                                                                                                                                             
        "
    ::= { hwPstnCallEmulateOprEntry 11 }

    
  hwPstnCallEmulateTestCalledFailReason OBJECT-TYPE
    SYNTAX      Unsigned32
    MAX-ACCESS  read-only
    STATUS      current
    DESCRIPTION
        "The called's fail reasons in Emulational test .
         Options:
        1.noreason(0)                           -indicates no reason, means normal                                                                                                                                                                                                                                                          
        2.otherproblem(1)                       -indicates other problem:other reason                                                                                                                                                                                                                               
        3.interfaceclose(65536)                 -indicates The config of AG is abnormal:interface is closed                                                                                                                                                                                                             
        4.theSALnodigimap(65537)                -indicates The config of AG is abnormal:SAL service has no digimap                                                                                                                                                                                                      
        5.emergencycallnodigimap(65538)         -indicates The config of AG is abnormal:emergency call has no digimap                                                                                                                                                                                                   
        6.novaliddigimapSIP(65539)              -indicates The config of AG is abnormal:no valid digimap(SIP)                                                                                                                                                                                                       
        7.noSALservice(65540)                   -indicates The config of AG is abnormal:no SAL service                                                                                                                                                                                                                  
        8.portloop(69632)                       -indicates The config of AG is abnormal:port is loop                                                                                                                                                                                                                    
        9.portprohibited(69633)                 -indicates The config of AG is abnormal:port is prohibited                                                                                                                                                                                                              
        10.usertypeerror(73728)                 -indicates The config of AG is abnormal:type of user is error                                                                                                                                                                                                           
        11.localendservice(73729)               -indicates The config of AG is abnormal:local party ends service                                                                                                                                                                                                        
        12.portnouser(73730)                    -indicates The config of AG is abnormal:port has no user                                                                                                                                                                                                                
        13.notelnum(73731)                      -indicates The config of AG is abnormal:no telephone number                                                                                                                                                                                                             
        14.localnocalledtelnum(73732)           -indicates The config of AG is abnormal:local party has no called telephone number                                                                                                                                                                                                     
        15.deluserendservice(73733)             -indicates The config of AG is abnormal:end service by deleting user                                                                                                                                                                                                    
        16.teststop(77824)                      -indicates The config of AG is abnormal:emulational test is stoped                                                                                                                                                                                                      
        17.userLicnotenough(77825)              -indicates The config of AG is abnormal:user License is not enough                                                                                                                                                                                                      
        18.theASLLicnotenough(77826)            -indicates The config of AG is abnormal:ASL License is not enough                                                                                                                                                                                                               
        19.calledpartynotexist(77827)           -indicates The config of AG is abnormal:called party is not exist                                                                                                                                                                                                                   
        20.calledpartynoestmismatchdmap(77828)  -indicates The config of AG is abnormal:called party is not exist or mismatch the digital map                                                                                                                                                                                                                  
        21.otherreasonAGconfigabnormal(131071)  -indicates The config of AG is abnormal:other reason                                                                                                                                                                                                                                
        22.userremoteblock(131072)              -indicates The state of AG is abnormal:user port is remote block                                                                                                                                                                                                            
        23.userremoteunblock(131073)            -indicates The state of AG is abnormal:user port is remote unblock                                                                                                                                                                                                          
        24.userendservieauto(131074)            -indicates The state of AG is abnormal:user ends servie automatically                                                                                                                                                                                                       
        25.useroffhook(131075)                  -indicates The state of AG is abnormal:user is offhook                                                                                                                                                                                                                  
        26.useroffhookPowerDailer(131076)       -indicates The state of AG is abnormal:user offhook PowerDailer                                                                                                                                                                                                                 
        27.userringing(131077)                  -indicates The state of AG is abnormal:user is ringing                                                                                                                                                                                                                      
        28.userlocke(131078)                    -indicates The state of AG is abnormal:user is locked                                                                                                                                                                                                                       
        29.useroutofservice(131079)             -indicates The state of AG is abnormal:user is out of service                                                                                                                                                                                                               
        30.userregisterexpire(131080)           -indicates The state of AG is abnormal:user's register time is expired                                                                                                                                                                                                      
        31.calledpartybusy(131081)              -indicates The state of AG is abnormal:called party is busy                                                                                                                                                                                                                 
        32.vaginterfacefault(135168)            -indicates The state of AG is abnormal:VAG interface is fault                                                                                                                                                                                                               
        33.bandoverload(135169)                 -indicates The state of AG is abnormal:the band is overloaded                                                                                                                                                                                                                   
        34.mgcoverloade(135170)                 -indicates The state of AG is abnormal:MGC is overloaded                                                                                                                                                                                                                    
        35.mgoverload(135171)                   -indicates The state of AG is abnormal:MG is overloaded                                                                                                                                                                                                                     
        36.poweroverload(139264)                -indicates The state of AG is abnormal:the power is overloaded                                                                                                                                                                                                                  
        37.innerresourceabnormal(139265)        -indicates The state of AG is abnormal:inner resource is abnormal                                                                                                                                                                                                           
        38.normalservicebrokenSAL(139266)       -indicates The state of AG is abnormal:SAL is broken by normal service                                                                                                                                                                                                      
        39.DSPfault(139267)                     -indicates The state of AG is abnormal:DSP is fault                                                                                                                                                                                                                         
        40.DSPresourcelack(139268)              -indicates The state of AG is abnormal:DSP's resource is not enough                                                                                                                                                                                                         
        41.mainbackupswitching(139269)          -indicates The state of AG is abnormal:main and backup board is switchi                                                                                                                                                                                                         
        42.portpowerdown(143360)                -indicates The state of AG is abnormal:port is power down                                                                                                                                                                                                               
        43.portnotexist(143361)                 -indicates The state of AG is abnormal:port is not exist                                                                                                                                                                                                                    
        44.porttesting(143362)                  -indicates The state of AG is abnormal:port is testing                                                                                                                                                                                                                              
        45.portfault(143363)                    -indicates The state of AG is abnormal:port is fault                                                                                                                                                                                                                                
        46.portoffhookPowerDailer(143364)       -indicates The state of AG is abnormal:port offhook PowerDailer                                                                                                                                                                                                                 
        47.portoffhookfailed(143365)            -indicates The state of AG is abnormal:port offhook failed                                                                                                                                                                                                                          
        48.agdialingunfinish(143366)            -indicates The state of AG is abnormal:AG's dialing is unfinished                                                                                                                                                                                                               
        49.otherreasonAGstateabnormal(196607)   -indicates The state of AG is abnormal:other reason                                                                                                                                                                                                                             
        50.localrefusecall(196608)              -indicates The interaction of signaling is abnormal:loacl party refuse                                                                                                                                                                                                      
        51.serviceflowabnormal(196609)          -indicates The interaction of signaling is abnormal:service flow is abn                                                                                                                                                                                                         
        52.remoterefusecall(200704)             -indicates The interaction of signaling is abnormal:remote party refuse                                                                                                                                                                                                     
        53.localnotsupport(204800)              -indicates The interaction of signaling is abnormal:local party dose no                                                                                                                                                                                                     
        54.remoteRTPmodeabnormal(208896)        -indicates The interaction of signaling is abnormal:RTP mode appointed by remote party is abnormal
        55.sdpnegotiatefail(208897)             -indicates The interaction of signaling is abnormal:SDP negotiate failed
        56.mgccontextmismatch(208898)           -indicates The interaction of signaling is abnormal:MGC's context is mismatch
        57.MGCnotcheckevent(208899)             -indicates The interaction of signaling is abnormal:MGC dose not appoint to check events
        58.novaliddigimapH248MGCP(208900)       -indicates The interaction of signaling is abnormal:no valid digimap(H248/MGCP)
        59.remotewrongrespond(208901)           -indicates The interaction of signaling is abnormal:the other party dose not respond correctly after dialing
        60.remotewrongrespondsignaling(208902)  -indicates The interaction of signaling is abnormal:the other party does not respond the signaling correctly 
        61.notstarttalk(208903)                 -indicates The interaction of signaling is abnormal:have not started talking
        62.notappointring(208904)               -indicates The interaction of signaling is abnormal:dose not appoint to ring
        63.remotenotcalllocal(208905)           -indicates The interaction of signaling is abnormal:remote party does not call local remote
        64.remoterealsecall(208906)             -indicates The interaction of signaling is abnormal:remote party realse the call
        65.remoterefusecallbt(208907)           -indicates The interaction of signaling is abnormal:remote party refuse call by busy tone
        66.unexpectedsignaling(208908)          -indicates The interaction of signaling is abnormal:unexpected signaling
        67.otherreasonsignalabnormal(262143)    -indicates The interaction of signaling is abnormal:other reason                                                                                                                                                                                                             
        "
    ::= { hwPstnCallEmulateOprEntry 12 }

    
 hwPstnLoopTestOprTable OBJECT-TYPE
    SYNTAX      SEQUENCE OF HwPstnLoopTestOprEntry
    MAX-ACCESS  not-accessible
    STATUS      current
    DESCRIPTION
      "
      Loop test table
      The index of this table is hwPstnLoopTestSerialNo"
    ::= { hwNTestMIBObjects 33 }

  hwPstnLoopTestOprEntry OBJECT-TYPE
    SYNTAX      HwPstnLoopTestOprEntry
    MAX-ACCESS  not-accessible
    STATUS      current
    DESCRIPTION
      "
      Loop test table
      The index of this entry is hwPstnLoopTestSerialNo"
      
          INDEX    {hwPstnLoopTestSerialNo}
    ::= { hwPstnLoopTestOprTable 1 }

  HwPstnLoopTestOprEntry ::=
    SEQUENCE
    {
      hwPstnLoopTestSerialNo       Integer32,
      hwPstnLoopTestDestIfIndex    Integer32,
      hwPstnLoopTestAssistIfIndex  Integer32,
      hwPstnLoopTestOprType        INTEGER,
      hwPstnLoopTestResult         Integer32,
      hwPstnLoopTestMode           INTEGER,
      hwPstnLoopTestDestTelNo      OCTET STRING,
      hwPstnLoopTestRequestID      Integer32
    }
    
    hwPstnLoopTestSerialNo OBJECT-TYPE
    SYNTAX      Integer32
    MAX-ACCESS  read-create
    STATUS      current
    DESCRIPTION
        "
        Test serial number
        "
        
    ::= { hwPstnLoopTestOprEntry 1 }  
  
  hwPstnLoopTestDestIfIndex OBJECT-TYPE
    SYNTAX      Integer32
    MAX-ACCESS  read-create
    STATUS      current
    DESCRIPTION
        "
        Target port ID"
        
    ::= { hwPstnLoopTestOprEntry 2 }    
    
  hwPstnLoopTestAssistIfIndex OBJECT-TYPE
  SYNTAX      Integer32
   MAX-ACCESS  read-create
  STATUS      current
  DESCRIPTION
      "
      Assistant port ID"
      
  ::= { hwPstnLoopTestOprEntry 3 }
  
  hwPstnLoopTestOprType OBJECT-TYPE
    SYNTAX      INTEGER{start(1),stop(2)}
    MAX-ACCESS  read-create
    STATUS      current
    DESCRIPTION
        "
        Operation type.
        Options:
        1. start(1) -indicates start the test
        2. stop(2)  -indicates stop the test
        "
    ::= { hwPstnLoopTestOprEntry 4 }
     
      hwPstnLoopTestResult OBJECT-TYPE
      SYNTAX      Integer32
     MAX-ACCESS  read-only
      STATUS      current
     DESCRIPTION
     
"
Test status:
1. Succeed; 2. Offhook on the target subscriber port fails; 3. Offhook on the assistant subscriber port fails; 4. Onhook on the target subscriber port fails; 5. Onhook on the assistant subscriber port fails;
6. Ringing on the target subscriber port fails; 7. Stopping ringing on the target subscriber port fails; 8. Channel test 1 fails. The target subscriber port transmits the DTMF signal to the TDM side. The assistant subscriber port does not detect any corresponding DTMF signal;
9. Channel test 2 fails. The assistant subscriber port transmits the DTMF signal to the TDM side. The target subscriber port does not detect any corresponding DTMF signal; 10. Channel test 3 fails. The target subscriber port transmits the DTMF signal to the IP side. The target subscriber port does not detect any corresponding DTMF signal on the TDM side; 11. Channel 4 test 4 fails. The assistant subscriber port transmits the DTMF signal to the IP side. The assistant subscriber port does not detect any corresponding DTMF signal on the TDM side;
12. Waiting for the dialing tone on the assistant subscriber port fails; 13. Waiting for the ringing on the target subscriber port fails; 14. The system fails due to abnormity; 15. The test stops because the tested subscriber port is busy;
16. The test stops because the user of the tested subscriber port hooks off; 17. The voice channel test fails because of insufficient DSP resources; 18. The DSP network function test fails (the turn around function is enabled); 19. The DSP network function test fails; 20. The codec loopback is successful, the SLIC loopback fails, and the SLIC chip is faulty; 21. The TDM loopback is successful, the codec loopback and SLIC loopback fail, and the codec chip, the SLIC chip, or the HighWay bus is faulty;
22. The DSP is faulty and the DSP TDM loopback fails; 23. The codec loopback fails and the codec chip is faulty.
"


::= { hwPstnLoopTestOprEntry 5 } 
 
    hwPstnLoopTestMode OBJECT-TYPE
    SYNTAX      INTEGER{hardwaretest(1),systemtest(2)}
    MAX-ACCESS  read-create
    STATUS      current
    DESCRIPTION
        "
        Test mode
        Options:
        1. hardwaretest(1)  -indicates it is a hardware test
        2. systemtest(2)    -indicates it is a systen test
        "        
    ::= { hwPstnLoopTestOprEntry 6 }
    
    hwPstnLoopTestDestTelNo OBJECT-TYPE
    SYNTAX      OCTET STRING (SIZE(16))
    MAX-ACCESS  read-create
    STATUS      current
    DESCRIPTION
        "
        Telephone number of the target port (the maximum length is 16)
        "
        
        
    ::= { hwPstnLoopTestOprEntry 7 }

    hwPstnLoopTestRequestID OBJECT-TYPE
    SYNTAX      Integer32
    MAX-ACCESS  read-only
    STATUS      current
    DESCRIPTION
        "
        Request ID
        "

    ::= { hwPstnLoopTestOprEntry 8 }
    
   hwPstnCallEmulateConfigTable OBJECT IDENTIFIER ::= { hwNTestMIBObjects 34 } 
   
   hwPstnCallEmulateTestIndicationTone OBJECT-TYPE
     SYNTAX      INTEGER{enable(1),disable(2)} 
     MAX-ACCESS  read-create
     STATUS      current
     DESCRIPTION
         "
         The enable flag of playing the indication tone.
         Options:
         1. enable(1)    -indicates that enable the indication tone
         1. disable(2)    -indicates that disable the indication tone
         Default:disable(2)
         "  
     ::= { hwPstnCallEmulateConfigTable 1 }

   hwPstnCallEmulateTestSendDTMF OBJECT-TYPE
     SYNTAX      INTEGER{enable(1),disable(2)}  
     MAX-ACCESS  read-create
     STATUS      current
     DESCRIPTION
         "
         Enable the function of sending DTMF numbers.
         Options:
         1. enable(1)    -indicates that enable sending DTMF numbers
         2. disable(2)    -indicates that disable sending DTMF numbers
         Default:enable(1)
         "  
      ::= { hwPstnCallEmulateConfigTable 2 }
     
   hwPstnCallEmulateTestSendDTMFDelay OBJECT-TYPE
     SYNTAX      Integer32(1..60) 
     MAX-ACCESS  read-create
     STATUS      current
     DESCRIPTION
         "
         The delay between the time when the user starts testing and the time when the user sends the first DTMF number.
         Default: 5
         Unit: second
         "  
     ::= { hwPstnCallEmulateConfigTable 3 }

   hwPstnCallEmulateTestSendDTMFPeriod OBJECT-TYPE
     SYNTAX      Integer32(200..8000) 
     MAX-ACCESS  read-create
     STATUS      current
     DESCRIPTION
         "
         The interval of sending DTMF numbers. It is used to set how often the system sends a DTMF number, in the unit of ms. It must be an integer multiple of 10. 
         Default: 1000
         Unit: millisecond
         "  
     ::= { hwPstnCallEmulateConfigTable 4 }
   
   hwPstnCallEmulateTestSendDTMFList OBJECT-TYPE
     SYNTAX      OCTET STRING (SIZE(64))
     MAX-ACCESS  read-create
     STATUS      current
     DESCRIPTION
         "
         The list of sending DTMF numbers.
         Default: ****************
         "  
     ::= { hwPstnCallEmulateConfigTable 5 }
     
   hwPstnCallEmulateTestDetectDTMF OBJECT-TYPE       
     SYNTAX      INTEGER{enable(1),disable(2)} 
     MAX-ACCESS  read-create
     STATUS      current
     DESCRIPTION
         "
         Enable the function of detecting DTMF numbers.
         Options:
         1. enable(1)    -indicates that enable the function of detecting DTMF numbers
         2. disable(2)   -indicates that disable the function of detecting DTMF numbers
         Default:disable(2)
         "  
     ::= { hwPstnCallEmulateConfigTable 6 }

     hwPstnCallEmulateTestMatchDTMF OBJECT-TYPE
     SYNTAX      INTEGER{enable(1),disable(2)} 
     MAX-ACCESS  read-create
     STATUS      current
     DESCRIPTION
         "
         Enable the function of matching DTMF numbers.
         Options:
         1. enable(1)    -indicates that enable the function of matching DTMF numbers
         2. disable(2)   -indicates that disable the function of matching DTMF numbers
         Default:disable(2)
         "  
     ::= { hwPstnCallEmulateConfigTable 7 }
     
     hwPstnCallEmulateTestMatchDTMFList OBJECT-TYPE
     SYNTAX      OCTET STRING (SIZE(64))
     MAX-ACCESS  read-create
     STATUS      current
     DESCRIPTION
         "
         The list of matched DTMF numbers.
         Default: *
         "  
     ::= { hwPstnCallEmulateConfigTable 8 }
    
    hwPstnCallEmulateTestMatchDTMFResultTone OBJECT-TYPE
     SYNTAX      INTEGER{enable(1),disable(2)} 
     MAX-ACCESS  read-create
     STATUS      current
     DESCRIPTION
         "
         Enable flag of playing the result tone after DTMF number detection.
         Options:
         1. enable(1)    -indicates that enable 
         2. disable(2)   -indicates that disable 
         Default:disable(2)
         "  
     ::= { hwPstnCallEmulateConfigTable 9 }        
   
   hwPstnCallEmulateTestWaitTime OBJECT-TYPE
     SYNTAX      Integer32(5..600)
     MAX-ACCESS  read-create
     STATUS      current
     DESCRIPTION
         "
         The time of call waiting in a called emulation test. The test is considered to be failed, if the system does not receive any call during this period. 
         Unit: second
         Default: 600
         "     
     ::= { hwPstnCallEmulateConfigTable 10 }   

   hwPstnCallEmulateTestHoldTime OBJECT-TYPE
     SYNTAX      Integer32(5..600)
     MAX-ACCESS  read-create
     STATUS      current
     DESCRIPTION
         "
         The time of call holding in an emulation test. The test is considered to be failed, if the system does not receive any call during this period.
         Unit: second
         Default: 600         
         "         
     ::= { hwPstnCallEmulateConfigTable 11 }    
     
    hwLineTestParaTable OBJECT-TYPE
    SYNTAX      SEQUENCE OF HwLineTestParaEntry
    MAX-ACCESS  not-accessible
    STATUS      current
    DESCRIPTION
      "
      pots test para config table
      The index of this table is hwLineTestParaFrameIndex and hwLineTestParaSlotIndex"
    ::= { hwNTestMIBObjects 35 }  
    
    hwLineTestParaEntry OBJECT-TYPE
    SYNTAX      HwLineTestParaEntry
    MAX-ACCESS  not-accessible
    STATUS      current
    DESCRIPTION
      "
      pots test para config table
      The index of this entry is hwLineTestParaFrameIndex and hwLineTestParaSlotIndex"
      
    INDEX    {hwLineTestParaFrameIndex,hwLineTestParaSlotIndex}
    ::= { hwLineTestParaTable 1 }  
    
    HwLineTestParaEntry ::=
    SEQUENCE
    {
      hwLineTestParaOprType        INTEGER,
      hwLineTestParaFrameIndex     Integer32,
      hwLineTestParaSlotIndex      Integer32,
      hwLineTestParaPv             Integer32,
      hwLineTestParaAcF            Integer32,
      hwLineTestParaPitF           Integer32,
      hwLineTestParaMaxfeScv       Integer32,
      hwLineTestParaMinfeScv       Integer32
    } 
    
    hwLineTestParaOprType OBJECT-TYPE
    SYNTAX INTEGER
      {
        configure(1),
        restore(2),
        invalid(-1)
      }
    MAX-ACCESS  read-create
    STATUS      current
    DESCRIPTION
        "
        The operation type of Test para config.
        Options:
        1. configure(1)     -configure the value of physical layer test para 
        2. restore(2)       -restore the value of physical layer test para  
        3. invalid(-1)      -invalid value
        "
    ::= { hwLineTestParaEntry 1 }
    
    hwLineTestParaFrameIndex OBJECT-TYPE
    SYNTAX Integer32 (-1 | 0..255)
    MAX-ACCESS read-only
    STATUS current      
    DESCRIPTION
        "Indicates the frameID of configuring test para.
         Range:   0-255|-1
        "
    ::= { hwLineTestParaEntry 2 }  
    
    hwLineTestParaSlotIndex OBJECT-TYPE
    SYNTAX Integer32 (-1 | 0..255)
    MAX-ACCESS read-only
    STATUS current      
    DESCRIPTION
        "Indicates the slotID of configuring test para.
         Range:   0-255|-1
        "
    ::= { hwLineTestParaEntry 3 } 
    
    hwLineTestParaPv OBJECT-TYPE
    SYNTAX Integer32 (-1 | 0..100000)
    MAX-ACCESS read-write
    STATUS current      
    DESCRIPTION
        "Indicates the peak line test voltage of permitted sending.
         Range:   0-100000|-1
         Default: 50000
         Unit: mV
        "
    DEFVAL     { 50000 }
    ::= { hwLineTestParaEntry 4 }  
    
    hwLineTestParaAcF OBJECT-TYPE
    SYNTAX Integer32 (-1 | 10..1000)
    MAX-ACCESS read-write
    STATUS current      
    DESCRIPTION
        "Indicates the AC signal frequency when testing the capacitance and catheter.
         Range:   10-1000|-1
         Default: 25
         Unit: Hz
        "
    DEFVAL     { 25 }
    ::= { hwLineTestParaEntry 5 }
    
    hwLineTestParaPitF OBJECT-TYPE
    SYNTAX Integer32 (-1 | 300..3400)
    MAX-ACCESS read-write
    STATUS current      
    DESCRIPTION
        "Indicates the frequency of line test voice.
         Range:   300-3400|-1
         Default: 800
         Unit: Hz
        "
    DEFVAL     { 800 }
    ::= { hwLineTestParaEntry 6 }  
    
    hwLineTestParaMaxfeScv OBJECT-TYPE
    SYNTAX Integer32 (-1 | 0..50000)
    MAX-ACCESS read-write
    STATUS current      
    DESCRIPTION
        "Indicates the max voltage of Signature test.
         Range: 0-50000|-1   
         Default: 50000
         Unit: mV 
         Step: 1000
        "
    DEFVAL     { 50000 }
    ::= { hwLineTestParaEntry 7 }  
    
    hwLineTestParaMinfeScv OBJECT-TYPE
    SYNTAX Integer32 (-1 | 0..50000)
    MAX-ACCESS read-write
    STATUS current      
    DESCRIPTION
        "Indicates the min voltage of Signature test.
         Range:   0-50000|-1
         Default: 3000
         Unit: mV 
         Step: 1000
        "
    DEFVAL     { 3000 }
    ::= { hwLineTestParaEntry 8 }
    
    hwMonitorTestOprTable OBJECT-TYPE
    SYNTAX      SEQUENCE OF HwMonitorTestOprEntry
    MAX-ACCESS  not-accessible
    STATUS      current
    DESCRIPTION
      "
      monitor test table
      The index of this table is ifIndex"
    ::= { hwNTestMIBObjects 36 }  
    
    hwMonitorTestOprEntry OBJECT-TYPE
    SYNTAX      HwMonitorTestOprEntry
    MAX-ACCESS  not-accessible
    STATUS      current
    DESCRIPTION
      "
      monitor test table
      The index of this entry is ifIndex"
      
    INDEX    {
              ifIndex
              }
    ::= { hwMonitorTestOprTable 1 }  
    
    HwMonitorTestOprEntry ::=
    SEQUENCE
    {
      hwMonitorTestAGV                      Integer32,
      hwMonitorTestBGV                      Integer32,
      hwMonitorTestLongitudinalCurrent      Integer32,
      hwMonitorTestTransversalCurrent       Integer32,
      hwMonitorTestBatteryVoltage           Integer32,
      hwMonitorTestSLICTemperature          Integer32
     } 
    
    hwMonitorTestAGV OBJECT-TYPE
    SYNTAX Integer32
    MAX-ACCESS  read-only
    STATUS      current
    DESCRIPTION
        "
        Monitor test A->ground voltage.
        Unit: millivolt, mV
        "
    ::= { hwMonitorTestOprEntry 1 }
    
    hwMonitorTestBGV OBJECT-TYPE
    SYNTAX Integer32
    MAX-ACCESS  read-only
    STATUS      current
    DESCRIPTION
        "
        Monitor test B->ground voltage.
        Unit: millivolt, mV
        "
    ::= { hwMonitorTestOprEntry 2 }   
    
    hwMonitorTestLongitudinalCurrent OBJECT-TYPE
    SYNTAX Integer32
    MAX-ACCESS  read-only
    STATUS      current
    DESCRIPTION
        "
        Monitor test Longitudinal Current.
        Unit: uA
        "
    ::= { hwMonitorTestOprEntry 3 }    
    
    hwMonitorTestTransversalCurrent OBJECT-TYPE
    SYNTAX Integer32
    MAX-ACCESS  read-only
    STATUS      current
    DESCRIPTION
        "
        Monitor test Transversal Current.
        Unit: uA
        "
    ::= { hwMonitorTestOprEntry 4 }   
    
    hwMonitorTestBatteryVoltage OBJECT-TYPE
    SYNTAX Integer32
    MAX-ACCESS  read-only
    STATUS      current
    DESCRIPTION
        "
        Monitor test Battery Voltage.
        Unit: millivolt, mV
        "
    ::= { hwMonitorTestOprEntry 5 } 
    
    hwMonitorTestSLICTemperature OBJECT-TYPE
    SYNTAX Integer32
    MAX-ACCESS  read-only
    STATUS      current
    DESCRIPTION
        "
        Monitor test SLIC Temperature.
        Unit: oC
        "
    ::= { hwMonitorTestOprEntry 6 }
    
END
