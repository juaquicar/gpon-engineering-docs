-- ============================================================================
-- Copyright (C) 2015 by  HUAWEI TECHNOLOGIES. All rights reserved.
-- Description: The MIB is used for defining Huawei's EPON NNI management MIB objects. 
-- Reference:
-- Version: V1.23
-- ============================================================================
    HUAWEI-EPONNNI-MIB DEFINITIONS ::= BEGIN

        IMPORTS
            huaweiUtility
                FROM HUAWEI-MIB
            MODULE-IDENTITY, OBJECT-TYPE, Unsigned32, NOTIFICATION-TYPE, Integer32, Counter32,Counter64
                FROM SNMPv2-SMI
            huaweiMgmt
                FROM HUAWEI-MIB
            ifIndex
                FROM IF-MIB
            hwFrameIndex, hwSlotIndex, hwPortIndex, hwConfigChangeIP
                FROM HUAWEI-DEVICE-MIB
            TruthValue, RowStatus, MacAddress
                FROM SNMPv2-TC
            SnmpAdminString
                FROM SNMP-FRAMEWORK-MIB
            HCPerfIntervalThreshold, HCPerfTimeElapsed
                FROM  HC-PerfHist-TC-MIB
            MODULE-COMPLIANCE, OBJECT-GROUP, NOTIFICATION-GROUP
                FROM SNMPv2-CONF;

        hwEponMIB MODULE-IDENTITY
            LAST-UPDATED "201511250000Z"
            ORGANIZATION "Huawei Technologies Co.,Ltd."
            CONTACT-INFO                                 
                         "Huawei Industrial Base         
                          Bantian, Longgang              
                          Shenzhen 518129                
                          People's Republic of China     
                          Website: http://www.huawei.com 
                          Email: support@huawei.com      
                         "                               
            DESCRIPTION
                "The MIB is used for defining Huawei's EPON NNI management MIB objects."
                
-- Revision history
            REVISION    "201511250000Z"
            DESCRIPTION "V1.23, changes in this revision:
                         - Modify the value range of the leaf node hwEponnniOpticsModuleSubType.
                        "
                        
            REVISION    "201210270000Z"
            DESCRIPTION "V1.21, changes in this revision:
                         - Modify the node hwEponnniPasswordChangeTrap name to hwEponnniAuthChangeTrap.
                        "
                        
            REVISION    "201207200000Z"
            DESCRIPTION "V1.20, changes in this revision:
                         - Delete unnecessary en dashes.
                        "
                        
            REVISION    "201205160900Z"
            DESCRIPTION "V1.19, changes in this revision:
                         - Modify the value range of the leaf node hwEponNniKeyLoid and hwEponNniKeyCheckCode.
                        "
                        
	    REVISION    "201105100900Z"
            DESCRIPTION "V1.18, changes in this revision:
                         - Modify the enum values of the leaf node hwEponnniOpticsModuleSubType and 
                           hwEponnniOpticsModuleType for obtaining optical-module information.
                         - Add leaf node hwEponnniOpticsModuleType, hwEponnniOpticsModuleSubType, hwEponnniOpticsModuleUsedType, 
                           hwEponnniOpticsModuleEncapsulationType in table hwEponnniCfgTable for obtaining optical-module information.
                        "	    
	    
            REVISION    "201009280900Z"
            DESCRIPTION "V1.15, changes in this revision:
                         - Add leaf node hwEponnniClearThreshold in table hwEponNniAlarmThresholdTable for clear optical-module threshold.
                        "

            REVISION    "201006300900Z"
            DESCRIPTION "V1.14, changes in this revision:
                         Modify the definition of the trap node: hwEponnniPasswordChangeTrap for trap optimization.
                        "
            REVISION    "201006220900Z"
            DESCRIPTION "V1.13, changes in this revision:
                         Modify chinese character and module name.
                        "

            REVISION    "201004080900Z"
            DESCRIPTION "V1.12, changes in this revision:
                         Add hwEponnniOntRogueOntFailAlarmTrap for sending trap when EPON ONU's optical-module always send laser.
                         Add hwEponnniOntRogueOntRestoreAlarmTrap for sending trap when EPON ONU's optical module always send laser alarm recovery.
                         Add hwEponnniTempeExceedThreAlarmTrap for sending trap when the temperature of EPON ONU's optical-module exceeded alarm threshold.
                         Add hwEponnniTempeExceedThreRestoreAlarmTrap for sending trap when the temperature of EPON ONU's optical-module
                         exceeded alarm threshold recovery.
                         Add hwEponnniVoltExceedThreAlarmTrap for sending trap when the voltage of EPON ONU's optical-module exceeded alarm threshold.
                         Add hwEponnniVoltExceedThreRestoreAlarmTrap for sending trap when the voltage of EPON ONU's optical-module exceeded alarm threshold recovery.
                         Add hwEponnniBiasExceedThreAlarmTrap for sending trap when the bias electrical current of EPON ONU's optical-module exceeded alarm threshold.
                         Add hwEponnniBiasExceedThreRestoreAlarmTrap for sending trap when The bias electric current of EPON ONU's optical-module
                         exceeded alarm threshold recovery.
                         Add hwEponnniTxPowerExceedThreAlarmTrap for sending trap when the tx-power of EPON ONU's optical-module exceeded alarm threshold.
                         Add hwEponnniTxPowerExceedThreRestoreRestoreAlarmTrap for sending trap when the tx-power of EPON ONU's optical-module exceeded alarm threshold recovery.
                         Add hwEponnniRxPowerExceedThreAlarmTrap for sending trap when the rx-power of EPON ONU's optical-module exceeded alarm threshold.
                         Add hwEponnniRxPowerExceedThreRestoreAlarmTrap for sending trap when the rx-power of EPON ONU's optical-module exceeded alarm threshold recovery.
                         Add hwEponnniPortSwitchAlarmTrap for sending trap when protection switchover occurs on the PON port.
                        "

            REVISION    "201002080900Z"
            DESCRIPTION "V1.11, changes in this revision:
                         Modify hwEponnniTypeDPortSwitchTrap.
                        "

            REVISION    "201001290900Z"
            DESCRIPTION "V1.10, changes in this revision:
                         Add leaf nodes hwEponniRxUnicastFrames, hwEponniRxMulticastFrames, hwEponniRxBroadcastFrames, hwEponniRx64BytesFrames,
                         hwEponniRx65to127BytesFrames, hwEponniRx128to255BytesFrames, hwEponniRx256to511BytesFrames, hwEponniRx512to1023BytesFrames,
                         hwEponniRx1024to1518BytesFrames, hwEponniRxOver1518BytesFrames, hwEponniRxUndersizeFrames, hwEponniRxOversizeFrames ,
                         hwEponniRxCrcErrorFrames, hwEponniRxDiscardedFrames, hwEponniTxUnicastFrames,hwEponniTxMulticastFrames,
                         hwEponniTxBroadcastFrames, hwEponniTx64BytesFrames, hwEponniTx65to127BytesFrames, hwEponniTx128to255BytesFrames,
                         hwEponniTx256to511BytesFrames, hwEponniTx512to1023BytesFrames, hwEponniTx1024to1518BytesFrames,
                         hwEponniTxOver1518BytesFrames and hwEponnniPonRxErrFramesCnt in table hwEponnniStatisticsTable
                         for getting statistics information.
                         Add leaf nodes hwEponnniTxPowerUpperThreshold, hwEponnniTxPowerLowerThreshold, hwEponnniBiasUpperThreshold,
                         hwEponnniBiasLowerThreshold, hwEponnniTemperatureUpperThreshold, hwEponnniTemperatureLowerThreshold,
                         hwEponnniVoltageUpperThreshold and hwEponnniVoltageLowerThreshold for setting or obtaining optical module alarm threshold.
                        "

            REVISION    "201001120900Z"
            DESCRIPTION "V1.09, changes in this revision:
                         Add hwEponnniTypeDPortSwitchTrap for sending trap when protection switchover occurs on the PON port.
                         Add hwEponnniXponModeSwitchResultTrap for sending trap when xpon mode switch.
                        "

            REVISION    "200910230900Z"
            DESCRIPTION "V1.08, changes in this revision:
                         Add leaf nodes hwEponnniUniTxOkOctetsCnt and hwEponnniUniRxOkOctetsCnt in table hwEponnniStatisticsTable
                         for getting statistics information.
                         Add leaf nodes hwEponnniOnuRogueOntState, hwEponnniActiveStatus, hwEponNniKeyLoid
                         and hwEponNniKeyCheckCode for setting or obtaining EPON NNI information.
                        "

            REVISION    "200905080900Z"
            DESCRIPTION "V1.06, changes in this revision:
                         Add leaf node hwEponnniPassword in table for setting password.
                        "

            REVISION    "200809280900Z"
            DESCRIPTION "V1.03, changes in this revision:
                         Add table hwEponnniAlarmThresholdTable for setting or obtaining optical module alarm threshold
                         Add table hwEponNniHistoryStatsTable for obtaining history statistics information.
                         Add leaf nodes hwEponnniTrafficBroadcast, hwEponnniTrafficMulticast, hwEponnniTrafficUnknowncast
                         hwEponnniTxPower, hwEponnniRxPower, hwEponnniTemperature, hwEponnniBiasCurrent
                         and hwEponnniVoltage in table hwEponnniCfgTable for setting or obtaining EPON NNI information.
                        "

            REVISION    "200711020900Z"
            DESCRIPTION "V1.00, Initial version."
            ::= { huaweiUtility 119 }

        hwEponnni   OBJECT IDENTIFIER ::= { hwEponMIB 1 }
        hwEponnniTrapsVbOids  OBJECT IDENTIFIER ::= { hwEponMIB 2 }
        hwEponnniCommonTraps  OBJECT IDENTIFIER ::= { hwEponMIB 3 }
        hwEponnniAlarmTraps  OBJECT IDENTIFIER ::= { hwEponMIB 4 }
        hwEponnniCommonTrapsPrefix  OBJECT IDENTIFIER ::= { hwEponnniCommonTraps 0 }
        hwEponnniAlarmTrapsPrefix  OBJECT IDENTIFIER ::= { hwEponnniAlarmTraps 0 }

        hwEponnniNotifications  OBJECT IDENTIFIER ::= { hwEponnni 0 }
        hwEponnniCfg            OBJECT IDENTIFIER ::= { hwEponnni 1 }
        hwEponnniStatistics     OBJECT IDENTIFIER ::= { hwEponnni 2 }
        hwEponNniHistoryStats       OBJECT IDENTIFIER ::= { hwEponnni 3 }
        hwEponnniAlarmThreshold   OBJECT IDENTIFIER ::= { hwEponnni 4 }

        --          Notifications Group          
        hwEponnniLOSTrap NOTIFICATION-TYPE
            OBJECTS {
                hwFrameIndex,
                hwSlotIndex,
                hwPortIndex
            }
            STATUS     current
            DESCRIPTION
                "This trap is sent when LOS(Loss of Signal) EPON NNI line happened.
                "
            ::= { hwEponnniNotifications 1 }

        hwEponnniUnRegisterTrap NOTIFICATION-TYPE
            OBJECTS {
                hwFrameIndex,
                hwSlotIndex,
                hwPortIndex
            }
            STATUS     current
            DESCRIPTION
                "This trap is sent when unregistered event of EPON NNI happened."
            ::= { hwEponnniNotifications 2 }

        --             EponnniCfg                     
        hwEponnniCfgTable  OBJECT-TYPE
            SYNTAX      SEQUENCE  OF  HwEponnniCfgEntry
            MAX-ACCESS  not-accessible
            STATUS      current
            DESCRIPTION
                "The table Eponnni config the EPON NNI, include manage EPON NNI, EPON NNI status information and inquire chipset.
                 The index of this table is ifIndex.
                "
            ::= { hwEponnniCfg 1 }

        hwEponnniCfgEntry  OBJECT-TYPE
            SYNTAX      HwEponnniCfgEntry
            MAX-ACCESS  not-accessible
            STATUS      current
            DESCRIPTION
                "The table Eponnni config the EPON NNI, include manage EPON NNI, EPON NNI status information and inquire chipset.
                 The index of this entry is ifIndex.
                "
            INDEX  { ifIndex }
            ::= { hwEponnniCfgTable 1 }

        HwEponnniCfgEntry  ::=
            SEQUENCE {
                hwEponnniMgntLaserMode      INTEGER,
                hwEponnniSubboardReset      INTEGER,
                hwEponnniLinkStatus         INTEGER,
                hwEponnniRegStatus          INTEGER,
                hwEponnniTxSpeed            Unsigned32,
                hwEponnniRxSpeed            Unsigned32,
                hwEponnniMac                MacAddress,
                hwEponnniHardwareVer        OCTET STRING,
                hwEponnniFirmwareVer        OCTET STRING,
                hwEponnniOamVer             OCTET STRING,
                hwEponnniTrafficBroadcast   Integer32,
                hwEponnniTrafficMulticast   Integer32,
                hwEponnniTrafficUnknowncast Integer32,
                hwEponnniTxPower            Integer32,
                hwEponnniRxPower            Integer32,
                hwEponnniTemperature        Integer32,
                hwEponnniBiasCurrent        Integer32,
                hwEponnniVoltage            Integer32,
                hwEponnniPassword           OCTET STRING,
                hwEponnniOnuRogueOntState   INTEGER,
                hwEponnniActiveStatus       INTEGER,
                hwEponNniKeyLoid            OCTET STRING,
                hwEponNniKeyCheckCode       OCTET STRING,
		hwEponnniOpticsModuleType               INTEGER,
		hwEponnniOpticsModuleSubType            INTEGER,
                hwEponnniOpticsModuleUsedType		INTEGER,
                hwEponnniOpticsModuleEncapsulationType	INTEGER
            }

        hwEponnniMgntLaserMode  OBJECT-TYPE
            SYNTAX      INTEGER {
                auto(0),
                off(1),
                on(2)
            }
            MAX-ACCESS  read-write
            STATUS      current
            DESCRIPTION
                "Describes the laser mode,
                 Options:
                 1. auto(0) - EPON NNI laser auto
                 2. off(1)  - EPON NNI laser off
                 3. on(2)   - EPON NNI laser on
                "
            ::= { hwEponnniCfgEntry 1 }

        hwEponnniSubboardReset  OBJECT-TYPE
            SYNTAX      INTEGER {
                reset(1)
            }
            MAX-ACCESS  read-write
            STATUS      current
            DESCRIPTION
                "Reset the sub board of EPON.
                 Options:
                 1. reset(1) - Reset the sub board
                "
            ::= { hwEponnniCfgEntry 2 }

        hwEponnniLinkStatus  OBJECT-TYPE
            SYNTAX      INTEGER {
                linkDown(1),
                linkUp(2)
            }
            MAX-ACCESS  read-only
            STATUS      current
            DESCRIPTION
                "Describes the port link status,
                 Options:
                 1. linkDown(1) - Can't receive optic signal
                 2. linkUp(2)   - Received optic signal
                "
            ::= { hwEponnniCfgEntry 3 }

        hwEponnniRegStatus  OBJECT-TYPE
            SYNTAX      INTEGER {
                registered(1),
                unregistered(2)
            }
            MAX-ACCESS  read-only
            STATUS      current
            DESCRIPTION
                "Describes the port register status,
                 Options:
                 1. registered(1)   - The port is authenticated successfully
                 2. unregistered(2) - The port fails to be authenticated
                "
            ::= { hwEponnniCfgEntry 4 }

        hwEponnniTxSpeed  OBJECT-TYPE
            SYNTAX      Unsigned32
            UNITS       "Mbps"
            MAX-ACCESS  read-only
            STATUS      current
            DESCRIPTION
                "The port up stream speed.
                 Unit:Mbps
                "
            ::= { hwEponnniCfgEntry 5 }

        hwEponnniRxSpeed  OBJECT-TYPE
            SYNTAX      Unsigned32
            UNITS       "Mbps"
            MAX-ACCESS  read-only
            STATUS      current
            DESCRIPTION
                "The port down stream speed.
                 Unit:Mbps
                "
            ::= { hwEponnniCfgEntry 6 }

        hwEponnniMac  OBJECT-TYPE
            SYNTAX      MacAddress
            MAX-ACCESS  read-only
            STATUS      current
            DESCRIPTION
                "The MAC address of EPON chipset."
            ::= { hwEponnniCfgEntry 7 }

        hwEponnniHardwareVer  OBJECT-TYPE
            SYNTAX      OCTET STRING
            MAX-ACCESS  read-only
            STATUS      current
            DESCRIPTION
                "The hardware version of EPON chipset."
            ::= { hwEponnniCfgEntry 8 }

        hwEponnniFirmwareVer  OBJECT-TYPE
            SYNTAX      OCTET STRING
            MAX-ACCESS  read-only
            STATUS      current
            DESCRIPTION
                "The firmware version of EPON chipset."
            ::= { hwEponnniCfgEntry 9 }

        hwEponnniOamVer  OBJECT-TYPE
            SYNTAX      OCTET STRING
            MAX-ACCESS  read-only
            STATUS      current
            DESCRIPTION
                "The OAM version of EPON chipset."
            ::= { hwEponnniCfgEntry 10 }

        hwEponnniTrafficBroadcast OBJECT-TYPE
            SYNTAX Integer32 (0..13)
            MAX-ACCESS read-write
            STATUS current
            DESCRIPTION
                "Traffic Broadcast of Eponnni Port,0 is off, 13 is complete.
                 Traffic suppression ID definition:
                 
                  NO.  Min bandwidth(kbps)  Max bandwidth(kbps)  Package number(pps)
                    1                    6                  145                   12
                    2                   12                  291                   24
                    3                   24                  582                   48
                    4                   48                 1153                   95
                    5                   97                 2319                  191
                    6                  195                 4639                  382
                    7                  390                 9265                  763
                    8                  781                18531                 1526
                    9                 1562                37063                 3052
                   10                 3125                74126                 6104
                   11                 6249               148241                12207
                   12                12499               296483                24414
                   13                    0                    0                    0
                "
                
            ::= { hwEponnniCfgEntry 11 }

        hwEponnniTrafficMulticast OBJECT-TYPE
            SYNTAX Integer32 (0..13)
            MAX-ACCESS read-write
            STATUS current
            DESCRIPTION
                "Traffic Multicast of Eponnni Port,0 is off, 13 is complete.
                 Traffic suppression ID definition:
                 
                  NO.  Min bandwidth(kbps)  Max bandwidth(kbps)  Package number(pps)               
                    1                    6                  145                   12
                    2                   12                  291                   24
                    3                   24                  582                   48
                    4                   48                 1153                   95
                    5                   97                 2319                  191
                    6                  195                 4639                  382
                    7                  390                 9265                  763
                    8                  781                18531                 1526
                    9                 1562                37063                 3052
                   10                 3125                74126                 6104
                   11                 6249               148241                12207
                   12                12499               296483                24414
                   13                    0                    0                    0
                "
            ::= { hwEponnniCfgEntry 12 }

        hwEponnniTrafficUnknowncast OBJECT-TYPE
            SYNTAX Integer32 (0..13)
            MAX-ACCESS read-write
            STATUS current
            DESCRIPTION
                "Traffic unicast of Eponnni Port,0 is off, 13 is complete.
                 Traffic suppression ID definition:   
                           
                  NO.  Min bandwidth(kbps)  Max bandwidth(kbps)  Package number(pps)                 
                    1                    6                  145                   12
                    2                   12                  291                   24
                    3                   24                  582                   48
                    4                   48                 1153                   95
                    5                   97                 2319                  191
                    6                  195                 4639                  382
                    7                  390                 9265                  763
                    8                  781                18531                 1526
                    9                 1562                37063                 3052
                   10                 3125                74126                 6104
                   11                 6249               148241                12207
                   12                12499               296483                24414
                   13                    0                    0                    0
                "
            ::= { hwEponnniCfgEntry 13 }

        hwEponnniTxPower  OBJECT-TYPE
            SYNTAX      Integer32
            MAX-ACCESS  read-only
            STATUS      current
            DESCRIPTION
                "The MDU TX power. It ranges from -10000 to 10000 units of 1/100 dBm."
            ::= { hwEponnniCfgEntry 14 }

        hwEponnniRxPower  OBJECT-TYPE
            SYNTAX      Integer32
            MAX-ACCESS  read-only
            STATUS      current
            DESCRIPTION
                "The MDU RX power. It ranges from -10000 to 10000 units of 1/100 dBm."
            ::= { hwEponnniCfgEntry 15 }

        hwEponnniTemperature  OBJECT-TYPE
            SYNTAX      Integer32
            MAX-ACCESS  read-only
            STATUS      current
            DESCRIPTION
                "The MDU Temperature. It ranges from -10000 to 10000 units of 1/100 C."
            ::= { hwEponnniCfgEntry 16 }

        hwEponnniBiasCurrent  OBJECT-TYPE
            SYNTAX      Integer32
            MAX-ACCESS  read-only
            STATUS      current
            DESCRIPTION
                "The MDU Laser Bias Electricity. It ranges from -10000 to 10000 units of 1/100 mA."
            ::= { hwEponnniCfgEntry 17 }

        hwEponnniVoltage  OBJECT-TYPE
            SYNTAX      Integer32
            MAX-ACCESS  read-only
            STATUS      current
            DESCRIPTION
                "The MDU Voltage. It ranges from -10000 to 10000 units of 1/100 mV."
            ::= { hwEponnniCfgEntry 18 }

        hwEponnniPassword OBJECT-TYPE
            SYNTAX OCTET STRING  (SIZE(0..32))
            MAX-ACCESS read-write
            STATUS current
            DESCRIPTION
                "The password of the EPON ONU."
            ::= { hwEponnniCfgEntry 19 }

        hwEponnniOnuRogueOntState  OBJECT-TYPE
            SYNTAX      INTEGER {
                yes(1),
                no(2)
            }
            MAX-ACCESS  read-only
            STATUS      current
            DESCRIPTION
                "Indicates whether the optical port is shut down due to the continuous mode(rogue ONT).
                 Options:
                 1. yes(1)  - Port is shut down due to the continuous mode
                 2. no(2)   - Port is not shut down due to the continuous mode
                 "
            ::= { hwEponnniCfgEntry 20 }

        hwEponnniActiveStatus  OBJECT-TYPE
            SYNTAX      INTEGER {
                active(1),
                standby(2)
            }
            MAX-ACCESS  read-only
            STATUS      current
            DESCRIPTION
                "Describes the EPONNNI port TYPED protect state.
                 Options:
                 1. active(1)  - Active state
                 2. standby(2) - Standby state
                "
            ::= { hwEponnniCfgEntry 21 }

        hwEponNniKeyLoid OBJECT-TYPE
            SYNTAX OCTET STRING  (SIZE(0..24))
            MAX-ACCESS read-write
            STATUS current
            DESCRIPTION
                "The loid of the EPON ONU."
            ::= { hwEponnniCfgEntry 22 }

        hwEponNniKeyCheckCode OBJECT-TYPE
            SYNTAX OCTET STRING  (SIZE(0..12))
            MAX-ACCESS read-write
            STATUS current
            DESCRIPTION
                "The checkcode of the EPON ONU."
            ::= { hwEponnniCfgEntry 23 }
            
	hwEponnniOpticsModuleType OBJECT-TYPE
	    SYNTAX      INTEGER {
                unknown(1),
	        gpon(2),
	        epon(3),
	        epon10g(4),
	        gpon10g(5),
	        wdmpon(6),
	        hybridpon(7),
	        gponepon(8),
	        invalid(-1)
	    }
	    MAX-ACCESS  read-only
	    STATUS      current
	    DESCRIPTION
	        "This object indicates the type of the optical transceiver.
                 Options:
                 1. unknown(1)  - Unknow
	         2. gpon(2)     - GPON
	         3. epon(3)     - EPON
	         4. epon10g(4)  - 10G EPON
	         5. gpon10g(5)  - 10G GPON
	         6. wdmpon(6)   - WDM PON
	         7. hybridpon(7)- Hybrid PON
	         8. gponepon(8) - GPON and EPON
	         9. invalid(-1) - Indicates that the query fails or no information is detected
                 "
	    ::= { hwEponnniCfgEntry 24 }
    
	hwEponnniOpticsModuleSubType OBJECT-TYPE
	    SYNTAX      INTEGER {
	        unknown(1),
	        classbplus(101),
	        classcplus(102),
	        classb(103),
	        px20(201),
	        px20plus(202),
	        pr30(301),
	        pr20(302), 
	        prx30(303), 
	        prx20(304),
	        classbplusandpx20plus(701),
	        n2a(405),
	        n2b(406),
	        n1(407),
	        invalid(-1)
	   }
	   MAX-ACCESS  read-only
	   STATUS      current
	   DESCRIPTION
	       "This object indicates the sub type of the optical transceiver.
                Options:
                1.unknown(1)                 - Unknow 
	        2.classbplus(101)            - CLASS B+
	        3.classcplus(102)            - CLASS C+
	        4.classb(103)                - CLASS B
	        5.px20(201)                  - PX20
	        6.px20plus(202)              - PX20+
	        7.pr30(301)                  - PR30
	        8.pr20(302)                  - PR20
	        9.prx30(303)                 - PRX30 
	        10.prx20(304)                - PRX20
		11.classbplusandpx20plus(701)- CLASS B+ and PX20+
		12.n2a(405)                  - N2A
                13.n2b(406)                  - N2B
                14.n1(407)                   - N1
	        15.invalid(-1)               - Indicates that the query fails or no information is detected
               "
	   ::= { hwEponnniCfgEntry 25 }
	
	hwEponnniOpticsModuleUsedType OBJECT-TYPE
	   SYNTAX      INTEGER {
	       unknown(1),
	       olt(2),
	       ont(3),
	       onu(4),
	       invalid(-1)
           }
	   MAX-ACCESS  read-only
	   STATUS      current
	   DESCRIPTION
	       "This object indicates the application scenario of the optical transceiver.
                Options:
                1.unknown(1)   - Unknow
	        2.olt(2)       - OLT
	        3.ont(3)       - ONT, This enumeration is obsolete.
	        4.onu(4)       - ONU
	        5.invalid(-1)  - Indicates that the query fails or no information is detected
	        "
           ::= { hwEponnniCfgEntry 26 }
	    
	hwEponnniOpticsModuleEncapsulationType OBJECT-TYPE
	   SYNTAX      INTEGER {
	       unknown(1),
	       sff2x5(2),
	       sff2x10(3), 
	       sfp(4), 
	       xfp(5), 
	       lxfp(6), 
	       bosaonboard(7),
	       invalid(-1)
	    }
	    MAX-ACCESS  read-only
	    STATUS      current
	    DESCRIPTION
	        "This object indicates the encapsulation information about the optical transceiver.
                Options:
                1. unknown(1)    - Unknown
 	        2. sff2x5(2)     - SFF 2x5
 	        3. sff2x10(3)    - SFF 2x10
 	        4. sfp(4)        - SFP
 	        5. xfp(5)        - XFP
 	        6. lxfp(6)       - LXFP
 	        7. bosaonboard(7)- BOSA ON BOARD
 	        8. invalid(-1)   - Indicates that the query fails or no information is detected
		"
	    ::= { hwEponnniCfgEntry 27 }
	
        --            EponnniStatistics               
        hwEponnniStatisticsTable  OBJECT-TYPE
            SYNTAX      SEQUENCE  OF  HwEponnniStatisticsEntry
            MAX-ACCESS  not-accessible
            STATUS      current
            DESCRIPTION
                "This table is used to query the statistics of the EPON port.
                 The index of this table is ifIndex.
                "
            ::= { hwEponnniStatistics 1 }

        hwEponnniStatisticsEntry  OBJECT-TYPE
            SYNTAX      HwEponnniStatisticsEntry
            MAX-ACCESS  not-accessible
            STATUS      current
            DESCRIPTION
                "This table is used to query the statistics of the EPON port.
                 The index of this entry is ifIndex.
                "
            INDEX  { ifIndex }
            ::= { hwEponnniStatisticsTable 1 }

        HwEponnniStatisticsEntry  ::=
            SEQUENCE {
                hwEponnniPonTxFramesCnt         Counter32,
                hwEponnniPonRxFramesCnt         Counter32,
                hwEponnniPonRxFECErrFramesCnt   Counter32,
                hwEponnniPonRxHECErrFramesCnt   Counter32,
                hwEponnniPonTxPQDropFramesCnt   Counter32,
                hwEPonnniUniTxFramesCnt         Counter32,
                hwEPonnniUniRxFramesCnt         Counter32,
                hwEponnniUniRxFECErrFramesCnt   Counter32,
                hwEponnniUniTxPQDropFramesCnt   Counter32,
                hwEponnniStatisticsClear        INTEGER,
                hwEponnniUniTxOkOctetsCnt       Counter64,
                hwEponnniUniRxOkOctetsCnt       Counter64,
                hwEponniRxUnicastFrames         Counter32,
                hwEponniRxMulticastFrames       Counter32,
                hwEponniRxBroadcastFrames       Counter32,
                hwEponniRx64BytesFrames         Counter32,
                hwEponniRx65to127BytesFrames    Counter32,
                hwEponniRx128to255BytesFrames   Counter32,
                hwEponniRx256to511BytesFrames   Counter32,
                hwEponniRx512to1023BytesFrames  Counter32,
                hwEponniRx1024to1518BytesFrames Counter32,
                hwEponniRxOver1518BytesFrames   Counter32,
                hwEponniRxUndersizeFrames       Counter32,
                hwEponniRxOversizeFrames        Counter32,
                hwEponniRxCrcErrorFrames        Counter32,
                hwEponniRxDiscardedFrames       Counter32,
                hwEponniTxUnicastFrames         Counter32,
                hwEponniTxMulticastFrames       Counter32,
                hwEponniTxBroadcastFrames       Counter32,
                hwEponniTx64BytesFrames         Counter32,
                hwEponniTx65to127BytesFrames    Counter32,
                hwEponniTx128to255BytesFrames   Counter32,
                hwEponniTx256to511BytesFrames   Counter32,
                hwEponniTx512to1023BytesFrames  Counter32,
                hwEponniTx1024to1518BytesFrames Counter32,
                hwEponniTxOver1518BytesFrames   Counter32,
                hwEponnniPonRxErrFramesCnt      Counter32
            }

        hwEponnniPonTxFramesCnt  OBJECT-TYPE
            SYNTAX      Counter32
            MAX-ACCESS  read-only
            STATUS      current
            DESCRIPTION
                "The PON port send OK frames."
            ::= { hwEponnniStatisticsEntry 1 }

        hwEponnniPonRxFramesCnt  OBJECT-TYPE
            SYNTAX      Counter32
            MAX-ACCESS  read-only
            STATUS      current
            DESCRIPTION
                "The PON received OK frames."
            ::= { hwEponnniStatisticsEntry 2 }

        hwEponnniPonRxFECErrFramesCnt  OBJECT-TYPE
            SYNTAX      Counter32
            MAX-ACCESS  read-only
            STATUS      current
            DESCRIPTION
                "The PON received FEC error frames."
            ::= { hwEponnniStatisticsEntry 3 }

        hwEponnniPonRxHECErrFramesCnt  OBJECT-TYPE
            SYNTAX      Counter32
            MAX-ACCESS  read-only
            STATUS      current
            DESCRIPTION
                "The PON received HEC error frames."
            ::= { hwEponnniStatisticsEntry 4 }

        hwEponnniPonTxPQDropFramesCnt  OBJECT-TYPE
            SYNTAX      Counter32
            MAX-ACCESS  read-only
            STATUS      current
            DESCRIPTION
                "The PON send PQ drop frames."
            ::= { hwEponnniStatisticsEntry 5 }

        hwEPonnniUniTxFramesCnt  OBJECT-TYPE
            SYNTAX      Counter32
            MAX-ACCESS  read-only
            STATUS      current
            DESCRIPTION
                "The UNI send OK frames."
            ::= { hwEponnniStatisticsEntry 6 }

        hwEPonnniUniRxFramesCnt  OBJECT-TYPE
            SYNTAX      Counter32
            MAX-ACCESS  read-only
            STATUS      current
            DESCRIPTION
                "The UNI received OK frames."
            ::= { hwEponnniStatisticsEntry 7 }

        hwEponnniUniRxFECErrFramesCnt  OBJECT-TYPE
            SYNTAX      Counter32
            MAX-ACCESS  read-only
            STATUS      current
            DESCRIPTION
                "The UNI received FEC error frames."
            ::= { hwEponnniStatisticsEntry 8 }

        hwEponnniUniTxPQDropFramesCnt  OBJECT-TYPE
            SYNTAX      Counter32
            MAX-ACCESS  read-only
            STATUS      current
            DESCRIPTION
                "The UNI send PQ drop frames."
            ::= { hwEponnniStatisticsEntry 9 }

        hwEponnniStatisticsClear  OBJECT-TYPE
            SYNTAX      INTEGER {
                resetStat(1)
            }
            MAX-ACCESS  read-write
            STATUS      current
            DESCRIPTION
                "Clear the statistics of EPON NNI,
                 Options:
                 1. resetStat(1) - Clear the statistics
                "
            ::= { hwEponnniStatisticsEntry 10 }

        hwEponnniUniTxOkOctetsCnt  OBJECT-TYPE
            SYNTAX      Counter64
            MAX-ACCESS  read-only
            STATUS      current
            DESCRIPTION
                "The UNI send OK Bytes."
            ::= { hwEponnniStatisticsEntry 11 }

        hwEponnniUniRxOkOctetsCnt  OBJECT-TYPE
            SYNTAX      Counter64
            MAX-ACCESS  read-only
            STATUS      current
            DESCRIPTION
                "The UNI received OK Bytes."
            ::= { hwEponnniStatisticsEntry 12 }

        hwEponniRxUnicastFrames  OBJECT-TYPE
            SYNTAX      Counter32
            MAX-ACCESS  read-only
            STATUS      current
            DESCRIPTION
                "The PON received unicast frames."
            ::= { hwEponnniStatisticsEntry 13 }

        hwEponniRxMulticastFrames  OBJECT-TYPE
            SYNTAX      Counter32
            MAX-ACCESS  read-only
            STATUS      current
            DESCRIPTION
                "The PON received multicast frames."
            ::= { hwEponnniStatisticsEntry 14 }

        hwEponniRxBroadcastFrames  OBJECT-TYPE
            SYNTAX      Counter32
            MAX-ACCESS  read-only
            STATUS      current
            DESCRIPTION
                "The PON received broadcast frames."
            ::= { hwEponnniStatisticsEntry 15 }

        hwEponniRx64BytesFrames  OBJECT-TYPE
            SYNTAX      Counter32
            MAX-ACCESS  read-only
            STATUS      current
            DESCRIPTION
                "The PON received frames of 64 bytes."
            ::= { hwEponnniStatisticsEntry 16 }

        hwEponniRx65to127BytesFrames  OBJECT-TYPE
            SYNTAX      Counter32
            MAX-ACCESS  read-only
            STATUS      current
            DESCRIPTION
                "The PON received frames of 65~127 bytes."
            ::= { hwEponnniStatisticsEntry 17 }

        hwEponniRx128to255BytesFrames  OBJECT-TYPE
            SYNTAX      Counter32
            MAX-ACCESS  read-only
            STATUS      current
            DESCRIPTION
                "The PON received frames of 128~255 bytes."
            ::= { hwEponnniStatisticsEntry 18 }
        hwEponniRx256to511BytesFrames  OBJECT-TYPE
            SYNTAX      Counter32
            MAX-ACCESS  read-only
            STATUS      current
            DESCRIPTION
                "The PON received frames of 256~511 bytes."
            ::= { hwEponnniStatisticsEntry 19 }

        hwEponniRx512to1023BytesFrames  OBJECT-TYPE
            SYNTAX      Counter32
            MAX-ACCESS  read-only
            STATUS      current
            DESCRIPTION
                "The PON received frames of 512~1023 bytes."
            ::= { hwEponnniStatisticsEntry 20 }

        hwEponniRx1024to1518BytesFrames  OBJECT-TYPE
            SYNTAX      Counter32
            MAX-ACCESS  read-only
            STATUS      current
            DESCRIPTION
                "The PON received frames of 1024~1518 bytes."
            ::= { hwEponnniStatisticsEntry 21 }

        hwEponniRxOver1518BytesFrames  OBJECT-TYPE
            SYNTAX      Counter32
            MAX-ACCESS  read-only
            STATUS      current
            DESCRIPTION
                "The PON received frames of over 1518 bytes."
            ::= { hwEponnniStatisticsEntry 22 }

        hwEponniRxUndersizeFrames  OBJECT-TYPE
            SYNTAX      Counter32
            MAX-ACCESS  read-only
            STATUS      current
            DESCRIPTION
                "The PON received under size frames."
            ::= { hwEponnniStatisticsEntry 23 }

        hwEponniRxOversizeFrames  OBJECT-TYPE
            SYNTAX      Counter32
            MAX-ACCESS  read-only
            STATUS      current
            DESCRIPTION
                "The PON received over size frames."
            ::= { hwEponnniStatisticsEntry 24 }

        hwEponniRxCrcErrorFrames  OBJECT-TYPE
            SYNTAX      Counter32
            MAX-ACCESS  read-only
            STATUS      current
            DESCRIPTION
                "The PON received crc error frames."
            ::= { hwEponnniStatisticsEntry 25}

        hwEponniRxDiscardedFrames  OBJECT-TYPE
            SYNTAX      Counter32
            MAX-ACCESS  read-only
            STATUS      current
            DESCRIPTION
                "The PON received discarded frames."
            ::= { hwEponnniStatisticsEntry 26 }

        hwEponniTxUnicastFrames  OBJECT-TYPE
            SYNTAX      Counter32
            MAX-ACCESS  read-only
            STATUS      current
            DESCRIPTION
                "The PON send unicast frames."
            ::= { hwEponnniStatisticsEntry 27 }

        hwEponniTxMulticastFrames  OBJECT-TYPE
            SYNTAX      Counter32
            MAX-ACCESS  read-only
            STATUS      current
            DESCRIPTION
                "The PON send multicast frames."
            ::= { hwEponnniStatisticsEntry 28 }

        hwEponniTxBroadcastFrames  OBJECT-TYPE
            SYNTAX      Counter32
            MAX-ACCESS  read-only
            STATUS      current
            DESCRIPTION
                "The PON send broadcast frames."
            ::= { hwEponnniStatisticsEntry 29 }

        hwEponniTx64BytesFrames  OBJECT-TYPE
            SYNTAX      Counter32
            MAX-ACCESS  read-only
            STATUS      current
            DESCRIPTION
                "The PON send frames of 64 bytes."
            ::= { hwEponnniStatisticsEntry 30 }

        hwEponniTx65to127BytesFrames  OBJECT-TYPE
            SYNTAX      Counter32
            MAX-ACCESS  read-only
            STATUS      current
            DESCRIPTION
                "The PON send frames of 65~127 bytes."
            ::= { hwEponnniStatisticsEntry 31 }

        hwEponniTx128to255BytesFrames  OBJECT-TYPE
            SYNTAX      Counter32
            MAX-ACCESS  read-only
            STATUS      current
            DESCRIPTION
                "The PON send frames of 128~255 bytes."
            ::= { hwEponnniStatisticsEntry 32 }

        hwEponniTx256to511BytesFrames  OBJECT-TYPE
            SYNTAX      Counter32
            MAX-ACCESS  read-only
            STATUS      current
            DESCRIPTION
                "The PON send frames of 256~511 bytes."
            ::= { hwEponnniStatisticsEntry 33 }

        hwEponniTx512to1023BytesFrames  OBJECT-TYPE
            SYNTAX      Counter32
            MAX-ACCESS  read-only
            STATUS      current
            DESCRIPTION
                "The PON send frames of 512~1023 bytes."
            ::= { hwEponnniStatisticsEntry 34 }

        hwEponniTx1024to1518BytesFrames  OBJECT-TYPE
            SYNTAX      Counter32
            MAX-ACCESS  read-only
            STATUS      current
            DESCRIPTION
                "The PON send frames of 1024~1518 bytes."
            ::= { hwEponnniStatisticsEntry 35 }

        hwEponniTxOver1518BytesFrames  OBJECT-TYPE
            SYNTAX      Counter32
            MAX-ACCESS  read-only
            STATUS      current
            DESCRIPTION
                "The PON send frames of over 1518 bytes."
            ::= { hwEponnniStatisticsEntry 36 }

        hwEponnniPonRxErrFramesCnt  OBJECT-TYPE
            SYNTAX      Counter32
            MAX-ACCESS  read-only
            STATUS      current
            DESCRIPTION
                "The PON received error frames."
            ::= { hwEponnniStatisticsEntry 37 }

        --        hwEponNniHistoryStats               
        hwEponNniHistoryStatsTable  OBJECT-TYPE
            SYNTAX      SEQUENCE  OF  HwEponNniHistoryStatsEntry
            MAX-ACCESS  not-accessible
            STATUS      current
            DESCRIPTION
                "This table provides the performance statistics of the EPON port:
                 current 24-hour performance statistics, history 30 24-hour performance statistics,
                 current 15-minute performance statistics, and history 96 15-minute performance statistics.
                 The indexes of this table are ifIndex, hwEponStatsIntervalType, hwEponStatsIntervalNum.
                "
            ::= { hwEponNniHistoryStats 1 }

        hwEponNniHistoryStatsEntry  OBJECT-TYPE
            SYNTAX      HwEponNniHistoryStatsEntry
            MAX-ACCESS  not-accessible
            STATUS      current
            DESCRIPTION
                "This table provides the performance statistics of the EPON port:
                 current 24-hour performance statistics, history 30 24-hour performance statistics,
                 current 15-minute performance statistics, and history 96 15-minute performance statistics.
                 The indexes of this entry are ifIndex, hwEponStatsIntervalType, hwEponStatsIntervalNum.
                "
            INDEX { ifIndex, hwEponStatsIntervalType, hwEponStatsIntervalNum }
            ::= { hwEponNniHistoryStatsTable 1 }

        HwEponNniHistoryStatsEntry  ::=
            SEQUENCE {
                hwEponStatsIntervalType         INTEGER,
                hwEponStatsIntervalNum          Integer32,
                hwEponStatsRxMPCP               Counter64,
                hwEponStatsRxOAMPDU             Counter64,
                hwEponStatsRxOctets             Counter64,
                hwEponStatsRxPkts               Counter64,
                hwEponStatsTxOctets             Counter64,
                hwEponStatsTxPkts               Counter64,
                hwTimeElapsed                   Integer32,
                hwValidInterval                 TruthValue
            }

        hwEponStatsIntervalType OBJECT-TYPE
            SYNTAX INTEGER {
                intervaltime15min(0),
                intervaltime24h(1),
                everbefore(2)
            }
            MAX-ACCESS not-accessible
            STATUS     current
            DESCRIPTION
                "Describes the type of EponNni History Statistic,
                 Options:
                 1. intervaltime15min(0) - The EponNNI History Statistic in 15 minutes
                 2. intervaltime24h(1)   - The EponNNI History Statistic in 24 hours
                 3. everbefore(2)        - All the EponNNI History Statistic
                "
            ::= { hwEponNniHistoryStatsEntry 1 }

        hwEponStatsIntervalNum OBJECT-TYPE
            SYNTAX     Integer32 (0..96)
            MAX-ACCESS not-accessible
            STATUS     current
            DESCRIPTION
                "The interval number of EponNni History Statistic.
                 When IntervalType is 15 minutes, IntervalNum is 0 - 96.
                 When IntervalType is 24 hours, IntervalNum is 0 - 30.
                 0 indicates the statistics in the current interval.
                 The greater the value, the longer the duration.
                 When hwEponStatsIntervalType is everbefore(3), this leaf object is skipped.
                "
            ::= { hwEponNniHistoryStatsEntry 2 }

        hwEponStatsRxMPCP OBJECT-TYPE
            SYNTAX     Counter64
            MAX-ACCESS read-only
            STATUS     current
            DESCRIPTION
                "Number of received MPCP frames."
            ::= { hwEponNniHistoryStatsEntry 3 }

        hwEponStatsRxOAMPDU OBJECT-TYPE
            SYNTAX     Counter64
            MAX-ACCESS read-only
            STATUS     current
            DESCRIPTION
                "Number of received OAMPDU frames."
            ::= { hwEponNniHistoryStatsEntry 4 }

        hwEponStatsRxOctets OBJECT-TYPE
            SYNTAX     Counter64
            MAX-ACCESS read-only
            STATUS     current
            DESCRIPTION
                "Total number of received octets."
            ::= { hwEponNniHistoryStatsEntry 5 }

        hwEponStatsRxPkts OBJECT-TYPE
            SYNTAX     Counter64
            MAX-ACCESS read-only
            STATUS     current
            DESCRIPTION
                "Total number of received frames."
            ::= { hwEponNniHistoryStatsEntry 6 }

        hwEponStatsTxOctets OBJECT-TYPE
            SYNTAX     Counter64
            MAX-ACCESS read-only
            STATUS     current
            DESCRIPTION
                "Total number of transmited octets."
            ::= { hwEponNniHistoryStatsEntry 7 }

        hwEponStatsTxPkts OBJECT-TYPE
            SYNTAX     Counter64
            MAX-ACCESS read-only
            STATUS     current
            DESCRIPTION
                "Total number of transmited frames."
            ::= { hwEponNniHistoryStatsEntry 8 }

        hwTimeElapsed OBJECT-TYPE
            SYNTAX Integer32
            MAX-ACCESS read-only
            STATUS     current
            DESCRIPTION
                "Indicates the data statistic seconds in this period.
                 This leaf object is valid when IntervalNum is 0 (namely, the current
                 15 minutes and the current 24 hours).
                "
            ::= { hwEponNniHistoryStatsEntry 9 }

        hwValidInterval OBJECT-TYPE
            SYNTAX TruthValue
            MAX-ACCESS read-only
            STATUS     current
            DESCRIPTION
                "Whether the interval number is valid."
            ::= { hwEponNniHistoryStatsEntry 10 }

        --      hwEponnniAlarmThreshold                   
        hwEponnniAlarmThresholdTable  OBJECT-TYPE
            SYNTAX      SEQUENCE  OF  HwEponnniAlarmThresholdEntry
            MAX-ACCESS  not-accessible
            STATUS      current
            DESCRIPTION
                "The table EponNni optical module alarm threshold.This table is used to set
                 and query the low alarm threshold, the high alarm threshold of eponnni.
                 The index of this table is ifIndex.
                "
            ::= { hwEponnniAlarmThreshold 1 }

        hwEponnniAlarmThresholdEntry  OBJECT-TYPE
            SYNTAX      HwEponnniAlarmThresholdEntry
            MAX-ACCESS  not-accessible
            STATUS      current
            DESCRIPTION
                "The table EponNni optical module alarm threshold. This table is used to set
                 and query the low alarm threshold, the high alarm threshold of eponnni.
                 The index of this entry is ifIndex.
                "
            INDEX  { ifIndex }
            ::= { hwEponnniAlarmThresholdTable 1 }

        HwEponnniAlarmThresholdEntry  ::=
            SEQUENCE {
                hwEponnniRxPowerUpperThreshold          Integer32,
                hwEponnniRxPowerLowerThreshold          Integer32,
                hwEponnniTxPowerUpperThreshold          Integer32,
                hwEponnniTxPowerLowerThreshold          Integer32,
                hwEponnniBiasUpperThreshold             Integer32,
                hwEponnniBiasLowerThreshold             Integer32,
                hwEponnniTemperatureUpperThreshold      Integer32,
                hwEponnniTemperatureLowerThreshold      Integer32,
                hwEponnniVoltageUpperThreshold          Integer32,
                hwEponnniVoltageLowerThreshold          Integer32,
                hwEponnniClearThreshold                 INTEGER   
            }

        hwEponnniRxPowerUpperThreshold  OBJECT-TYPE
            SYNTAX      Integer32
            MAX-ACCESS  read-write
            STATUS      current
            DESCRIPTION
                "The MDU Rx-power upper limit threshold. It ranges from -9900 to 10000 units of 1/100 dBm."
            ::= { hwEponnniAlarmThresholdEntry 1 }

        hwEponnniRxPowerLowerThreshold  OBJECT-TYPE
            SYNTAX      Integer32
            MAX-ACCESS  read-write
            STATUS      current
            DESCRIPTION
                "The MDU Rx-power lower limit threshold. It ranges from -9900 to 10000 units of 1/100 dBm."
            ::= { hwEponnniAlarmThresholdEntry 2 }

        hwEponnniTxPowerUpperThreshold  OBJECT-TYPE
            SYNTAX      Integer32
            MAX-ACCESS  read-write
            STATUS      current
            DESCRIPTION
                "The MDU Tx-power upper limit threshold. It ranges from -9900 to 10000 units of 1/100 dBm."
            ::= { hwEponnniAlarmThresholdEntry 3 }

        hwEponnniTxPowerLowerThreshold  OBJECT-TYPE
            SYNTAX      Integer32
            MAX-ACCESS  read-write
            STATUS      current
            DESCRIPTION
                "The MDU Tx-power lower limit threshold. It ranges from -9900 to 10000 units of 1/100 dBm."
            ::= { hwEponnniAlarmThresholdEntry 4 }

        hwEponnniBiasUpperThreshold  OBJECT-TYPE
            SYNTAX      Integer32
            MAX-ACCESS  read-write
            STATUS      current
            DESCRIPTION
                "The MDU Bias upper limit threshold. It ranges from 0 to 10000 units of mA."
            ::= { hwEponnniAlarmThresholdEntry 5 }

        hwEponnniBiasLowerThreshold  OBJECT-TYPE
            SYNTAX      Integer32
            MAX-ACCESS  read-write
            STATUS      current
            DESCRIPTION
                "The MDU Bias lower limit threshold. It ranges from 0 to 10000 units of mA."
            ::= { hwEponnniAlarmThresholdEntry 6 }

        hwEponnniTemperatureUpperThreshold  OBJECT-TYPE
            SYNTAX      Integer32
            MAX-ACCESS  read-write
            STATUS      current
            DESCRIPTION
                "The MDU Temperature upper limit threshold. It ranges from -9900 to 30000 units of 1/100 C."
            ::= { hwEponnniAlarmThresholdEntry 7 }

        hwEponnniTemperatureLowerThreshold  OBJECT-TYPE
            SYNTAX      Integer32
            MAX-ACCESS  read-write
            STATUS      current
            DESCRIPTION
                "The MDU Temperature lower limit threshold. It ranges from -9900 to 30000 units of 1/100 C."
            ::= { hwEponnniAlarmThresholdEntry 8 }

        hwEponnniVoltageUpperThreshold  OBJECT-TYPE
            SYNTAX      Integer32
            MAX-ACCESS  read-write
            STATUS      current
            DESCRIPTION
                "The MDU Voltage upper limit threshold. It ranges from 0 to 10000 units of 1/100 V."
            ::= { hwEponnniAlarmThresholdEntry 9 }

        hwEponnniVoltageLowerThreshold  OBJECT-TYPE
            SYNTAX      Integer32
            MAX-ACCESS  read-write
            STATUS      current
            DESCRIPTION
                "The MDU Voltage lower limit threshold. It ranges from 0 to 10000 units of 1/100 V."
            ::= { hwEponnniAlarmThresholdEntry 10 }
                
        hwEponnniClearThreshold  OBJECT-TYPE
           SYNTAX      INTEGER {
                invalid(0),
                clear(1),
                cleared(32767)
            }
            MAX-ACCESS  read-write
            STATUS      current
            DESCRIPTION
                "Clear the MDU threshold.
                 Options:
                 1. invalid(0)     - The MDU threshold clear state is invalid.
                 2. clear(1)       - Clear the MDU threshold.
                 3. cleared(32767) - The MDU threshold is cleared.
                "
            ::= { hwEponnniAlarmThresholdEntry 11 }  
                            
--      hwEponnniTrapsVbOids  OBJECT IDENTIFIER ::= { hwEponMIB 2 }

        hwEponNNITrapSerialNo OBJECT-TYPE
            SYNTAX       Integer32
            MAX-ACCESS   accessible-for-notify
            STATUS       current
            DESCRIPTION
                "Serial No. of EponNNI trap."
            ::= { hwEponnniTrapsVbOids 1 }

        hwEponNNITrapOperType OBJECT-TYPE
            SYNTAX       Integer32
            MAX-ACCESS   accessible-for-notify
            STATUS       current
            DESCRIPTION
                "Operation type of EponNNI trap."
            ::= { hwEponnniTrapsVbOids 2 }

--      hwEponnniCommonTraps  OBJECT IDENTIFIER ::= { hwEponMIB 3 }

        hwEponnniTypeDPortSwitchTrap NOTIFICATION-TYPE
            OBJECTS {
                hwConfigChangeIP,
                ifIndex,
                ifIndex
            }
            STATUS current
            DESCRIPTION
                "TypeD port switch trap.
                 The first ifIndex is the active one after switching over.
                 The second ifIndex is the standby one after switching over.
                 The hwEponnniTypeDPortSwitchTrap will be sent when typeD port switch.
                "
            ::= { hwEponnniCommonTraps 0 1 }

        hwEponnniAuthChangeTrap NOTIFICATION-TYPE
            OBJECTS {
                hwConfigChangeIP,
                hwEponNNITrapOperType,
                ifIndex,
                hwEponnniPassword,
                hwEponNniKeyLoid,
                hwEponNniKeyCheckCode
            }
            STATUS current
            DESCRIPTION
                "The hwEponnniAuthChangeTrap will be sent when the authentication information changes.
                "
            ::= { hwEponnniCommonTraps 0 2 }


 --      hwEponnniAlarmTraps

        hwEponnniOntRogueOntFailAlarmTrap NOTIFICATION-TYPE
            OBJECTS {
                hwFrameIndex,
                hwSlotIndex,
                hwPortIndex
            }
            STATUS current
            DESCRIPTION
                "Rogue ONT fail trap.
                 EPON ONU was identified as rogue ONU, because it gave out light in the incorrect time.
                 The notification indicates alarm when optical module has been turn off for service of ONU failed.
                "
            ::= { hwEponnniAlarmTraps 0 1 }

        hwEponnniOntRogueOntRestoreAlarmTrap NOTIFICATION-TYPE
            OBJECTS {
                hwFrameIndex,
                hwSlotIndex,
                hwPortIndex
            }
            STATUS current
            DESCRIPTION
                "EPON ONU's optical module send laser recovery trap.
                 The notification indicates alarm when EPON ONU's optical module sent laser recovery.
                "
            ::= { hwEponnniAlarmTraps 0 2 }

        hwEponnniTempeExceedThreAlarmTrap NOTIFICATION-TYPE
            OBJECTS {
                hwFrameIndex,
                hwSlotIndex,
                hwPortIndex,
                hwEponnniTemperatureLowerThreshold,
                hwEponnniTemperatureUpperThreshold,
                hwEponnniTemperature
            }
            STATUS current
            DESCRIPTION
                "The temperature of EPON optical module exceeded threshold trap.
                 The notification indicates alarm when the temperature of EPON optical module
                 exceeded alarm threshold.
                "
            ::= { hwEponnniAlarmTraps 0 3 }

        hwEponnniTempeExceedThreRestoreAlarmTrap NOTIFICATION-TYPE
            OBJECTS {
                hwFrameIndex,
                hwSlotIndex,
                hwPortIndex,
                hwEponnniTemperatureLowerThreshold,
                hwEponnniTemperatureUpperThreshold,
                hwEponnniTemperature
            }
            STATUS current
            DESCRIPTION
                "The temperature of EPON optical module exceeded threshold recovery trap.
                 The notification indicates alarm when the temperature of EPON optical module
                 exceeded alarm threshold recovery.
                "
            ::= { hwEponnniAlarmTraps 0 4 }

        hwEponnniVoltExceedThreAlarmTrap NOTIFICATION-TYPE
            OBJECTS {
                hwFrameIndex,
                hwSlotIndex,
                hwPortIndex,
                hwEponnniVoltageLowerThreshold,
                hwEponnniVoltageUpperThreshold,
                hwEponnniVoltage
            }
            STATUS current
            DESCRIPTION
                "The voltage of EPON ONU's optical-module exceeded alarm threshold trap.
                 The notification indicates alarm when voltage of EPON ONU's optical-module
                 exceeded alarm threshold.
                "
            ::= { hwEponnniAlarmTraps 0 5 }

        hwEponnniVoltExceedThreRestoreAlarmTrap NOTIFICATION-TYPE
            OBJECTS {
                hwFrameIndex,
                hwSlotIndex,
                hwPortIndex,
                hwEponnniVoltageLowerThreshold,
                hwEponnniVoltageUpperThreshold,
                hwEponnniVoltage
            }
            STATUS current
            DESCRIPTION
                "The voltage of EPON ONU's optical-module exceeded alarm threshold recovery trap.
                 The notification indicates alarm when voltage of EPON ONU's optical-module exceeded
                 alarm threshold recovery.
                "
            ::= { hwEponnniAlarmTraps 0 6 }

        hwEponnniBiasExceedThreAlarmTrap NOTIFICATION-TYPE
            OBJECTS {
                hwFrameIndex,
                hwSlotIndex,
                hwPortIndex,
                hwEponnniBiasLowerThreshold,
                hwEponnniBiasUpperThreshold,
                hwEponnniBiasCurrent
            }
            STATUS current
            DESCRIPTION
                "The bias of EPON ONU's optical module exceeded alarm threshold trap.
                 The notification indicates alarm when the bias of EPON ONU's optical module
                 exceeded alarm threshold.
                "
            ::= { hwEponnniAlarmTraps 0 7 }

        hwEponnniBiasExceedThreRestoreAlarmTrap NOTIFICATION-TYPE
            OBJECTS {
                hwFrameIndex,
                hwSlotIndex,
                hwPortIndex,
                hwEponnniBiasLowerThreshold,
                hwEponnniBiasUpperThreshold,
                hwEponnniBiasCurrent
            }
            STATUS current
            DESCRIPTION
                "The bias of EPON ONU's optical module exceeded alarm threshold recovery trap.
                 The notification indicates alarm when the bias of EPON ONU's optical module exceeded
                 alarm threshold recovery.
                "
            ::= { hwEponnniAlarmTraps 0 8 }

        hwEponnniTxPowerExceedThreAlarmTrap NOTIFICATION-TYPE
            OBJECTS {
                hwFrameIndex,
                hwSlotIndex,
                hwPortIndex,
                hwEponnniTxPowerLowerThreshold,
                hwEponnniTxPowerUpperThreshold,
                hwEponnniTxPower
            }
            STATUS current
            DESCRIPTION
                "The tx-power of EPON ONU's optical module exceeded alarm threshold trap.
                 The notification indicates alarm when the Tx Power of EPON ONU's optical module
                 exceeded alarm threshold.
                "
            ::= { hwEponnniAlarmTraps 0 9 }

        hwEponnniTxPowerExceedThreRestoreRestoreAlarmTrap NOTIFICATION-TYPE
            OBJECTS {
                hwFrameIndex,
                hwSlotIndex,
                hwPortIndex,
                hwEponnniTxPowerLowerThreshold,
                hwEponnniTxPowerUpperThreshold,
                hwEponnniTxPower
            }
            STATUS current
            DESCRIPTION
                "The tx-power of EPON ONU's optical module exceeded alarm threshold recovery trap.
                 The notification indicates alarm when the tx-power of EPON ONU's optical module exceeded
                 alarm threshold recovery.
                "
            ::= { hwEponnniAlarmTraps 0 10 }

        hwEponnniRxPowerExceedThreAlarmTrap NOTIFICATION-TYPE
            OBJECTS {
                hwFrameIndex,
                hwSlotIndex,
                hwPortIndex,
                hwEponnniRxPowerLowerThreshold,
                hwEponnniRxPowerUpperThreshold,
                hwEponnniRxPower
            }
            STATUS current
            DESCRIPTION
                "The rx-power of EPON ONU's optical-module exceeded alarm threshold trap.
                 The notification indicates alarm when the rx-power of EPON ONU's optical-module
                 exceeded alarm threshold.
                "
            ::= { hwEponnniAlarmTraps 0 11 }

        hwEponnniRxPowerExceedThreRestoreAlarmTrap NOTIFICATION-TYPE
            OBJECTS {
                hwFrameIndex,
                hwSlotIndex,
                hwPortIndex,
                hwEponnniRxPowerLowerThreshold,
                hwEponnniRxPowerUpperThreshold,
                hwEponnniRxPower
            }
            STATUS current
            DESCRIPTION
                "The rx-power of EPON ONU's optical-module exceeded alarm threshold recovery trap.
                 The notification indicates alarm when the rx-power of EPON ONU's optical-module exceeded
                 alarm threshold recovery.
                "
            ::= { hwEponnniAlarmTraps 0 12 }

        hwEponnniPortSwitchAlarmTrap NOTIFICATION-TYPE
            OBJECTS {
                hwFrameIndex,
                hwSlotIndex,
                hwPortIndex,
                hwPortIndex
            }
            STATUS current
            DESCRIPTION
                "Port switch trap.
                 The notification indicates alarm when the protection switchover occurs on the PON port
                 and it has no effect on the service.
                "
            ::= { hwEponnniAlarmTraps 0 13 }
        END
