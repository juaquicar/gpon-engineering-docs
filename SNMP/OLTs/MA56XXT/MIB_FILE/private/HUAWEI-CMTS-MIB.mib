-- ================================================================= 
-- Copyright (C) 2016 by HUAWEI TECHNOLOGIES. All rights reserved    
-- Description:  The mib is used for defining huawei's CMTS           
--               management in distributing mode MIB objects.                                     
-- Reference: 
-- Version: V2.37
-- ================================================================


       HUAWEI-CMTS-MIB DEFINITIONS ::= BEGIN
       IMPORTS
           MODULE-IDENTITY, mib-2, OBJECT-TYPE, Counter32, Counter64,
           Unsigned32, Integer32, Gauge32, NOTIFICATION-TYPE, IpAddress
               FROM SNMPv2-SMI
           TruthValue, DateAndTime, RowStatus, MacAddress,TEXTUAL-CONVENTION, DisplayString
               FROM SNMPv2-TC
           ifIndex, InterfaceIndex, InterfaceIndexOrZero, ifAdminStatus, ifOperStatus
               FROM IF-MIB 
           docsIfCmtsModIndex, docsIfCmtsModIntervalUsageCode, DocsEqualizerData
               FROM DOCS-IF-MIB
           AttributeMask, docsIf3CmtsCmRegStatusId, docsIf3CmtsCmUsStatusChIfIndex, docsIf3CmMdCfgIpProvMode, docsIf3BondingGrpCfgDir, docsIf3BondingGrpCfgCfgId
               FROM DOCS-IF3-MIB
           docsLoadbal3GeneralGrpCfgNodeName,docsLoadbal3RestrictCmCfgId,docsLoadbal3ResGrpCfgId
               FROM DOCS-LOADBAL3-MIB
           MODULE-COMPLIANCE, OBJECT-GROUP
               FROM SNMPv2-CONF
           SnmpAdminString
               FROM SNMP-FRAMEWORK-MIB
           OwnerString, EntryStatus
               FROM RMON-MIB
           huaweiUtility
               FROM HUAWEI-MIB
           hwFrameIndex, hwSlotIndex, hwPortIndex, hwConfigChangeIP
               FROM HUAWEI-DEVICE-MIB
           docsIfDownChannelId, docsIfUpChannelId, TenthdB
               FROM DOCS-IF-MIB
           InetAddressType,InetAddress,InetAddressPrefixLength,InetPortNumber,InetAddressIPv6
               FROM INET-ADDRESS-MIB
           docsQosServiceFlowId,docsQosSID,docsQosParamSetServiceFlowId,docsQosParamSetBitMap
               FROM DOCS-QOS3-MIB
           DocsL2vpnIdentifier,docsL2vpnIdx
               FROM DOCS-L2VPN-MIB
           docsIfCmtsCmStatusIndex 
               FROM DOCS-IF-MIB
           SubcarrierSpacingType
               FROM DOCS-IF31-MIB
           MeasStatusType
               FROM DOCS-PNM-MIB;
                 
   hwCmtsMIB MODULE-IDENTITY
            LAST-UPDATED "201607050000Z"
            ORGANIZATION "Huawei Technologies Co.,Ltd."
            CONTACT-INFO                                 
                   "Huawei Industrial Base         
                    Bantian, Longgang              
                    Shenzhen 518129                
                    People's Republic of China     
                    Website: http://www.huawei.com 
                    Email: support@huawei.com      
                   " 
            DESCRIPTION
                "The mib is used for defining huawei's CMTS management in distributing mode MIB objects.
                "
--  Revision history
       REVISION     "201607050000Z"
       DESCRIPTION  "V2.37, Modified the range of hwCmtsRfPowerDsGroupConfigGroupId, hwCmtsRfPowerDsMonitorStatusGroupId, hwCmtsRfPowerDsMonitorTempGroupId and hwCmtsEqamChannelSymbolRate.
                            Added the table hwCmtsRfPowerDsAmpGroupTable.
                            Added the table hwCmtsDownstreamSweepTable."
                            
       REVISION     "201607010000Z"
       DESCRIPTION  "V2.36, Modified the description of leaf hwCmtsCmCurr15MCrc, hwCmtsCmCurr1DayCrc, hwCmtsCmCurrEverBeforeCrc, hwCmtsCmHist15MCrc and hwCmtsCmHist1DayCrc ."

       REVISION     "201606290000Z"
       DESCRIPTION  "V2.35, Modified the range of hwDocsIf3CmtsCmRegStatusDsPartialChannelMask, hwDocsIf3CmtsCmDownChannelInfoChannelId, hwCmtsEqamChannelId, hwCmtsCapabilityEqamChannelNum."

       REVISION     "201606240000Z"
       DESCRIPTION  "V2.34, Modified the range of hwCmtsCapabilityDownstreamChannelNum."
       
       REVISION     "201606080000Z"
       DESCRIPTION  "V2.33, Modified the description of leaf hwCmtsUpChannelNotActiveReason, hwCmtsEqamChannelNotActiveReason and hwCmtsDownChannelNotActiveReason.
                Added the table hwDocsPnmCmtsUsFecStatisticTable.
                Added the leaf hwCmtsUsHistorySpectrumUploadTime in table hwCmtsUsHistorySpectrumCfgTable.
                Added the leaf hwCmtsUsCmcPerformanceUploadTime  in table hwCmtsUsCmcPerformanceCfgTable."
       
       REVISION     "201606060000Z"
       DESCRIPTION  "V2.32, Modified the description of leaf hwCmtsUpChannel20CmDataRateSum, hwCmtsUpChannel30CmDataRateSum, hwCmtsUpChannel31CmDataRateSum,
                    hwCmtsDownChannel20CmDataRateSum, hwCmtsDownChannel30CmDataRateSum and hwCmtsDownChannel31CmDataRateSum."
                
       REVISION     "201606020000Z"
       DESCRIPTION  "V2.31, Added the leaf hwDocsIf3SidClusterNumber, hwDocsIf3SidClusterMaxRequest, hwDocsIf3SidClusterMaxTime, 
              hwDocsIf3SidClusterMaxTotalByte, hwDocsIf3SidClusterMaxOutstandingByte and hwDocsIf3PeriodicRngInterval in hwDocsIf3MdCfgTable.
                Added the table hwCmtsEqamChannelTable, hwCmtsEqamChannelUtilizationTable and hwCmtsEqamChannelStatisticsTable.
                Modified the range of hwCmtsDownChannelNotActiveReason and hwDocsIf3MdCfgOperation.
                Added the leaf hwCmtsCapabilityEqamChannelNum in hwCmtsCapabilityConfigTable.
                Added the leaf hwCmtsEqamChannelStatusChangeTrap, hwCmtsEqamAbnormalStateAlarmTrap and hwCmtsEqamNormalStateAlarmTrap in hwcmtsTrapsVbOids." 

       REVISION     "201605300000Z"
       DESCRIPTION  "V2.30, Added the leaf hwCmtsCmDataChangeCmcIfindexList in hwCmtsCmDataChangeTrap." 

       REVISION     "201605270000Z"
       DESCRIPTION  "V2.29, Modified the leaf hwCmtsEQAMChannelUtilizationAlarmTrap in hwdocsIfCmtsTraps."    

       REVISION     "201605240000Z"
       DESCRIPTION  "V2.28, Added the leaf hwdocsIfUpstreamChannelUcdType in hwdocsIfUpstreamChannelTable."       

       REVISION     "201605230000Z"
       DESCRIPTION  "V2.27, Modified the description of leaf hwCmtsUsSpectrumMonitorUsChannelId."

       REVISION     "201605060000Z"
       DESCRIPTION  "V2.26, Modified the description of leaf hwCmtsRfPowerDsMonitorFreqType and hwCmtsRfPowerDsMonitorFreqFunction."       
       
       REVISION     "201604250000Z"
       DESCRIPTION  "V2.25, Added the leaf hwCmtsUsSpectrumMonitorReportPeriod in hwCmtsUsSpectrumMonitorCfgTable, 
                            Added the table hwCmtsUsCalibrationCfgTable and hwCmtsUsSpectrumUdpCfgTable."

       REVISION     "201604140000Z"
       DESCRIPTION  "V2.24, Added the leaf hwCmtsCmCurr15MCrc, hwCmtsCmCurr1DayCrc,hwCmtsCmCurrEverBeforeCrc, 
                            hwCmtsCmHist15MCrc,hwCmtsCmHist1DayCrc, hwDocsIf31CmtsUsOfdmaChanMaxDataRate, hwDocsIf31CmtsDsOfdmChanMaxDataRate."

       REVISION     "201604120000Z"
       DESCRIPTION  "V2.23, Added the leaf hwCmtsCapabilityRealD31UpstreamMaxFrequency and hwCmtsCapabilityRealD31DownstreamMaxFrequency in hwCmtsCapabilityStatusTable."
 
       REVISION     "201603260000Z"
       DESCRIPTION  "V2.22, Added the table hwDocsPnmBulkCtlTable."

       REVISION     "201603240000Z"
       DESCRIPTION  "V2.21, Remove the empty lines of hwCmtsRfPowerDsMonitorConfigTable Description."
     
       REVISION     "201603230000Z"
       DESCRIPTION  "V2.20, Modified the range of hwCmtsRfPowerDsGroupConfigMaxFreq."

       REVISION     "201603220000Z"
       DESCRIPTION  "V2.19, Modified the form of description."        


       REVISION    "201603160000Z"
       DESCRIPTION "V2.18, Added the leaf hwCmtsCablePerformanceCurr15MElapsedTime, hwCmtsCablePerformanceCurr15MValidityFlag,
                    hwCmtsCablePerformanceCurr15MSuccessPeriodRng, hwCmtsCablePerformanceCurr15MPeriodRngLoss,
                    hwCmtsCablePerformanceCurr15MSeriousPeriodRngLoss, hwCmtsCablePerformanceCurr15MPowerAdjust,
                    hwCmtsCablePerformanceCurr15MSeriousPowerAdjust, hwCmtsCablePerformanceCurr1DayElapsedTime,
                    hwCmtsCablePerformanceCurr1DayValidityFlag, hwCmtsCablePerformanceCurr1DaySuccessPeriodRng,
                    hwCmtsCablePerformanceCurr1DayPeriodRngLoss, hwCmtsCablePerformanceCurr1DaySeriousPeriodRngLoss,
                    hwCmtsCablePerformanceCurr1DayPowerAdjust, hwCmtsCablePerformanceCurr1DaySeriousPowerAdjust,
                    hwCmtsCablePerformanceEverBeforeElapsedTime, hwCmtsCablePerformanceEverBeforeValidityFlag,
                    hwCmtsCablePerformanceEverBeforeSuccessPeriodRng, hwCmtsCablePerformanceEverBeforePeriodRngLoss,
                    hwCmtsCablePerformanceEverBeforeSeriousPeriodRngLoss, hwCmtsCablePerformanceEverBeforePowerAdjust,
                    hwCmtsCablePerformanceEverBeforeSeriousPowerAdjust in table hwCmtsCablePerformanceCurrTable.
                    Modified the name of hwCmtsCablePerformanceEverbeforeStartTime to hwCmtsCablePerformanceEverBeforeStartTime.
                    Modified the name of hwCmtsCablePerformanceEverbeforeSuccessReg to hwCmtsCablePerformanceEverBeforeSuccessReg.
                    Modified the name of hwCmtsCablePerformanceEverbeforeFailReg to hwCmtsCablePerformanceEverBeforeFailReg.
                    Modified the name of hwCmtsCablePerformanceEverbeforeRepeatReg to hwCmtsCablePerformanceEverBeforeRepeatReg.
                    Added the table hwDocsCmtsOssAdaptSwitchTable.
                    Added hwCmtsRfPowerDsGroupMinAtt in hwCmtsRfPowerDsGroupTable.
                    Added hwCmtsRfPowerDsMinCatvAtt in hwCmtsRfPowerTable.
                    Added hwCmtsRfPowerDsMinDocsisAtt in hwCmtsRfPowerTable.
                    Added hwCmtsRfPowerCatvCwAndDocScqamDiff in hwCmtsRfPowerTable.
                    Added hwCmtsRfPowerDsMonitorFreqFunction in hwCmtsRfPowerDsMonitorConfigTable.
                    Modified the enumaration of hwCmtsRfPowerDsGroupConfigMaxFreqType, hwCmtsRfPowerDsMonitorStatusFreqType, hwCmtsRfPowerDsMonitorTempFreqType and hwCmtsRfPowerDsMonitorFreqType.
                    Modified the range of hwCmtsRfPowerDsGroupConfigMaxFreq."
 
       REVISION     "201603030000Z"
       DESCRIPTION  "V2.17, Modified the description of leaf hwDocsIf3CmtsCmDepartureReasonCode."         
   
       REVISION     "201602290000Z"
       DESCRIPTION  "V2.16, Modify the description of leaf hwDocsIf3MdCfgOperation."

       REVISION     "201602250000Z"
       DESCRIPTION  "V2.15, Modify the description of leaf hwDocsIfRFOutUsAdminStatus and hwDocsIfRFOutUsOperStatus.
                     Disuse the leaf hwDocsIfRFOutCfgAttenuationValue and hwDocsIfRFOutOperAttenuationValue."
       
       REVISION     "201602240000Z"
       DESCRIPTION  "V2.14, Delete the description of INTEGER."

       REVISION     "201602200000Z"
       DESCRIPTION  "V2.13, Modify the description of leaf hwCmtsDownChannelOperation in hwCmtsDownChannelTable.
                    Modify the description of leaf hwCmtsCmConnOperation in hwCmtsCmConnectivityTable.
                    Modify the description of hwCmtsCmTrapAlarmConfigEntry.
                    Modify the description of hwCmtsMassOfflineCmPercent, hwCmtsMassUnstableConnCmPercent in hwcmtsTrapsVbOids."         
       
       REVISION     "201602170000Z"
       DESCRIPTION  "V2.12, Modify the description of leaf hwDocsIf3MdCfgOperation and hwDocsIf31CmtsDsOfdmChanEfficiency."     
       
       REVISION     "201602150000Z"
       DESCRIPTION  "V2.11, Modify the UNITS of leaf hwDocsIf31CmtsUsOfdmaChanMinRxMer and hwDocsIf31CmtsUsOfdmaChanMaxRxMer in hwDocsIf31CmtsUsOfdmaChanTable."  

       REVISION     "201602060000Z"
       DESCRIPTION  "V2.10, Modify the description of leaf hwDocsIfDownChannelModulation in hwDocsIfDownstreamChannelTable."  

       REVISION     "201602030000Z"
       DESCRIPTION  "V2.09, Modify the description of leaf hwCmtsDownChannelMaxDataRate,hwCmtsDownChannelRealTimeDataRate,hwCmtsDownChannel20CmDataRateSum,
                    hwCmtsDownChannel30CmDataRateSum,hwCmtsDownChannelSymbolRate,hwCmtsDownChannelNotActiveReason,hwCmtsDownChannel20CmUtilization,hwCmtsDownChannel30CmUtilization,
                    hwCmtsDownChannelRealTimeTxPower,hwCmtsDownChannelConfigTxPower,hwCmtsDownChannelOperation,hwCmtsDownChannel31CmDataRateSum,hwCmtsDownChannel31CmUtilization,
                    hwdocsIfUsChanneSpectrumGroupId,hwDocsIfDownChannelModulation." 

       REVISION     "201602010000Z"
       DESCRIPTION  "V2.08, Modify the description of leaf hwCmtsCmNumSummaryTotalCmNum, hwCmtsCmNumSummaryOnlineCmNum, hwCmtsCmNumSummaryUnOnlineCmNum,
                     hwCmtsCmNumSummaryOfflineCmNum, hwCmtsCmNumSummaryWidebandCmNum, hwCmtsCmNumSummaryRangingCompleteCmNum, hwCmtsCmNumSummaryStartDhcpV4CmNum, 
                     hwCmtsCmNumSummaryDhcpOfferCmNum, hwCmtsCmNumSummaryDhcpv4CompleteCmNum, hwCmtsCmNumSummaryDhcpV4RequestCmNum, hwCmtsCmNumSummaryStartDhcpV6CmNum,
                     hwCmtsCmNumSummaryDhcpv6AdvertiseCmNum, hwCmtsCmNumSummaryDhcpV6RequestCmNum, hwCmtsCmNumSummaryDhcpV6CompleteCmNum, hwCmtsCmNumSummaryStartTftpCmNum,
                     hwCmtsCmNumSummaryTftpCompleteCmNum, hwCmtsCmNumSummaryEaeCmNum in hwCmtsCmNumSummaryTable."
       
       REVISION     "201602010000Z"
       DESCRIPTION  "V2.07, Modify the description of leaf hwDocsLoadbal3RestrictCmCfgMethod in hwDocsLoadbal3RestrictCmCfgTable."

       REVISION     "201601280000Z"
       DESCRIPTION  "V2.06, Modified the descripition of the hwCmtsAuthKey."

       REVISION     "201601260000Z"
       DESCRIPTION  "V2.05, Modified the enumaration of hwCmtsRfPowerDsMonitorTempFreqType.
                     Modified the description of hwCmtsUpChannelContentionFlag, hwCmtsUpChannelSnr, hwCmtsChannelMicroReflection, hwCmtsUpChannelMaxDataRate,
                     hwCmtsUpChannelRealTimeDataRate, hwCmtsUpChannelModulationType, hwCmtsUpChannelNotActiveReason, hwCmtsUpChannelPer,
                     hwCmtsUpChannel20CmUtilization, hwCmtsUpChannel30CmUtilization, hwCmtsUpChannelMinSnr, hwCmtsUpChannelMaxSnr, 
                     hwCmtsUpChannel31CmUtilization, hwCmtsLoadBalanceCMMoveInterval, hwCmtsCablePerformanceCurr15MSuccessReg, 
                     hwCmtsCablePerformanceCurr15MFailReg, hwCmtsCablePerformanceCurr15MRepeatReg, hwCmtsCablePerformanceCurr1DaySuccessReg, 
                     hwCmtsCablePerformanceCurr1DayFailReg, hwCmtsCablePerformanceCurr1DayRepeatReg."

       REVISION     "201601230000Z"
       DESCRIPTION "V2.04, Added the table hwCmtsCablePerformanceCurrTable.
                    Added the leaf hwCmtsCmNumSummaryInitCmNum, hwCmtsCmNumSummaryRejectCmNum in table hwCmtsCmNumSummaryTable.
                    Modified the description of hwCmtsMassUnstableConnCmPercent.
                    Modified the description of hwDocsPnmCmtsUsOfdmaRxMerSubCarrierSpacing."
       
       REVISION     "201601210000Z"
       DESCRIPTION  "V2.03, Modified the description of UNITS in file." 

       REVISION     "201601180000Z"
       DESCRIPTION  "V2.02, Added hwCmtsMassUnstableConnCmPercent in hwcmtsTrapsVbOids.
               Added hwCmtsMassOfflineCmPercent in hwcmtsTrapsVbOids.
               Modified the objects of hwCmtsUnstableConnCmExceedThresholdAlarmTrap.
               Modified the objects of hwCmtsOfflineCmExceedThresholdAlarmTrap.
               Modified the description of hwCmtsUnstableConnCmExceedThresholdAlarmTrap.
               Modified the description of hwCmtsOfflineCmExceedThresholdAlarmTrap"

       REVISION     "201601130000Z"
       DESCRIPTION  "V2.01, Modified the description of hwDocsIf31CmtsUsOfdmaChanTable, hwDocsIf31CmtsDsOfdmChanEfficiency."  

       REVISION     "201601130000Z"
       DESCRIPTION  "V2.00, Modified the description of hwDocsPnmCmtsUsOfdmaRxMerZeroFreq, hwDocsPnmCmtsUsOfdmaRxMerData."
                      
       REVISION     "201601040000Z"
       DESCRIPTION  "V1.99, Added the table hwCmtsCmTrapCtrlTable.
                    Added the table hwCmtsCmTrapAlarmConfigTable.
                    Added the leaf hwCmtsCmOnOfflineTrap,hwCmtsCmAlarmCmFaultTrap,hwCmtsCmAlarmCmRestoreTrap in table  
                    hwdocsIfCmtsCommonTraps.
                    Modified the description of hwCmtsOverCmSpecAlarmTrap.
                    Added hwCmtsOverCmSpec31Num in hwcmtsTrapsVbOids.
                    Added the leaf hwDocsIf31CmtsUsOfdmaChanMdUsSgId,hwDocsIf31CmtsUsOfdmaChanPer and hwDocsIf31CmtsUsOfdmaChanRealTimeDataRate in table hwDocsIf31CmtsUsOfdmaChanTable.
                    Added the leaf hwDocsIf31CmtsDsOfdmChanRealTimeDataRate in table hwDocsIf31CmtsDsOfdmChanTable.
                    Added the leaf hwDocsIf31CmtsCmRegStatusPrimaryUsTimingOffset in table hwDocsIf31CmtsCmRegStatusTable.
                    Added the leaf hwDocsIf31CmtsCmUsOfdmaChannelT3Timeouts and hwDocsIf31CmtsCmUsOfdmaChannelT4Timeouts in table hwDocsIf31CmtsCmUsOfdmaChannelStatusTable.
                    Modified the description of hwCmtsAdmissionCtrlStatisticsChannelId.
                    Modified the description of hwCmtsAdmissionCtrlChannelBandwidthChannelId."

       REVISION     "201512300000Z"
       DESCRIPTION  "V1.98, Modified the description of hwDocsIf3CmtsCmRegStatusCurrentPolicyID, hwDocsIf3CmtsCmRegStatusCurrentServiceTypeID,
                    hwDocsIf3CmtsCmRegStatusCurrentPriority, hwDocsIf3CmtsCmRegStatusPolicyIDinCfgFile, hwDocsIf3CmtsCmRegStatusPolicyIDinCfgFile,
                    hwDocsIf3CmtsCmRegStatusPriorityinCfgFile."
                     
       REVISION     "201512260000Z"
       DESCRIPTION  "V1.97, Modified the SYNTAX of hwDocsIf31CmtsCmUsOfdmaChannelMinMeanRxMer, hwDocsIf31CmtsCmUsOfdmaChannelMaxMeanRxMer.
              Modified the description of hwDocsIf31CmtsCmUsOfdmaChannelMinMeanRxMer, hwDocsIf31CmtsCmUsOfdmaChannelMaxMeanRxMer, 
              hwDocsIf31CmtsUsOfdmaChanMaxRxMer, hwDocsIf31CmtsUsOfdmaChanMinRxMer."

       REVISION     "201512210000Z"
       DESCRIPTION  "V1.96, Modified the description of hwCmtsLoadBalanceDifferenceThresholdD3."
                     
       REVISION     "201512170000Z"
       DESCRIPTION  "V1.95, Modified the enumaration of hwCmtsRfPowerDsGroupConfigMaxFreqType, hwCmtsRfPowerDsMonitorFreqType, hwCmtsRfPowerDsMonitorStatusFreqType,
                    hwCmtsRfPowerDsMonitorTempFreqType.
                    Modified the description of hwCmtsRfPowerDsGroupConfigMaxFreqType, hwCmtsRfPowerDsGroupConfigRFOutPower, hwCmtsRfPowerDsCatvDocsisDiff,
                    hwCmtsRfPowerDsMonitorFreqType, hwCmtsRfPowerDsMonitorStatusFreqType, hwCmtsRfPowerDsMonitorTempFreqType.
                    Modified the range of hwCmtsRfPowerDsGroupConfigRFOutEq, hwCmtsRfPowerDsGroupConfigEq."
                    
       REVISION     "201512080000Z"
       DESCRIPTION  "V1.94, Added the leaf hwCmtsIpReturnUsChannelRxPowerConfig, hwCmtsIpReturnUsChannelRxPowerStatus in table
                    hwCmtsIpReturnUsChannelTable."
 
       REVISION     "201512070000Z"
       DESCRIPTION  "V1.93, Modified the description of hwDocsIf3CmtsCmRegStatusPrimaryDs, hwDocsIf3CmtsCmRegStatusPrimaryUs.
                     Modified the description of hwCmtsCmOverCapaReasonList in table hwCmtsCmOverCapaTable.
                     Modified the description of hwDocsIf31CmtsUsOfdmaChanTable, hwDocsIf31CmtsDsOfdmChanTable."

       REVISION     "201512040000Z"
       DESCRIPTION  "V1.92, Modified the description of hwDocsIf31CmtsCmDsOfdmChannelTxPower, hwDocsIf31CmtsCmDsOfdmChannelRxPower, 
              hwDocsIf31CmtsCmDsOfdmChannelMinRxPower, hwDocsIf31CmtsCmDsOfdmChannelMaxRxPower, hwDocsIf31CmtsCmUsOfdmaChannelMinMeanRxMer, 
              hwDocsIf31CmtsCmUsOfdmaChannelMaxMeanRxMer, hwDocsIf31CmtsCmDsOfdmChannelMeanRxMER, hwDocsIf31CmtsCmDsOfdmChannelMinMeanRxMER, 
              hwDocsIf31CmtsCmDsOfdmChannelMaxMeanRxMER, hwDocsIf31CmtsUsOfdmaChanMinRxMer, hwDocsIf31CmtsUsOfdmaChanMaxRxMer, 
              hwDocsIf31CmtsDsOfdmChanTxPower, hwDocsIf31CmtsCmUsOfdmaChannelTxPower, hwDocsIf31CmtsCmUsOfdmaChannelMinTxPower, 
              hwDocsIf31CmtsCmUsOfdmaChannelMaxTxPower."

       REVISION     "201512010000Z"
       DESCRIPTION  "V1.91, Modified the leaf hwCmtsCmOverCapaReasonList in table hwCmtsCmOverCapaTable."

       REVISION     "201511300000Z"
       DESCRIPTION  "V1.90, Modified the leaf hwDocsLoadbal3RestrictCmCfgGrpId in table hwDocsLoadbal3RestrictCmCfgTable."
         
       REVISION     "201511300000Z"
       DESCRIPTION  "V1.89, Added the leaf hwCmtsRfPowerDsGroupConfigAtt, hwCmtsRfPowerDsGroupConfigEq, hwCmtsRfPowerDsGroupStatusAtt,
                     hwCmtsRfPowerDsGroupStatusEq in table hwCmtsRfPowerDsGroupTable.
                     Added the leaf hwCmtsRfPowerDsAdjustMode, hwCmtsRfPowerDsConfigCatvAtt, hwCmtsRfPowerDsConfigDocsisAtt, hwCmtsRfPowerDsStatusCatvAtt,
                     hwCmtsRfPowerDsStatusDocsisAtt in table hwCmtsRfPowerTable.
                     Added the leaf hwCmtsRfPowerUsStatusAttenuation, hwCmtsRfPowerUsStatusEq in table hwCmtsRfPowerUsTable.
         "
           
       REVISION     "201511270000Z"
       DESCRIPTION  "V1.88, Added the DEFVAL of the leaf hwCmtsIpReturnDsChannelTxPowerConfig."

       REVISION     "201511150000Z"
       DESCRIPTION  "V1.87, Added the leaf hwDocsIf3CmtsCmRegStatusCurrentServiceTypeID, hwDocsIf3CmtsCmRegStatusCurrentPolicyID,hwDocsIf3CmtsCmRegStatusPolicyIDinCfgFile,
                                hwDocsIf3CmtsCmRegStatusPriorityinCfgFile, hwDocsIf3CmtsCmRegStatusCurrentPriority in table hwCmtsRfPowerDsGroupConfigTable.
        Added the table hwDocsIf31CmtsCmUsOfdmaChannelStatusTable.
              Added the table hwDocsIf31CmtsCmDsOfdmChannelStatusTable.
              Added the leaf hwDocsIf3CmtsCmRegStatusOfdmaPartialChannelMask, hwDocsIf3CmtsCmRegStatusOfdmPartialChannelMask in table hwDocsIf3CmtsCmRegStatusTable.
        Added the leaf hwCmtsUpChannel31CmDataRateSum,hwCmtsUpChannel31CmUtilization in table hwCmtsUpChannelTable.
        Added the leaf hwCmtsDownChannel31CmDataRateSum,hwCmtsDownChannel31CmUtilization in table hwCmtsDownChannelTable.
        Modified the leaf hwDocsIfCmtsUpChnlMslotIntervalUsageCode.hwDocsIf3CmtsCmRegStatusLbGroupId .
        Added the leaf hwDocsIf31CmtsUsOfdmaChanMinRxMer,hwDocsIf31CmtsUsOfdmaChanMaxRxMer int table hwDocsIf31CmtsUsOfdmaChanTable.
        Added the leaf hwDocsIf31CmtsDsOfdmChanTxPower in table hwDocsIf31CmtsDsOfdmChanTable.
        Modified the range of flowing leaves:hwCmtsCmFrequencyDsChannelID, hwCmtsCmFrequencyUsChannelID."

       REVISION     "201511040000Z"
       DESCRIPTION  "V1.86, Add the table hwDocsIf3CmtsCmDepartureReasonTable,
                     Added the leaf hwDocsIf3MdCfgOperation in table hwDocsIf3MdCfgTable,      
                     Added the leaf hwdocsIfUpstreamChannelOperation in table hwdocsIfUpstreamChannelTable, 
                     Added the leaf hwCmtsDownChannelOperation in table hwCmtsDownChannelTable,   
                     Added the leaf hwCmtsCmConnOperation in table hwCmtsCmConnectivityTable,
                     Modified the leaf hwDocsIf3CmtsCmCtrlOperStatus in table hwDocsIf3CmtsCmRegStatusTable."
       REVISION     "201511030000Z"
       DESCRIPTION  "V1.85, Modify the size of hwCmtsCmServiceDomainName from 1..15 to 0..15."

       REVISION     "201510300000Z"
       DESCRIPTION  "V1.84, Added the leaf hwCmtsRfPowerDsAdjustOperation in table hwCmtsRfPowerTable.
                     Modified the range of hwCmtsRfPowerDsCatvDocsisDiff."
       
       REVISION     "201510300000Z"
       DESCRIPTION  "V1.83, Added the leaf  hwCmtsIpReturnDsModulationTechConfig,hwCmtsIpReturnDsModulationTechStatus,hwCmtsIpReturnDsChannelTxPowerConfig,
                     hwCmtsIpReturnDsChannelTxPowerStatus,hwCmtsIpReturnDsBitRateConfig,hwCmtsIpReturnDsBitRateStatus in table hwCmtsIpReturnDsChannelTable.
                     Modified the enumaration of hwCmtsIpReturnDsChannelFreqWidthConfig,hwCmtsIpReturnDsChannelFreqWidthStatus.
                     Modify the range of leaf hwCmtsIpReturnDsChannelFrequencyConfig,hwCmtsIpReturnDsChannelFrequencyStatus.
                     Added the leaf  hwCmtsIpReturnUsModulationTechConfig,hwCmtsIpReturnUsModulationTechStatus,
                     hwCmtsIpReturnUsBitRateConfig,hwCmtsIpReturnUsBitRateStatus in table hwCmtsIpReturnUsChannelTable.
                     Modified the enumaration of hwCmtsIpReturnUsChannelFreqWidthConfig,hwCmtsIpReturnUsChannelFreqWidthStatus."

       REVISION     "201510210000Z"
       DESCRIPTION  "V1.82, Modified the name of hwCmtsRfPowerDsGroupConfigTable to hwCmtsRfPowerDsGroupTable.
                     Modified the name of hwCmtsRfPowerConfigTable to hwCmtsRfPowerTable.
                     Modified the name of hwCmtsRfPowerDsGroupConfigMaxFreqPower to hwCmtsRfPowerDsGroupConfigRFOutPower.
                     Modified the name of hwCmtsRfPowerDsGroupConfigEq to hwCmtsRfPowerDsGroupConfigRFOutEq.
                     Modified the name of hwCmtsRfPowerUsConfigTable to hwCmtsRfPowerUsTable.
                     Added the leaf hwCmtsRfPowerDsGroupSplitterType in table hwCmtsRfPowerDsGroupConfigTable.
                     Modified the range of flowing leaves:hwCmtsRfPowerDsMonitorFrequency, hwCmtsRfPowerDsMonitorStatusFrequency,
                     hwCmtsRfPowerDsMonitorTempFrequency, hwCmtsRfPowerDsGroupConfigMaxFreqPower, hwCmtsUsSpectrumMonitorDataID.
                     Modified the description of hwCmtsRfPowerUsConfigAttenuation, hwCmtsRfPowerUsConfigEq, hwCmtsRfPowerDsCatvDocsisDiff.
                     Modified the enumaration of hwCmtsDownChannelNotActiveReason."

       REVISION     "201510170000Z"
       DESCRIPTION  "V1.81, Add the table hwCmtsCmServiceDomainMappingTable."

       REVISION     "201510160000Z"
       DESCRIPTION  "V1.80, Modified the enumaration of hwCmtsDownChannelNotActiveReason."
                     
       REVISION     "201510120000Z"
       DESCRIPTION  "V1.79, Added the leaf hwCmtsCapabilityPNMSpecturmMaxFrequency in table hwCmtsCapabilityStatusTable.
                     Added the leaf hwCmtsCapabilityPNMSpecturmResolution in table hwCmtsCapabilityStatusTable.
                     Added the leaf hwCmtsCapabilityPNMSpecturm in table hwCmtsCapabilityStatusTable."

       REVISION     "201509280000Z"
       DESCRIPTION  "V1.78, Add the table of hwDocsIf31CmtsDsOfdmChanTable.
                     Add the table of hwDocsIf31CmtsUsOfdmaChanTable.
                     Add the table of hwDocsIf31CmtsCmRegStatusTable.
                     Add the table of hwDocsPnmCmtsUsOfdmaRxMerTable.
                     Add the table of hwDocsPnmCmtsUsOfdmaRxMerReportTable.
                     Added the leaf hwCmtsUsSpectrumMonitorFrequencyList for hwCmtsUsSpectrumMonitorCfgTable.
                     Modified the enumaration of hwDocsIfDownstreamChannelMode.
                     Deleted the leaf hwCmtsCapabilityRealEqamSdvDownstreamChannelNum in table hwCmtsCapabilityStatusTable.
                     Added the leaf hwCmtsCapabilityRealEqamDownstreamChannelNum in table hwCmtsCapabilityStatusTable.
                     Modified the description of hwCmtsUsRasterCheckCnr1.
                     Modified the description of hwCmtsUsRasterCheckCnr2."
         
       REVISION     "201509180000Z"
       DESCRIPTION  "V1.77, Add notSupportChannelAnnex(19) in hwCmtsDownChannelNotActiveReason.
                Add the leaf hwDocsIfDownstreamChannelAnnex in table hwDocsIfDownstreamChannelTable.
          Add leaf hwCmtsCapabilityChannelAnnex in table hwCmtsCapabilityStatusTable.
          Modified the enumaration and description of hwCmtsUsSpectrumMonitorMode, hwCmtsUsSpectrumMonitorResolution.
          Extended parameter range for hwCmtsUsSpectrumMonitorFrequencyStart.
          Extended parameter range for hwCmtsUsSpectrumMonitorFrequencyEnd.
          Extended parameter range for hwCmtsUsSpectrumMonitorSampleStart.
          Add the table hwCmtsUsHistorySpectrumCfgTable.
          Modified the enumaration of hwCmtsUsSpectrumMonitorDataType, hwCmtsUsInfoCollectFileType,
          hwCmtsUsInfoCollectDataItem.
          Add the table hwCmtsUsRasterCfgTable.
          Add the table hwCmtsUsRasterCheckTable.
          Add the leaf hwCmtsRasterStatusCheckPara.
          "
       REVISION     "201509150000Z"
       DESCRIPTION  "V1.76, Added the leaf hwCmtsCapabilityUpstreamCenterFreqSpan65MHz..
                     Modified the parameter of hwCmtsUpChannelNotActiveReason and hwCmtsDownChannelNotActiveReason.
                     "
       REVISION     "201508280000Z"
       DESCRIPTION  "V1.75, Modified the description of hwCmtsRfPowerDsMonitorTempExpectPower.
                     Modified the description of hwCmtsRfPowerDsMonitorTempFreqMeterPower.
                     Modified the description of hwCmtsCmWhitelistModeEntry.
                     Modify the SYNTAX of hwCmtsCmWhitelistIndex. "

       REVISION     "201508270000Z"
       DESCRIPTION  "V1.74, Modified the description of hwCmtsRfPowerDsMonitorStatusFreqExpectPower.
                     Modified the description of hwCmtsRfPowerDsMonitorStatusFreqMeterPower"

       REVISION     "201508240000Z"
       DESCRIPTION  "V1.73, Added the leaf hwIpReturnConnectObject."
      
       REVISION     "201508190000Z"
       DESCRIPTION  "V1.72, Modified the description of hwCmtsCmWhitelistIndex.
                     Modified the description of hwCmtsCmWhitelistType.
                     Modified the description of hwCmtsCmWhitelistMacList.
                     Modified the description of hwCmtsCmWhitelistMacMaskList.
                     Modified the description of hwCmtsCmWhitelistRowstatus.
                     Modify the range of hwCmtsCmWhitelistIndex.
                     "
       REVISION     "201508140000Z"
       DESCRIPTION  "V1.71, Modified the wrong word bettwen to between,
            Modefied the wrong word configration to configuration ,
            Modified the wrong word bongding to bonding,
            Modified the wrong word quering to querying,
            Modified the wrong word infomation to information,
            Modified the wrong word indecates to indicates,
            Modified the wrong word letf to left,
            Modified the word up stream and down stream to upstream and downstream."
       REVISION     "201508130000Z"
       DESCRIPTION  "V1.70, Modified the enumaration and description of hwCmtsRfPowerDsMonitorStatusFreqWidth, hwCmtsRfPowerDsMonitorStatusFreqType, hwCmtsRfPowerDsMonitorTempFreqWidth,
                     hwCmtsRfPowerDsMonitorTempFreqType, hwCmtsRfPowerDsMonitorFreqWidth,hwCmtsRfPowerDsMonitorFreqType."

       REVISION     "201508100000Z"
       DESCRIPTION  "V1.69, Modified missing spelling in some mib nodes."

       REVISION     "201508060000Z"
       DESCRIPTION  "V1.68, Modified the description of hwCmtsRfPowerDsMonitorStatusTable, hwCmtsRfPowerDsGroupConfigTable, hwCmtsRfPowerUsConfigTable
                     Extended parameter 
                     Modified the description of hwCmtsRfPowerDsMonitorStatusFrequency.
                     Modified the description of hwCmtsRfPowerDsMonitorStatusFreqIndex.
                     Modified the description of hwCmtsRfPowerDsGroupConfigEq.
                     Modified the description of hwCmtsRfPowerUsConfigAttenuation.
                     Modified the description of hwCmtsRfPowerUsConfigEq."
                     
       REVISION     "201507300000Z"
       DESCRIPTION  "V1.67, Modified the description of hwCmtsRfPowerDsGroupConfigEntry, hwCmtsRfPowerConfigTable, hwCmtsRfPowerConfigEntry, hwCmtsRfPowerUsConfigEntry,
                     hwCmtsRfPowerDsMonitorStatusEntry, hwCmtsRfPowerDsMonitorConfigEntry, hwCmtsRfPowerDsMonitorIndex.
                     Extended parameter range for hwCmtsRfPowerDsMonitorIndex."

       REVISION     "201507240000Z"
       DESCRIPTION  "V1.66, Added leaf hwCmtsCapabilityRealEqamSdvDownstreamChannelNum in table hwCmtsCapabilityStatusTable.
                    Modified the enumaration of the leaf hwDocsIfDownstreamChannelMode.
        Modified the enumaration of the leaf hwDocsLoadbal3RestrictCmCfgMacVer.
                    Added the flowing tables:hwCmtsRfPowerDsGroupConfigTable, hwCmtsRfPowerConfigTable, hwCmtsRfPowerUsConfigTable.
                    Added the flowing tables:hwCmtsRfPowerDsMonitorStatusTable, hwCmtsRfPowerDsMonitorTempTable and hwCmtsRfPowerDsMonitorConfigTable.
                    Modified the description of hwCmtsOverCmSpecAlarmTrap.
                    Added the leaf hwCmtsRfTxPowerAbnormalFaultTrap.
                    Added the leaf hwCmtsRfTxPowerAbnormalRestoreTrap.
                    Added the leaf hwCmtsDownstreamRfPowerAdjustmentGroupID."
      
       REVISION     "201507230000Z"
       DESCRIPTION  "V1.65, Modified the description of the hwCmtsOverCmSpecAlarmTrap."

       REVISION     "201506260000Z"
       DESCRIPTION  "V1.64, Modified the description of the hwDocsIf3CmtsCmRegStatusUsBondingGroupId, hwDocsIf3CmtsCmRegStatusDsBondingGroupId, hwDocsIf3CmtsCmRegStatusRccCfgId, hwDocsIf3CmtsCmRegStatusDsRequiredMask,
                     hwDocsIf3CmtsCmRegStatusDsForbiddenMask, hwDocsIf3CmtsCmRegStatusUsRequiredMask, hwDocsIf3CmtsCmRegStatusUsForbiddenMask. Modified the SYNTAX of hwDocsIf3BondingGrpCfgMdSg."

       REVISION     "201506230000Z"
       DESCRIPTION  "V1.63, Modified the descripition of the hwCmtsAuthKey."
       
       REVISION     "201506150000Z"
       DESCRIPTION  "V1.62, Added the table hwCmtsIpReturnUsChannelTable.Added the table hwCmtsIpReturnDsChannelTable. 
                     Added hwDocsIf3CmtsCmRegStatusOfdmMTC and hwDocsIf3CmtsCmRegStatusOfdmProfileCapability to hwDocsIf3CmtsCmRegStatusTable.
                     Modified the enumaration of the leaf hwDocsIf3CmtsCmRegStatusDOCSISVersion, hwDocsIf3CmtsCmRegStatusValue and hwDocsIf3CmtsCmRegStatusPreviousStatusValue.
                     Add the table hwDocsIf3BondingGrpCfgTable.
                     Added the flowing leaves:hwDocsIf3CmtsCmRegStatusUsBondingGroupId,hwDocsIf3CmtsCmRegStatusDsBondingGroupId,hwDocsIf3CmtsCmRegStatusRccCfgId,
                     hwDocsIf3CmtsCmRegStatusDsRequiredMask,hwDocsIf3CmtsCmRegStatusDsForbiddenMask,hwDocsIf3CmtsCmRegStatusUsRequiredMask,hwDocsIf3CmtsCmRegStatusUsForbiddenMask.
                     Added leaf hwCmtsCapabilityRealRfIpReturnSupport in table hwCmtsCapabilityStatusTable.
                     Added the flowing leaves:hwCmtsUsSpectrumMonitorUsSgId,hwCmtsUsSpectrumMonitorUsChannelId.
                     Added the table hwCmtsUsInfoCollectTable.
                     Added the table hwCmtsUsCmcPerformanceCfgTable"

       REVISION     "201506050000Z"
       DESCRIPTION  "V1.61, Add the table of hwDocsLoadbalanceClassifyStatTable. Add the flowing leaves:hwCmtsLoadBalanceStaticDynamicThreshold and hwCmtsLoadBalanceDynamicStaticThreshold." 

       REVISION     "201505270000Z"
       DESCRIPTION  "V1.60, Modified the description of hwCmtsCmTrafficUpStreamCir, hwCmtsCmTrafficUpStreamCbs, hwCmtsCmTrafficUpStreamPir, hwCmtsCmTrafficUpStreamPbs, 
                     hwCmtsCmTrafficDownStreamCir, hwCmtsCmTrafficDownStreamCbs, hwCmtsCmTrafficDownStreamPir, hwCmtsCmTrafficDownStreamPbs,
                     hwCmtsCmTrafficUpStream, hwCmtsCmTrafficDownStream, hwCmtsCmTrafficUpStreamMax and hwCmtsCmTrafficDownStreamMax in hwCmtsCmTrafficTable."

       REVISION     "201505260000Z"
       DESCRIPTION  "V1.59, Added the flowing leaves:hwdocsIf3MdCfgMapLeadTime and hwdocsIf3MdCfgMinMapTime."
                     
       REVISION     "201505160000Z"
       DESCRIPTION  "V1.58, Modified the parameter of hwCmtsUpChannelNotActiveReason from exceedMaxUsSGNum(9) to exceedMaxUsSGNum(10).
                     Modified description of the leaf hwCmtsCapabilityRealMdUsSgNum."
                     
       REVISION     "201505070000Z"
       DESCRIPTION  "V1.57, Modified the enumaration and description of the leaf hwCmtsServiceDomainMappingMatchType. 
                     Add the object hwCmtsL2vpnFloodingModeConfigObject."
       
       REVISION     "201504270000Z"
       DESCRIPTION  "V1.56, Extended parameter range for hwCmtsUpChannelNotActiveReason,added parameter exceedMaxUsSGNum(9);
                     Added the flowing leaves:hwdocsIfUpstreamChannelMdUsSgId,hwDocsIf3MdCfgUsSgMode,hwCmtsCapabilityRealMdUsSgNum;
                     Added the flowing tables:hwDocsLoadbal3ResGrpCfgTable,hwDocsIf3CmtsMdUsSgStatTable and hwCmtsLoadBalanceStatusChannelTable."

       REVISION     "201504250000Z"
       DESCRIPTION  "V1.55, Modified the description of hwCmtsCmDataChangeCmOperTypeList."
       REVISION     "201504220000Z"
       DESCRIPTION  "V1.54, Modified the MAX-ACCESS of hwCmtsCmPnmGroupIndex in hwCmtsCmPnmAttributeTable."
       
              
       REVISION     "201504100000Z"
       DESCRIPTION  "V1.53, Changed the mib file from HUAWEI-IF-EXT-MIB to IF-MIB in IMPORTS."
       
       REVISION     "201504060000Z"
       DESCRIPTION  "V1.52, Add the leaf hwDocsIf3CmtsCmRegStatusCrc, hwDocsIf3CmtsCmRegStatusHcs for hwDocsIf3CmtsCmRegStatusTable.
                     Modified the description of hwDocsIf3CmtsCmRegStatusSysDesc in hwDocsIf3CmtsCmRegStatusTable.
                     Modified the description of hwCmtsCmNumSummaryIfName in hwCmtsCmNumSummaryTable.
                     "
                     
       REVISION     "201504020000Z"
       DESCRIPTION  "V1.51, Changed the mib file from HUAWEI-TC-MIB to HUAWEI-IF-EXT-MIB in IMPORTS."

       REVISION     "201503300000Z"
       DESCRIPTION  "V1.50, Add the leaf hwCmtsCmNumSummaryIfName for hwCmtsCmNumSummaryTable"
       
       REVISION     "201503280000Z"
       DESCRIPTION  "V1.49, Add the leaf hwCmtsDownChannelConfigTxPower for hwCmtsDownChannelTable."

       REVISION     "201503180000Z"
       DESCRIPTION  "V1.48, Modify the range of leaf hwCmtsUsSpectrumMonitoReportInterval and hwCmtsUsSpectrumMonitorCollectInterval in hwCmtsUsSpectrumMonitorInfoTable.
                     Modify the range of leaf hwCmtsUsConstellationReportInterval and hwCmtsUsConstellationCollectInterval in hwCmtsUsConstellationInfoTable."
                     
       REVISION     "201503140000Z"
       DESCRIPTION  "V1.47, Modified the SYNTAX of hwDocsIf3CmtsCmRegStatusLbGroupId and hwDocsIf3CmtsCmRegStatusLbGroupIdinCfgFile in hwDocsIf3CmtsCmRegStatusTable.
                     Modified the range of hwDocsIf3CmtsCmRegStatusLbGroupId and hwDocsIf3CmtsCmRegStatusLbGroupIdinCfgFile in hwDocsIf3CmtsCmRegStatusTable.
                     Modified the description of hwDocsIf3CmtsCmRegStatusLbGroupId in hwDocsIf3CmtsCmRegStatusTable."
                     
       REVISION     "201503100000Z"
       DESCRIPTION  "V1.46, Added hwCmtsGoingOnlineCmNum in hwcmtsTrapsVbOids.
                     Modify the description of the node hwDocsIf3CmtsCmRegStatusLbGroupId."
                     
       REVISION     "201503090000Z"
       DESCRIPTION  "V1.45, Added hwCmtsGoingOnlineCmNum in hwcmtsTrapsVbOids.
                     Disuse the leaf hwCmtsUsConstellationMac, hwCmtsUsConstellationPreEqualMER, hwCmtsUsConstellationMER and hwCmtsUsConstellationMERSample in hwCmtsUsConstellationInfoTable."
                     

       REVISION     "201503030000Z"
       DESCRIPTION  "V1.44, Modify the range of leaf hwCmtsUsSpectrumMonitorCollectInterval in hwCmtsUsSpectrumMonitorInfoTable.
                     Modify the range of leaf hwCmtsUsConstellationCollectInterval in hwCmtsUsConstellationInfoTable."
                     
       REVISION     "201503030000Z"
       DESCRIPTION  "V1.44, Modify the description of the leaf hwCmtsUsSpectrumMonitorSwitch, hwCmtsUsSpectrumMonitorResolution and hwCmtsUsSpectrumMonitorSampleTime.
                     Modify the description of the entry hwCmtsCmPnmAttributeEntry and hwCmtsUsSpectrumMonitorInfoEntry."
       
       REVISION     "201502260000Z"
       DESCRIPTION  "V1.43, Modify the size list of hwCmtsSysCfgBandwidthUtilizationInterval from 0..86400 to 60..86400."
                     
       REVISION     "201502120000Z"
       DESCRIPTION  "V1.42, Delete the the leaf hwCmtsUsSpectrumMonitorDesc, add the leaf hwCmtsUsSpectrumMonitorSampleStart for hwCmtsUsSpectrumMonitorCfgTable.
                     Add the table hwCmtsUsSpectrumMonitorInfoTable.
                     Add the table hwCmtsUsConstellationInfoTable."
       
       REVISION     "201502100000Z"
       DESCRIPTION  "V1.42, Add the table hwCmtsCmPnmAttributeTable."
       REVISION     "201502060000Z"
       DESCRIPTION  "V1.41, Add invalid value the description of the leaf hwDocsIf3CmtsCmRegStatusMacDomainDsSvcGroup, hwDocsIf3CmtsCmRegStatusMacDomainUsSvcGroup, 
                                   hwDocsIf3CmtsCmRegStatusMacDomainCmSvcGroup and hwDocsIf3CmtsCmRegStatusLbGroupIdinCfgFile in hwDocsIf3CmtsCmRegStatusTable."

       REVISION     "201501310000Z"
       DESCRIPTION  "V1.40, Modify the object hwCmtsAdmissionCtrlChannelBandwidthChannelType to hwCmtsAdmCtrlChlBandwidthChannelType for hwCmtsAdmissionCtrlAlarmMinorFaultTrap,
                                     hwCmtsAdmissionCtrlAlarmMinorRestoreTrap, hwCmtsAdmissionCtrlAlarmMajorFaultTrap and hwCmtsAdmissionCtrlAlarmMajorRestoreTrap.
                                     Modify value range of hwDocsCableModemMaxCpeNum."
                     
       REVISION     "201501210000Z"
       DESCRIPTION  "V1.39, Modify the SYNTAX of hwDocsIf3CmtsCmRegStatusHostInterface. Modify the definition of hwCmtsServiceTypeEntry INDEX."
          
       REVISION     "201501190000Z"
       DESCRIPTION  "V1.38, Add the table hwCmtsServiceVlanTable.
                            Add the table hwL2vpnCmMplsNsiTable."
          
       REVISION     "201501190000Z"
       DESCRIPTION  "V1.37, Modify the description of the leaf hwCmtsCapabilityRealUpstreamChannelNum, hwCmtsCapabilityRealDownstreamChannelNum,
                                    hwCmtsCapabilityRealUpstreamMaxFrequency, hwCmtsCapabilityRealDownstreamMaxFrequency, hwCmtsCapabilityRealDownstreamMaxFrequencySpan, 
                                    hwCmtsUsSpectrumMonitorDesc and hwDocsIf3CmtsCmDownChannelInfoFrequency"

       REVISION     "201501140000Z"
       DESCRIPTION  "V1.36, Modify the description of the leaf hwDocsIf3CmtsCmRegStatusPrimaryDs and hwDocsIf3CmtsCmRegStatusPrimaryDsFrequency"
  
       REVISION     "201501050000Z"
       DESCRIPTION  "V1.35, Modify the description of the leaf hwCmtsServiceDomainMappingVpnID.
               Modify the description of the leaf hwDocsIf3CmtsCmCpeInfoIPv4Addr.
               Modify the MAX-ACCESS type of the leaf hwCmtsSpectrumGroupRowstatus,hwCmtsLoadBalanceExcludeCmRowStatus,hwCmtsAdmissionCtrlMappingRowStatus."
        
       REVISION     "201412230000Z"
       DESCRIPTION  "V1.35, Add the table of hwCmtsUsSpectrumMonitorCfgTable.
                            Add the leaf hwCmtsCapabilityRealDownstreamMaxFrequencyGroupNum.
                            Add the leaf hwCmtsCapabilityRealDownstreamFrequencyGroupCenterDivisor.
                            Add exceedMaxFreqGroup(9) in hwCmtsDownChannelNotActiveReason"
     
       REVISION     "201412100000Z"
       DESCRIPTION  "V1.35, Modify the description of the table hwDocsLoadbalanceStatTable."

       REVISION     "201412170000Z"
       DESCRIPTION  "V1.34, Add the table hwCmtsCmWhitelistTable.
                    Add the table hwCmtsCmWhitelistModeTable.
                    Add the leaf hwCmtsCmWhitelistMac for hwcmtsTrapsVbOids.
                    Add the leaf hwCmtsCmWhitelistMacTrap.  "
       REVISION     "201412080000Z"
       DESCRIPTION  "V1.33, Add the leaf hwCmtsLoadBalanceDifferenceThresholdD3 for hwCmtsLoadBalanceTable.
                          Modify the range of leaf hwDocsLoadbal3RestrictCmCfgMethod in hwDocsLoadbal3RestrictCmCfgTable.
                          Modify the description of the leaf hwDocsIf3CmtsCmRegStatusUsTxPowerReachMaxFlag in hwDocsIf3CmtsCmRegStatusTable.
                          Modify the description of the entry hwDocsLoadbalanceStatEntry in hwDocsLoadbalanceStatTable.
                          Modify the description of the table hwDocsIfCmtsCmCpeMacToCmTable."

       REVISION     "201412050000Z"
       DESCRIPTION  "V1.32, Modify the description of the leaves hwCmtsServiceDomainMappingID, hwCmtsServiceDomainMappingOuterVlan, hwCmtsServiceDomainMappingSIpAddressPrefixLen, hwCmtsServiceDomainMappingVpnID, hwCmtsServiceDomainMemberAddressPrefixLen, hwCmtsServiceDomainMemberFrameID, hwCmtsServiceDomainMemberSlotID, hwCmtsServiceDomainMemberIfindex."

       REVISION     "201412010000Z"
       DESCRIPTION  "V1.31, Add the leaf hwCmtsSysCfgBandwidthUtilizationInterval for hwCmtsSysCfgTable.
                            Add the table of hwDocsIfCmtsCmCpeMacToCmTable.
                            Add the leaf hwdocsIfCmtsModGuardTimeSize and hwdocsIfCmtsBasedModIndex for hwdocsIfCmtsModulationTable.
                            Add the leaf hwDocsIf3CmtsCmRegStatusTotalUsPktErrorNum, and hwDocsIf3CmtsCmRegStatusUsPer for hwDocsIf3CmtsCmRegStatusTable.
                            Modify the range of leaf hwDocsIfUpstreamChannelStatusModulationProfile in hwDocsIfUpstreamChannelStatusTable.
                            Modify the range of leaf hwCmtsSpectrumGroupSecondaryModulationType1 and hwCmtsSpectrumGroupSecondaryModulationType2 in hwCmtsSpectrumGroupTable.
                            Add the leaf hwDocsIf3CmtsCmRegStatusUsTxPowerReachMaxFlag for hwDocsIf3CmtsCmRegStatusTable.
                            Add the leaves hwDocsIfUpstreamChannelPowerAdjustThreshold, hwDocsIfUpstreamChannelPowerAdjustContinue, hwDocsIfUpstreamChannelPowerAdjustMax for hwdocsIfUpstreamChannelTable. 
                            Add the leaves hwDocsIfUpstreamChannelStatusPowerAdjustThreshold, hwDocsIfUpstreamChannelStatusPowerAdjustContinue, hwDocsIfUpstreamChannelStatusPowerMaxAdjust for hwDocsIfUpstreamChannelStatusTable.
                            Add the leaf hwCmtsLoadBalanceD3DifferenceThreshold and hwDocsLoadbal3RestrictCmCfgServiceTypeID.
                            Add the table hwDocsLoadbalanceStatTable."

       REVISION     "201412010000Z" 
       DESCRIPTION  "V1.30, Add the leaves hwCmtsServiceDomainMappingOuterVlanMode, hwCmtsServiceDomainMappingVpnID for hwCmtsServiceDomainMappingTable.
                     Add the leaves hwCmtsServiceDomainMemberFrameID,hwCmtsServiceDomainMemberSlotID,hwCmtsServiceDomainMemberIfindex for hwCmtsServiceDomainMemberTable.
                     Add port(2), board(3) in hwCmtsServiceDomainMemberType and modify the description."

       REVISION     "201411280000Z"
       DESCRIPTION  "V1.29, Modify the description of hwCmtsDownChannelRealTimeTxPower"

       REVISION     "201411210000Z"
       DESCRIPTION  "V1.28, Add the leaf hwCmtsDownChannelRealTimeTxPower for hwCmtsDownChannelTable"

       REVISION     "201409250000Z"
       DESCRIPTION  "V1.27, Modify the SYNTAX of hwdocsIfUpstreamChannelRngHoldoffPriority and hwdocsIfUpstreamChannelRngHoldoffPriority from Integer32 to Unsigned32. 
                            Modify the description of hwCmtsCmOverCapaTable,HwCmtsCmOverCapaEntry,hwCmtsCmOverCapaNum,and hwCmtsCmOverCapaReasonList.
                            Modify the SYNTAX of hwDocsIfRFOutCfgAttenuationValue and hwDocsIfRFOutOperAttenuationValue from Integer32 to INTEGER.
                            Modify the DESCRIPTION of hwDocsIfRFOutCfgAttenuationValue and hwDocsIfRFOutOperAttenuationValue"
                                      
       REVISION     "201409120000Z"
       DESCRIPTION  "V1.26, Modify the enumaration and description of the leaf hwCmtsCmIndexListSecondIndex. 
                                      Add the leaf hwCmtsCapabilityScdma.
                                      Add notSupportScdma(8) in hwCmtsUpChannelNotActiveReason"

       REVISION     "201408250000Z"
       DESCRIPTION  "V1.25, Add the leaf hwCmtsAdmCtrlChlBandwidthChannelType for hwcmtsTrapsVbOids."

       REVISION     "201408200000Z"
       DESCRIPTION  "V1.24, Add the table of hwCmtsUpstreamExtTable."
       
       REVISION     "201408050000Z"
       DESCRIPTION  "V1.23, Add the table hwDocsIfCmtsUpChnlMslotCounterTable         
                     Modify the range of leaf hwCmtsSpectrumGroupHopPeriod for hwCmtsSpectrumGroupTable.
         Add onlinePk(51), onlineNetAccessDisabledPk(52), wonlinePk(53), wonlineNetAccessDisabledPk(54), ponlinePk(55), ponlineNetAccessDisabledPk(56) in hwDocsIf3CmtsCmRegStatusValue.
         Add onlinePk(51), onlineNetAccessDisabledPk(52), wonlinePk(53),wonlineNetAccessDisabledPk(54) in hwDocsIf3CmtsCmRegStatusPreviousStatusValue.
         "
       
       REVISION     "201407280000Z"
       DESCRIPTION  "V1.22, Add the leaves hwDocsIf3CmtsCmRegStatusPrimaryUsGoodCodewords,hwDocsIf3CmtsCmRegStatusPrimaryUsCorrectedErrorCodewords,
                     hwDocsIf3CmtsCmRegStatusPrimaryUsUncorrectedErrorCodewords,hwDocsIf3CmtsCmRegStatusPrimaryUsFrequency, 
                     hwDocsIf3CmtsCmRegStatusPrimaryUsChannelWidth, hwDocsIf3CmtsCmRegStatusPrimaryDsGoodCodewords, 
                     hwDocsIf3CmtsCmRegStatusPrimaryDsCorrectedErrorCodewords, hwDocsIf3CmtsCmRegStatusPrimaryDsUncorrectedErrorCodewords and 
                     hwDocsIf3CmtsCmRegStatusPrimaryDsFrequency for hwDocsIf3CmtsCmRegStatusTable.
                     Add the leaves hwDocsIf3CmtsCmUsStatusEqdData,hwdocsIf3CmtsCmUsStatusFrequency and hwdocsIf3CmtsCmUsStatusChannelWidth for hwDocsIf3CmtsCmUsStatusTable.
                     Add the leaf hwDocsIf3CmtsCmDownChannelInfoFrequency for hwDocsIf3CmtsCmDownChannelInfoTable.
                     Add the table of hwCmtsCmNumStatisticsTable and hwCmtsCmIndexListTable.  
                     Modify the range of leaf hwCmtsDownChannelNotActiveReason for hwCmtsDownChannelTable.                   
                     Modify the description of hwDocsIf3CmtsCmDownChannelInfoSnr, hwDocsIf3CmtsCmDownChannelInfoMinSnr, hwDocsIf3CmtsCmDownChannelInfoMaxSnr.                     
                     Add the table of hwCmtsCmFrequencyTable.
                     Modify the description of leaf hwCmtsCmOverCapaReasonList.
                     Modify the node name from hwDocsIfRFOutAttenuationValue to hwDocsIfRFOutCfgAttenuationValue. 
                     Add the leaf hwDocsIf3CmtsCmDownChannelInfoMinRxPower, hwDocsIf3CmtsCmDownChannelInfoMaxRxPower, hwDocsIf3CmtsCmDownChannelInfoMinSnr, hwDocsIf3CmtsCmDownChannelInfoMaxSnr for hwDocsIf3CmtsCmDownChannelInfoTable.
                     Add the leaf hwDocsIf3CmtsCmUsStatusMaxSignalNoise, hwDocsIf3CmtsCmUsStatusMinSignalNoise for hwDocsIf3CmtsCmUsStatusTable.
                     Add the leaf hwCmtsUpChannelMinSnr, hwCmtsUpChannelMaxSnr for hwCmtsUpChannelTable.
                     Add the leaf hwDocsIf3CmtsCmRegStatusServiceTypeID for hwDocsIf3CmtsCmRegStatusTable.
                     modified the description of hwCmtsCmTrafficUpStreamCir, hwCmtsCmTrafficUpStreamCbs, hwCmtsCmTrafficUpStreamPir, hwCmtsCmTrafficUpStreamPbs, 
                     hwCmtsCmTrafficDownStreamCir, hwCmtsCmTrafficDownStreamCbs, hwCmtsCmTrafficDownStreamPir, hwCmtsCmTrafficDownStreamPbs,
                     hwCmtsCmTrafficUpStream, hwCmtsCmTrafficDownStream, hwCmtsCmTrafficUpStreamMax and hwCmtsCmTrafficDownStreamMax in hwCmtsCmTrafficTable.
                     Delete leaf hwCmtsCableModemVendorNameDefault.
                     Modify the name of leaf hwCmtsCableModemVendorName to hwCmtsCableModemUserDefinedVendorName.
                     Modify the OID of leaf hwCmtsCableModemVendorRowStatus. 
                     "
       REVISION     "201407110000Z"
       DESCRIPTION  "V1.21, modified the description of hwCmtsServiceDomainMappingSIpAddressType and hwCmtsServiceDomainMemberAddressType."

       REVISION     "201407100000Z"
       DESCRIPTION  "V1.20, Add the leaf hwDocsIfRFOutCfgAttenuationValue  and hwDocsIfRFOutOperAttenuationValue for hwDocsIfRFOutTable.
                     Add the table of hwDocsLoadbal3RestrictCmCfgTable.       
                     Add the leaf hwDocsIf3CmtsCmRegStatusRangingClassIDValidFlag and hwDocsIf3CmtsCmRegStatusRangingClassID for hwDocsIf3CmtsCmRegStatusTable.
                     Modify the description of leaf hwDocsIf3CmtsCmAccessNumLowerThreshold.
                     Modify the entry name of hwDocsIfUpstreamChannelStatusTable"

       REVISION     "201406230000Z"
       DESCRIPTION  "V1.19, Modify CONTACT-INFO information and the following not normative nodes to satisfy for the new OMSYS tool                       
                    hwCmtsUpChannelHist15MinEntry
                    hwCmtsUpChannelNotActiveReason
                    hwDocsIf3CmtsCmRegStatusBpi
                    hwCmtsAdmissionCtrlMappingSchedulingType
                    hwCmtsAdmissionCtrlChannelBandwidthChannelType
                    hwCmtsDownChannelNotActiveReason.
                     "
       REVISION     "201404080000Z"
       DESCRIPTION  "V1.18, delete leaf hwCmtsCableModemVendorNameDefault.
                     Modify the name of leaf hwCmtsCableModemVendorName to hwCmtsCableModemUserDefinedVendorName.
                     Modify the OID of leaf hwCmtsCableModemVendorRowStatus.
           Add table hwDocsIf3CmtsCmThresholdTable.
                     Add leaf hwCmtsCmAccessThresholdAlarmMinorFaultTrap and hwCmtsCmAccessThresholdAlarmMajorRestoreTrap in hwdocsIfCmtsCommonTraps.
                     Add leaf hwDocsIf3CmtsCmAccessCurrentNum in hwcmtsTrapsVbOids
                     Add hwCmtsLoadBalanceCmNumDifferenceThreshold in hwCmtsLoadBalanceTable.
                     Add hwDocsIf3CmtsCmUsRangingStatusList in hwcmtsTrapsVbOids and hwDocsIf3CmtsCmRemoteQueryTrap.
                     Add the hwCmtsServiceTypeTable for CMTS.
                     Modify the description of hwDocsIf3CmtsCmRegStatusUsPartialChannelMask and hwDocsIf3CmtsCmRegStatusDsPartialChannelMask.
                     Modify the index of table hwCmtsCableModemVendorStatisticTable to ifIndex from ifIndex and hwCmtsCableModemOUIList.
                     Add the leaf hwCmtsPortStatusChangeTrap.
           Add the leaves hwCmtsSysSnrDegradeThreshold and hwCmtsSysSnrRestoreThreshold for hwCmtsSysCfgTable.
                     Add the leaves hwCmtsSNRDegradeAlarmTrap,hwCmtsSNRRestoreAlarmTrap,hwCmtsUpstreamAbnormalStateAlarmTrap,hwCmtsUpstreamNormalStateAlarmTrap,hwCmtsDownstreamAbnormalStateAlarmTrap, and hwCmtsDownstreamNormalStateAlarmTrap for hwdocsIfCmtsCommonTraps.
             Add the leaves hwCmtsUpChannel20CmUtilization and hwCmtsUpChannel30CmUtilization for hwCmtsUpChannelTable.
                     Add the leaves hwDocsIf3CmtsCmRegStatusUsPartialChannelMask and hwDocsIf3CmtsCmRegStatusDsPartialChannelMask for hwDocsIf3CmtsCmRegStatusTable.
                     Add the leaf hwDocsIf3CmtsCmUsStatusUtilization for hwDocsIf3CmtsCmUsStatusTable.
                     Add the leaf hwDocsIf3CmtsCmDownChannelInfoUtilization for hwDocsIf3CmtsCmDownChannelInfoTable.
                     Add the leaves hwCmtsDownChannel20CmUtilization and hwCmtsDownChannel30CmUtilization for hwCmtsDownChannelTable.
                 Add the table of hwDocsIfRFOutTable.
                     Added hwCmtsLoadBalanceRangeOverrideMode in hwCmtsLoadBalanceTable.
                     Add the table of hwCmtsCmUsChannelCurrTable."          
                     
       REVISION     "201402100000Z"
       DESCRIPTION  "V1.17, Add the table of hwServiceFlowExtTable." 

       REVISION     "201401270000Z"
       DESCRIPTION  "V1.16, Move the tables hwCmtsCableModemVendorTable and hwCmtsCableModemVendorStatisticTable from hwCmtsObject to hwCmtsAccessObject.
                     Modify the range of hwDocsIf3CmtsCmDownChannelInfoChannelId,hwCmtsAdmissionCtrlChannelBandwidthChannelId,hwCmtsAdmissionCtrlStatisticsChannelId. 
                     Modify the description of hwDocsIf3CmtsCmRegStatusPrimaryUs
             Modify the range of hwDocsIf3CmtsCmRegStatusUpChannelNum. 
             Add the leaf hwDocsIf3CmtsCmDownChannelInfoMer,hwDocsIf3CmtsCmDownChannelInfoMerSamples, hwDocsIf3CmtsCmDownChannelInfoMicroreflections
                     for hwDocsIf3CmtsCmDownChannelInfoTable.
                     Add leaf  hwDocsIf3CmtsCmDsMerList,hwDocsIf3CmtsCmDsMerSamplesList, hwDocsIf3CmtsCmDsMicroreflectionsList, hwDocsIf3CmtsCmDsPer for hwDocsIf3CmtsCmRemoteQueryTrap.
                     Add the table of hwCmtsCableModemVendorTable and hwCmtsCableModemVendorStatisticTable.
                     Add the table of hwCmtsCapabilityConfigTable and hwCmtsCapabilityStatusTable.
                     Add the table of hwCmtsLoadBalanceExcludeCmTable.
                     Add leaf node:hwCmtsDownChannelNotActiveReason,hwCmtsUpChannelNotActiveReason,hwDocsIf3CmMdCfgIpProvMode.
                     Modify the DESCRIPTION of hwDocsIf3CmtsCmRegStatusPrimaryDsTxPower, hwDocsIf3CmtsCmRegStatusPrimaryUsRxPower and hwDocsIf3CmtsCmRegStatusPrimaryUsTxPower.
                     Add the leaf hwDocsIf3CmtsCmRegStatusDsPer for hwDocsIf3CmtsCmRegStatusTable.
                     Add the leaf hwCmtsUpChannelPer for hwCmtsUpChannelTable.
                     Delete the range of leaf node: hwCmtsCmCurrId, hwCmtsCmHist15MId, hwCmtsCmHist1DayId, hwDocsIfCmtsCmPtr, hwCmtsMtaInfoCmId.
                     Add dhcpv6Advertise(49), dhcpv6Request(50) in hwDocsIf3CmtsCmRegStatusValue and modify the description.
                     Add dhcpv6Advertise(49), dhcpv6Request(50) in hwDocsIf3CmtsCmRegStatusPreviousStatusValue and modify the description.
                     Add leaf node: hwDocsIf3CmtsCmCpeInfoIPv6Addr, hwDocsIf3CmtsCmCpeInfoIPv6Prefix, hwDocsIf3CmtsCmCpeInfoIPv6PrefixLength, 
                     hwDocsIf3CmtsCmCpeInfoIPv6LinkLocal, hwCmtsCmNumSummaryDhcpV4RequestCmNum, hwCmtsCmNumSummaryStartDhcpV6CmNum, 
                     hwCmtsCmNumSummaryDhcpv6AdvertiseCmNum, hwCmtsCmNumSummaryDhcpV6RequestCmNum, hwCmtsCmNumSummaryDhcpV6CompleteCmNum.
                     Add hwDocsIfCmtsIPv6ToCmTable.
                     Added the leaf hwCmtsDownChannelSymbolRate for hwCmtsDownChannelTable.
                     Added the leaf hwCmtsSysCfgEQAMUtilizationAlarmThreshold for hwCmtsSysCfgTable.
                     Added the leaf hwDocsIfDownstreamChannelMode,hwDocsIfDownstreamChannelSymbolRate for hwDocsIfDownstreamChannelTable.
                     Added the leaf hwCmtsEQAMChannelUtilizationAlarmTrap for hwdocsIfCmtsTraps.
                     Added the leaf hwCmtsDsChannelIndex, hwCmtsDsChannelUtilization for hwcmtsTrapsVbOids.
                     "
       REVISION     "201401160000Z"
       DESCRIPTION  "V1.15, Add table hwCmtsServiceDomainTable, hwCmtsServiceDomainMappingTable and hwCmtsServiceDomainMemberTable."

       REVISION     "201312240000Z"
       DESCRIPTION  "V1.14, Modify the range of hwCmtsAuthKey from 1~80 to 0~80."

       REVISION     "201311210000Z"
       DESCRIPTION  "V1.13, added hwDocsIf3CmtsCmRegStatusSnmpProxyUpdateTime in hwDocsIf3CmtsCmRegStatusTable.
                     Added hwCmtsRemoteQueryControlTable for CMTS.
                     Added hwCmtsOverCmSpecAlarmTrap.
                     Added hwCmtsOverCmSpec20Num and hwCmtsOverCmSpec30Num in hwcmtsTrapsVbOids.
                     Added the leaf hwDocsIf3CmtsCmRegStatusDsChangeTimes for hwDocsIf3CmtsCmRegStatusTable.
                     Added the leaves hwDocsIf3CmtsCmUsStatusMinTxPower and hwDocsIf3CmtsCmUsStatusMaxTxPower for hwDocsIf3CmtsCmUsStatusTable.
                     Added hwDocsIf3CmtsCmRegStatusT1Timeouts, hwDocsIf3CmtsCmRegStatusT2Timeouts, hwDocsIf3CmtsCmUsStatusT3Timeouts,
                     hwDocsIf3CmtsCmUsStatusT4Timeouts and hwDocsIf3CmtsCmIGMPVersion for hwDocsIf3CmtsCmRemoteQueryTrap.
                     Added hwDocsIf3CmtsCmRegStatusT1Timeouts, hwDocsIf3CmtsCmRegStatusT2Timeouts, hwDocsIf3CmtsCmUsStatusT3Timeouts,
                     hwDocsIf3CmtsCmUsStatusT4Timeouts and hwDocsIf3CmtsCmIGMPVersion in hwcmtsTrapsVbOids.
                     Modify the range of hwCmtsSysCfgUnstableConnCmNumThreshold and hwCmtsSysCfgOfflineCmNumThreshold in hwCmtsSysCfgTable.
                     Added hwCmtsUsFftDataTable for CMTS.
                     Added the leaf hwDocsIf3CmtsCmRegStatusVoiceEnabled for hwDocsIf3CmtsCmRegStatusTable.
                     Added hwDocsIf3MdCfgTable.
                     Modify the max access of leaf hwdocsIfUsChannelPreEqEnable in hwdocsIfUpstreamChannelTable.
                     Modify the DESCRIPTION of hwDocsIf3CmtsCmRegStatusPreviousStatusValue.
                     Modify the range of leaf hwCmtsSpectrumGroupSecondaryModulationType1 and hwCmtsSpectrumGroupSecondaryModulationType2 in hwCmtsSpectrumGroupTable.
                     Modify the range of leaf hwDocsIfUpstreamChannelStatusModulationProfile in hwDocsIfUpstreamChannelStatusTable.
                     Add the leaf for hwdocsIfCmtsModulationTable: hwdocsIfCmtsModType."
                     
       REVISION     "201306160000Z"
       DESCRIPTION  "V1.12, Added the following leaves for hwDocsIf3CmtsCmRegStatusTable: hwDocsIf3CmtsCmRegStatusGoodCodeWords, hwDocsIf3CmtsCmRegStatusGoodCodeWords,
                    hwDocsIf3CmtsCmRegStatusUncorrectedErrorCodeWords, hwDocsIf3CmtsCmRegStatusValue, hwDocsIf3CmtsCmCtrlOperStatus, hwDocsIf3CmtsCmRegStatusRemoteQuery.
                    hwDocsIf3CmtsCmRegStatusPrimaryDsRxPower, hwDocsIf3CmtsCmRegStatusPrimaryDsSnr, hwDocsIf3CmtsCmRegStatusSysDesc, hwDocsIf3CmtsCmRegStatusPortIfIndex, 
                    hwDocsIf3CmtsCmRegStatusPrimaryUsTxTimingOffset, hwDocsIf3CmtsCmRegStatusOfflineTime, hwDocsIf3CmtsCmRegStatusPreviousStatusValue.
                    Added the following leaves for hwDocsIf3CmtsCmUsStatusTable: hwDocsIf3CmtsCmUsGoodCodewords, hwDocsIf3CmtsCmUsCorrectedErrorCodewords,
                    hwDocsIf3CmtsCmUsUncorrectedErrorCodewords, hwDocsIf3CmtsCmRegStatusPrimaryUs, hwDocsIf3CmtsCmRegStatusPrimaryUsRxPower, hwDocsIf3CmtsCmUsStatusTxTimingOffset
                    hwDocsIf3CmtsCmRegStatusPrimaryUsTxPower, hwDocsIf3CmtsCmRegStatusPrimaryDsTxPower, hwDocsIf3CmtsCmRegStatusPrimaryUsSnr.
                    Added the following leaves for hwCmtsUpChannelTable: hwCmtsUpChannelMaxDataRate, hwCmtsUpChannelRealTimeDataRate, hwCmtsUpChannel20CmDataRateSum, hwCmtsUpChannel30CmDataRateSum.
                    Added the table of hwCmtsDownChannelTable.
                    Added the following leaves for hwCmtsUpChannelCurrTable: hwCmtsUpChannelCurr15MStartTime, hwCmtsUpChannelCurr15MElapsedTime,
                    hwCmtsUpChannelCurr1DayStartTime, hwCmtsUpChannelCurr1DayElapsedTime.
                    Added the following leaves for hwCmtsChannelHist15MinTable: hwCmtsUpChannelHist15MStartTime, hwCmtsUpChannelHist15MElapsedTime, hwCmtsUpChannelHist15MValidityFlag.
                    Added the following leaves for hwCmtsUpChannelHist1DayTable: hwCmtsUpChannelHist1DayStartTime, hwCmtsUpChannelHist1DayElapsedTime, hwCmtsUpChannelHist1DayValidityFlag.
                    Added the following tables for CMTS: hwCmtsSysCfgTable,hwCmtsSnrDetectTable, hwCmtsCmCurrTable, hwCmtsCmHist15MinTable, hwDocsIf3CmtsCmCpeStatTable,
                    hwCmtsCmHist1DayTable hwCmtsCmStatThresholdTable, hwDocsIfCmtsIPToCmTable, hwCmtsMtaInfoTable, hwDocsIfUpstreamChannelStatusTable, hwCmtsLoadBalanceTable.
                    Added the following leaves for hwDocsIf3CmtsCmRegStatusTable: hwDocsIf3CmtsCmRegStatusValue, hwDocsIf3CmtsCmCtrlOperStatus, hwDocsIf3CmtsCmRegStatusRemoteQuery.
                    Added  hwDocsIf3CmtsCmRemoteQueryTrap, hwCmtsMassUnstableConnCmNum, hwCmtsMassOfflineCmNum and hwcmtsTrapsVbOids for CMTS. 
                    Added the following leaves for hwCmtsSpectrumGroupTable:
                    hwCmtsSpectrumGroupSecondaryModulationType1, hwCmtsSpectrumGroupSecondaryModulationType2,
                    hwCmtsSpectrumGroupChannelWidth, hwCmtsSpectrumGroupFirstSnr, hwCmtsSpectrumGroupSecondSnr,
                    hwCmtsSpectrumGroupProtectPower, hwCmtsSpectrumGroupPriority.
                    Added leaves hwdocsIfUsChannelPreEqEnable and hwDocsIfUpstreamChannelRxPower in table hwdocsIfUpstreamChannelTable.
                    Added leaf hwdocsLoadbal3GeneralGrpInitTech in table hwdocsLoadbal3GeneralGrpCfgTable.
                    Modify leaf hwdocsIfUsChanneHopReset in hwdocsIfUpstreamChannelTable.
                    Delete the value of these leaves:hwCmtsSpectrumGroupId,hwdocsIfUsChanneSpectrumGroupId.
                    Added the table of hwCmtsCmNumSummaryTable, hwDocsIfDownstreamChannelTable.
                    Added leaf hwDocsIf3CmtsCmCpeInfoDeviceDesc in table hwDocsIf3CmtsCmCpeInfoTable.
                    Modify the description of the leaf node hwCmtsCmRegRemoteStatus
                    Added the following leaves for hwDocsIf3CmtsCmDownChannelInfoTable: hwDocsIf3CmtsCmDownChannelInfoSnr, hwDocsIf3CmtsCmDownChannelInfoRxPower,"
                                                                
       REVISION     "201306010000Z"
       DESCRIPTION  "V1.11, Add hwCmtsCmTrafficTable for cm traffic.
                     Add the table of hwCmtsBundleTable, hwCmtsBundleMemberTable and hwCmtsBundleReservedVlanList.
                     Add the table of hwCmtsQosAdjustRuleTable, hwCmtsQosAdjustInfoTable, hwCmtsQosAdjustCancelTable and hwCmtsCmServiceFlowTable.
                     Add hwCmtsCmTrafficTable for cm traffic."

       REVISION     "201304150000Z"
       DESCRIPTION  "V1.10, Added the unit of node hwCmtsUpChannelSnr.
                     Add the table of hwCmtsAdmissionCtrlTable."

       REVISION     "201303300000Z"
       DESCRIPTION  "V1.09, Add object hwCmtsTrafficBurstConfigObject for traffic burst.
                     Add leaf hwCmtsTrafficBurstUpstreamEnable in object hwCmtsTrafficBurstConfigObject.
                     Add leaf hwCmtsTrafficBurstDownstreamEnable in object hwCmtsTrafficBurstConfigObject."

       REVISION     "201303210000Z"
       DESCRIPTION  "V1.08, Added the following tables for CMTS: hwCmtsCmOverCapaTable, hwCmtsAdmissionCtrlTypeTable,
                     hwCmtsAdmissionCtrlMappingTable, hwCmtsAdmissionCtrlPortBandwidthTable, hwCmtsAdmissionCtrlChannelBandwidthTable,
                     hwCmtsAdmissionCtrlStatisticsTable, hwCmtsMtaBasicTable."

       REVISION     "201303190000Z"
       DESCRIPTION  "V1.07, Add table hwPacketcableGateInfoTable and hwPacketcableGateStatisticsTable for PacketCable.
                     Add hwPacketCable1DotxSwitch, hwPacketCableMultimediaSwitch, hwPacketCableAuthorizeCommonMtaSwitch,
                     hwPacketCableMaxGateCount, hwPacketCable1DotxTimerT0, hwPacketCable1DotxTimerT1,
                     hwPacketCableMultimediaTimerT1, hwPacketCable1dotxSendSubscriberID in object hwPacketCableObject."

       REVISION     "201301310000Z"
       DESCRIPTION  "V1.06, Added the following table for CMTS: hwCmtsSpectrumGroupTable, hwdocsIfUpstreamChannelTable,
                     hwDocsIf3CmtsCmRegStatusTable, hwDocsIf3CmtsCmUsStatusTable, hwDocsIf3CmtsCmDownChannelInfoTable,
                     and hwDocsIf3CmtsCmCpeInfoTable."

       REVISION     "201302250000Z"
       DESCRIPTION  "V1.05, Added description of hwDocsCableModemMaxCpeNum."

       REVISION     "201212250000Z"
       DESCRIPTION  "V1.04, Added hwCmtsTraps objects."

       REVISION     "201212010000Z"
       DESCRIPTION  "V1.03, Added hwCmtsCfgTable to config tftp proxy option for CMTS."

       REVISION     "201211140000Z"
       DESCRIPTION  "V1.02, Added the following node for CMTS: hwDocsCableSchedulePriorityMappingMask, hwDocsCableModemMaxCpeNum."

       REVISION     "201207120000Z"
       DESCRIPTION  "V1.00, Initial version."
       ::= { huaweiUtility 180 }

   hwCmtsObjectMIB OBJECT IDENTIFIER ::= { hwCmtsMIB 1}
   hwCmtsTraps     OBJECT IDENTIFIER ::= { hwCmtsMIB 2 }
   hwcmtsTrapsVbOids      OBJECT IDENTIFIER ::= { hwCmtsMIB 3 }

   hwCmtsObject OBJECT IDENTIFIER ::= { hwCmtsObjectMIB  1}

   hwdocsIfCmtsTraps OBJECT IDENTIFIER ::= {hwCmtsTraps 1}
   hwdocsIfCmtsCommonTraps     OBJECT IDENTIFIER ::= { hwdocsIfCmtsTraps 0 }

   -- DOCSIS 3.0 OSSI specification

   DocsisVersion ::= TEXTUAL-CONVENTION
       STATUS          current
       DESCRIPTION
           "Indicates the DOCSIS Radio Frequency specification being
            referenced.
            'docsis10' indicates DOCSIS 1.0.
            'docsis11' indicates DOCSIS 1.1.
            'docsis20' indicates DOCSIS 2.0.
            'docsis30' indicates DOCSIS 3.0."
       REFERENCE
           "DOCSIS 3.0 MAC and Upper Layer Protocols Interface
            Specification CM-SP-MULPIv3.0-I03-070223, DOCSIS
            Version section of the Common Radio Frequency
            Interface Encodings Annex."
       SYNTAX        INTEGER {
            docsis10 (1),
            docsis11 (2),
            docsis20 (3),
            docsis30 (4)
       }

    -- Table hwCmtsUpChannelCurrTable
    hwCmtsUpChannelCurrTable OBJECT-TYPE
          SYNTAX     SEQUENCE OF HwCmtsUpChannelCurrEntry
          MAX-ACCESS not-accessible
          STATUS     current
          DESCRIPTION
               "Indicates the current statistics table of a CMTS upstream channel.
               The index of this table is ifIndex."
          ::= { hwCmtsObject 1 }

    hwCmtsUpChannelCurrEntry OBJECT-TYPE
          SYNTAX     HwCmtsUpChannelCurrEntry
          MAX-ACCESS not-accessible
          STATUS     current
          DESCRIPTION
               "Indicates the current statistics table of a CMTS upstream channel.
               The index of this entry is ifIndex."
          INDEX       { ifIndex }
          ::= { hwCmtsUpChannelCurrTable 1 }

    HwCmtsUpChannelCurrEntry ::=
          SEQUENCE {
                    hwCmtsUpChannelCurr15MUnerroredCodewords         Counter64,
                    hwCmtsUpChannelCurr15MCorrectedCodewords         Counter64,
                    hwCmtsUpChannelCurr15MUncorrectableCodewords     Counter64,
                    hwCmtsUpChannelCurr1DayUnerroredCodewords        Counter64,
                    hwCmtsUpChannelCurr1DayCorrectedCodewords        Counter64,
                    hwCmtsUpChannelCurr1DayUncorrectableCodewords    Counter64,
                    hwCmtsUpChannelEverBeforeUnerroredCodewords      Counter64,
                    hwCmtsUpChannelEverBeforeCorrectedCodewords      Counter64,
                    hwCmtsUpChannelEverBeforeUncorrectableCodewords  Counter64,
                    hwCmtsUpChannelCurr15MStartTime                  DateAndTime,
                    hwCmtsUpChannelCurr15MElapsedTime                Integer32,
                    hwCmtsUpChannelCurr1DayStartTime                 DateAndTime,
                    hwCmtsUpChannelCurr1DayElapsedTime               Integer32
                  }

    hwCmtsUpChannelCurr15MUnerroredCodewords OBJECT-TYPE
          SYNTAX     Counter64
          MAX-ACCESS read-only
          STATUS     current
          DESCRIPTION
               "Total number of unerrored codewords count during current 15 minutes."
          ::= { hwCmtsUpChannelCurrEntry 1 }

    hwCmtsUpChannelCurr15MCorrectedCodewords OBJECT-TYPE
          SYNTAX     Counter64
          MAX-ACCESS read-only
          STATUS     current
          DESCRIPTION
               "Total number of corrected codewords count during current 15 minutes."
          ::= { hwCmtsUpChannelCurrEntry 2 }

    hwCmtsUpChannelCurr15MUncorrectableCodewords OBJECT-TYPE
          SYNTAX     Counter64
          MAX-ACCESS read-only
          STATUS     current
          DESCRIPTION
               "Total number of uncorrectable codewords count during current 15 minutes."
          ::= { hwCmtsUpChannelCurrEntry 3 }

    hwCmtsUpChannelCurr1DayUnerroredCodewords OBJECT-TYPE
          SYNTAX     Counter64
          MAX-ACCESS read-only
          STATUS     current
          DESCRIPTION
               "Total number of unerrored codewords count during current day."
          ::= { hwCmtsUpChannelCurrEntry 4 }

    hwCmtsUpChannelCurr1DayCorrectedCodewords OBJECT-TYPE
          SYNTAX     Counter64
          MAX-ACCESS read-only
          STATUS     current
          DESCRIPTION
               "Total number of corrected codewords count during current day."
          ::= { hwCmtsUpChannelCurrEntry 5 }

    hwCmtsUpChannelCurr1DayUncorrectableCodewords OBJECT-TYPE
          SYNTAX     Counter64
          MAX-ACCESS read-only
          STATUS     current
          DESCRIPTION
               "Total number of uncorrectable codewords count during current day."
          ::= { hwCmtsUpChannelCurrEntry 6 }

    hwCmtsUpChannelEverBeforeUnerroredCodewords OBJECT-TYPE
          SYNTAX     Counter64
          MAX-ACCESS read-only
          STATUS     current
          DESCRIPTION
               "Total number of unerrored codewords count everbefore."
          ::= { hwCmtsUpChannelCurrEntry 7 }

    hwCmtsUpChannelEverBeforeCorrectedCodewords OBJECT-TYPE
          SYNTAX     Counter64
          MAX-ACCESS read-only
          STATUS     current
          DESCRIPTION
               "Total number of corrected codewords count everbefore."
          ::= { hwCmtsUpChannelCurrEntry 8 }

    hwCmtsUpChannelEverBeforeUncorrectableCodewords OBJECT-TYPE
          SYNTAX     Counter64
          MAX-ACCESS read-only
          STATUS     current
          DESCRIPTION
               "Total number of uncorrectable codewords count everbefore."
          ::= { hwCmtsUpChannelCurrEntry 9 }

   hwCmtsUpChannelCurr15MStartTime OBJECT-TYPE
          SYNTAX  DateAndTime
          MAX-ACCESS  read-only
          STATUS  current
          DESCRIPTION
                "
                Indicates the start time of the current 15-minute statistical period.
                "
          ::= { hwCmtsUpChannelCurrEntry 10 }


    hwCmtsUpChannelCurr15MElapsedTime OBJECT-TYPE
          SYNTAX  Integer32
          UNITS   "s"
          MAX-ACCESS  read-only
          STATUS  current
          DESCRIPTION
                "
                Indicates the elapsed time in the current 15-minute statistical period.
                "
          ::= { hwCmtsUpChannelCurrEntry 11 }

    hwCmtsUpChannelCurr1DayStartTime OBJECT-TYPE
          SYNTAX  DateAndTime
          MAX-ACCESS  read-only
          STATUS  current
          DESCRIPTION
                "
                Indicates the start time of the current 24-hour statistical period.
                "
          ::= { hwCmtsUpChannelCurrEntry 12 }


    hwCmtsUpChannelCurr1DayElapsedTime OBJECT-TYPE
          SYNTAX  Integer32
          UNITS   "s"
          MAX-ACCESS  read-only
          STATUS  current
          DESCRIPTION
                "
                Indicates the elapsed time in the current 24-hour statistical period.
                "
          ::= { hwCmtsUpChannelCurrEntry 13 }


    -- Table hwCmtsChannelHist15MinTable
    hwCmtsChannelHist15MinTable OBJECT-TYPE
          SYNTAX     SEQUENCE OF HwCmtsChannelHist15MinEntry
          MAX-ACCESS not-accessible
          STATUS     current
          DESCRIPTION
               "Indicates the statistics table of a CMTS upstream channel during history 15 minutes.
               The indexes of this table are ifIndex and hwCmtsUpChannelHist15MInterval."
          ::= { hwCmtsObject 2 }

    hwCmtsChannelHist15MinEntry OBJECT-TYPE
          SYNTAX     HwCmtsChannelHist15MinEntry
          MAX-ACCESS not-accessible
          STATUS     current
          DESCRIPTION
               "Indicates the statistics table of a CMTS upstream channel during history 15 minutes.
               The indexes of this entry are ifIndex and hwCmtsUpChannelHist15MInterval."
          INDEX       { ifIndex, hwCmtsUpChannelHist15MInterval }
          ::= { hwCmtsChannelHist15MinTable 1 }

    HwCmtsChannelHist15MinEntry ::=
          SEQUENCE {
                    hwCmtsUpChannelHist15MInterval               Integer32,
                    hwCmtsUpChannelHist15MUnerroredCodewords     Counter64,
                    hwCmtsUpChannelHist15MCorrectedCodewords     Counter64,
                    hwCmtsUpChannelHist15MUncorrectableCodewords Counter64,
                    hwCmtsUpChannelHist15MStartTime              DateAndTime,
                    hwCmtsUpChannelHist15MElapsedTime            Integer32,
                    hwCmtsUpChannelHist15MValidityFlag           Integer32
                  }

    hwCmtsUpChannelHist15MInterval OBJECT-TYPE
          SYNTAX  Integer32 (1..96)
                MAX-ACCESS  not-accessible
                STATUS  current
                DESCRIPTION
               "The type of the statistics table of a CMTS upstream channel during history 15 minutes,
                this leaf is essential."
          ::= { hwCmtsChannelHist15MinEntry 1 }

    hwCmtsUpChannelHist15MUnerroredCodewords OBJECT-TYPE
          SYNTAX     Counter64
          MAX-ACCESS read-only
          STATUS     current
          DESCRIPTION
               "Total number of unerrored codewords count during history 15 minutes."
          ::= { hwCmtsChannelHist15MinEntry 2 }

    hwCmtsUpChannelHist15MCorrectedCodewords OBJECT-TYPE
          SYNTAX     Counter64
          MAX-ACCESS read-only
          STATUS     current
          DESCRIPTION
               "Total number of corrected codewords count during history 15 minutes."
          ::= { hwCmtsChannelHist15MinEntry 3 }

    hwCmtsUpChannelHist15MUncorrectableCodewords OBJECT-TYPE
          SYNTAX     Counter64
          MAX-ACCESS read-only
          STATUS     current
          DESCRIPTION
               "Total number of uncorrectable codewords count during history 15 minutes."
          ::= { hwCmtsChannelHist15MinEntry 4 }

    hwCmtsUpChannelHist15MStartTime OBJECT-TYPE
          SYNTAX  DateAndTime
          MAX-ACCESS  read-only
          STATUS  current
          DESCRIPTION
                "
                Indicates the start time of a statistical period.
                "
          ::= { hwCmtsChannelHist15MinEntry 5 }

    hwCmtsUpChannelHist15MElapsedTime OBJECT-TYPE
          SYNTAX  Integer32
          UNITS   "s"
          MAX-ACCESS  read-only
          STATUS  current
          DESCRIPTION
                "
                Indicates the elapsed time in a statistical period.
                "
          ::= { hwCmtsChannelHist15MinEntry 6 }

    hwCmtsUpChannelHist15MValidityFlag OBJECT-TYPE
          SYNTAX  Integer32 (1..2)
          MAX-ACCESS  read-only
          STATUS  current
          DESCRIPTION
                "
                Indicates the flag for statistical information.
                Options:
                1-Yes
                2-No
                "
          ::= { hwCmtsChannelHist15MinEntry 7 }

    -- Table hwCmtsUpChannelHist1DayTable
    hwCmtsUpChannelHist1DayTable OBJECT-TYPE
          SYNTAX     SEQUENCE OF HwCmtsUpChannelHist1DayEntry
          MAX-ACCESS not-accessible
          STATUS     current
          DESCRIPTION
               "Indicates the statistics table of a CMTS upstream channel during history 1 day.
               The indexes of this table are ifIndex and hwCmtsUpChannelHist1DayInterval."
          ::= { hwCmtsObject 3 }

    hwCmtsUpChannelHist1DayEntry OBJECT-TYPE
          SYNTAX     HwCmtsUpChannelHist1DayEntry
          MAX-ACCESS not-accessible
          STATUS     current
          DESCRIPTION
               "Indicates the statistics table of a CMTS upstream channel during history 1 day.
               The indexes of this entry are ifIndex and hwCmtsUpChannelHist1DayInterval."
          INDEX       { ifIndex, hwCmtsUpChannelHist1DayInterval }
          ::= { hwCmtsUpChannelHist1DayTable 1 }

    HwCmtsUpChannelHist1DayEntry ::=
          SEQUENCE {
                    hwCmtsUpChannelHist1DayInterval                Integer32,
                    hwCmtsUpChannelHist1DayUnerroredCodewords      Counter64,
                    hwCmtsUpChannelHist1DayCorrectedCodewords        Counter64,
                    hwCmtsUpChannelHist1DayUncorrectableCodewords  Counter64,
                    hwCmtsUpChannelHist1DayStartTime               DateAndTime,
                    hwCmtsUpChannelHist1DayElapsedTime             Integer32,
                    hwCmtsUpChannelHist1DayValidityFlag            Integer32
                  }

    hwCmtsUpChannelHist1DayInterval OBJECT-TYPE
          SYNTAX  Integer32 (1..30)
                MAX-ACCESS  not-accessible
                STATUS  current
                DESCRIPTION
               "The type of the statistics table of a CMTS upstream channel during history 1 day,
                this leaf is essential."
          ::= { hwCmtsUpChannelHist1DayEntry 1 }

    hwCmtsUpChannelHist1DayUnerroredCodewords OBJECT-TYPE
          SYNTAX     Counter64
          MAX-ACCESS read-only
          STATUS     current
          DESCRIPTION
               "Total number of unerrored codewords count during history 1 day."
          ::= { hwCmtsUpChannelHist1DayEntry 2 }

    hwCmtsUpChannelHist1DayCorrectedCodewords OBJECT-TYPE
          SYNTAX     Counter64
          MAX-ACCESS read-only
          STATUS     current
          DESCRIPTION
               "Total number of corrected codewords count during history 1 day."
          ::= { hwCmtsUpChannelHist1DayEntry 3 }

    hwCmtsUpChannelHist1DayUncorrectableCodewords OBJECT-TYPE
          SYNTAX     Counter64
          MAX-ACCESS read-only
          STATUS     current
          DESCRIPTION
               "Total number of uncorrectable codewords count during history 1 day."
          ::= { hwCmtsUpChannelHist1DayEntry 4 }

    hwCmtsUpChannelHist1DayStartTime OBJECT-TYPE
          SYNTAX  DateAndTime
          MAX-ACCESS  read-only
          STATUS  current
          DESCRIPTION
                "
                Indicates the start time of a statistical period.
                "
          ::= { hwCmtsUpChannelHist1DayEntry 5 }

    hwCmtsUpChannelHist1DayElapsedTime OBJECT-TYPE
          SYNTAX  Integer32
          UNITS   "s"
          MAX-ACCESS  read-only
          STATUS  current
          DESCRIPTION
                "
                Indicates the elapsed time in a statistical period.
                "
          ::= { hwCmtsUpChannelHist1DayEntry 6 }

    hwCmtsUpChannelHist1DayValidityFlag OBJECT-TYPE
          SYNTAX  Integer32 (1..2)
          MAX-ACCESS  read-only
          STATUS  current
          DESCRIPTION
                "
                Indicates the flag for statistical information.
                Options:
                1-Yes
                2-No
                "
          ::= { hwCmtsUpChannelHist1DayEntry 7 }

    -- Table hwCmtsUpChannelTable
    hwCmtsUpChannelTable OBJECT-TYPE
          SYNTAX     SEQUENCE OF HwCmtsUpChannelEntry
          MAX-ACCESS not-accessible
          STATUS     current
          DESCRIPTION
               "Indicates the signal quality of a CMTS upstream channel.
               The index of this table is ifIndex."
          ::= { hwCmtsObject 4 }

    hwCmtsUpChannelEntry OBJECT-TYPE
          SYNTAX     HwCmtsUpChannelEntry
          MAX-ACCESS not-accessible
          STATUS     current
          DESCRIPTION
               "Indicates the signal quality of a CMTS upstream channel.
               The index of this entry is ifIndex."
          INDEX       { ifIndex }
          ::= { hwCmtsUpChannelTable 1 }

    HwCmtsUpChannelEntry ::=
          SEQUENCE {
                    hwCmtsUpChannelContentionFlag        INTEGER,
                    hwCmtsUpChannelSnr                   Integer32,
                    hwCmtsChannelMicroReflection         Integer32,
                    hwCmtsUpChannelMaxDataRate           Integer32,
                    hwCmtsUpChannelRealTimeDataRate      Integer32,
                    hwCmtsUpChannelModulationType        INTEGER,
                    hwCmtsUpChannel20CmDataRateSum       Unsigned32,
                    hwCmtsUpChannel30CmDataRateSum       Unsigned32,
                    hwCmtsUpChannelNotActiveReason       INTEGER,
                    hwCmtsUpChannelPer                   Integer32,
                    hwCmtsUpChannel20CmUtilization       Counter32,
                    hwCmtsUpChannel30CmUtilization       Counter32,
                    hwCmtsUpChannelMinSnr                Integer32,
                    hwCmtsUpChannelMaxSnr                Integer32,
                    hwCmtsUpChannel31CmDataRateSum       Unsigned32,
                    hwCmtsUpChannel31CmUtilization       Counter32
                  }

    hwCmtsUpChannelContentionFlag OBJECT-TYPE
          SYNTAX     INTEGER
              {
              no(0),
              yes(1)
              }
          MAX-ACCESS read-only
          STATUS     current
          DESCRIPTION
               "Status of contention intervals for an upstream channel.
               Options:
               1. no(0) - No contention interval exists
               2. yes(1) - Contention intervals exist
               Default: no(0)
               "
          ::= { hwCmtsUpChannelEntry 1 }

    hwCmtsUpChannelSnr OBJECT-TYPE
          SYNTAX     Integer32
          UNITS       "0.1dB"
          MAX-ACCESS read-only
          STATUS     current
          DESCRIPTION
               "The SNR of a upstream channel.
               -1 represents invalid value.
               "
          ::= { hwCmtsUpChannelEntry 2 }

    hwCmtsChannelMicroReflection OBJECT-TYPE
          SYNTAX     Integer32
          UNITS       "-dBc"
          MAX-ACCESS read-only
          STATUS     current
          DESCRIPTION
               "The total number Micro-reflections of a upstream channel.
               -1 represents invalid value."
          ::= { hwCmtsUpChannelEntry 3 }

    hwCmtsUpChannelMaxDataRate OBJECT-TYPE
          SYNTAX     Integer32
          UNITS      "kbps"
          MAX-ACCESS read-only
          STATUS     current
          DESCRIPTION
               "The max data rate.
               -1 represents invalid value.
               "
          ::= { hwCmtsUpChannelEntry 4 }

    hwCmtsUpChannelRealTimeDataRate OBJECT-TYPE
          SYNTAX     Integer32
          UNITS      "kbps"
          MAX-ACCESS read-only
          STATUS     current
          DESCRIPTION
               "The real time data rate.
               -1 represents invalid value.
               "
          ::= { hwCmtsUpChannelEntry 5 }

    hwCmtsUpChannelModulationType OBJECT-TYPE
          SYNTAX     INTEGER
              {
              other(1),
              qpsk(2),
              qam16(3),
              qam8(4),
              qam32(5),
              qam64(6),
              qam128(7),
              qam256(8)
              }
          MAX-ACCESS read-only
          STATUS     current
          DESCRIPTION
               "
               The modulation type of up channel.
               Options:
               1. other(1) - Indicates the other modulation type
               2. qpsk(2) - QPSK
               3. qam16(3) - QAM16
               4. qam8(4) - QAM8
               5. qam32(5) - QAM32
               6. qam64(6) - QAM64
               7. qam128(7) - QAM128
               8. qam256(8) - QAM256
               Default: qpsk(2)
               "
          ::= { hwCmtsUpChannelEntry 6 }

    hwCmtsUpChannel20CmDataRateSum OBJECT-TYPE
          SYNTAX     Unsigned32
          UNITS      "kbps"
          MAX-ACCESS read-only
          STATUS     current
          DESCRIPTION
               "Rate sum of all DOCSIS 2.0 cable modem on the channel.
                0 represents invalid value."
          ::= { hwCmtsUpChannelEntry 7 }

    hwCmtsUpChannel30CmDataRateSum OBJECT-TYPE
          SYNTAX     Unsigned32
          UNITS      "kbps"
          MAX-ACCESS read-only
          STATUS     current
          DESCRIPTION
               "Rate sum of all DOCSIS 3.0 cable modem on the channel.
                0 represents invalid value."
          ::= { hwCmtsUpChannelEntry 8 }
          
    hwCmtsUpChannelNotActiveReason OBJECT-TYPE
          SYNTAX     INTEGER
              {
              other(1),
              noLicense(2),
              channelModErr(3),
              exceedMaxChannelNum(4),
              exceedMaxFreq(5),
              exceedMaxFreqSpan(6),
              notSupportScdma(8),
              exceedMaxUsSGNum(10),
              notSupportFreqSpan65MHz(19),
              invalid(-1)
              }
          MAX-ACCESS read-only
          STATUS     current
          DESCRIPTION
               "
               The reason of up channel not active.
               Options:
               1. other(1) - Other reason                   
               2. noLicense(2) - No license                 
               3. channelModErr(3) - Channel mode error            
               4. exceedMaxChannelNum(4) - Channel ID exceeds actual capability      
               5. exceedMaxFreq(5) - The channel frequency exceeds actual capability             
               6. exceedMaxFreqSpan(6) - Exceed maximum frequency span    
               7. notSupportScdma(8) - Not support scdma channel type   
               8. exceedMaxUsSGNum(10) - Exceed maximum upstream service group number
               9. notSupportFreqSpan65MHz(19) - The channel center frequency does not 
                                                meet spectrum span requirements
               10. invalid(-1) - Indicates the up channel is active               
               invalid(-1) represents invalid value.
               "  
          ::= { hwCmtsUpChannelEntry 9 }

    hwCmtsUpChannelPer OBJECT-TYPE
          SYNTAX     Integer32
          UNITS      "0.00001"
          MAX-ACCESS read-only
          STATUS     current
          DESCRIPTION
               "
               The rate of package error received on the up channels.
               -1 represents invalid value.
               "  
          ::= { hwCmtsUpChannelEntry 10 }

    hwCmtsUpChannel20CmUtilization OBJECT-TYPE
          SYNTAX     Counter32
          UNITS      "%"
          MAX-ACCESS read-only
          STATUS     current
          DESCRIPTION
               "
               Traffic ratio of DOCSIS 2.0 on the upstream channel. 
               DOCSIS 2.0 traffic ratio on the upstream channel = All DOCSIS 2.0 service traffic on the upstream channel/Capacity of the upstream channel.
               0 represents invalid value.
               "  
          ::= { hwCmtsUpChannelEntry 11 }
                    
    hwCmtsUpChannel30CmUtilization OBJECT-TYPE
          SYNTAX     Counter32
          UNITS      "%"
          MAX-ACCESS read-only
          STATUS     current
          DESCRIPTION
               "
               Traffic ratio of DOCSIS 3.0 on the upstream channel. 
               DOCSIS 3.0 traffic ratio on the upstream channel = All DOCSIS 3.0 service traffic on the upstream channel/Capacity of the upstream channel.
               0 represents invalid value.
               "  
          ::= { hwCmtsUpChannelEntry 12 }
          
    hwCmtsUpChannelMinSnr OBJECT-TYPE
          SYNTAX     Integer32
          UNITS       "0.1dB"
          MAX-ACCESS read-only
          STATUS     current
          DESCRIPTION
               "The minimum SNR of a upstream channel. 
               -1 represents invalid value."
          ::= { hwCmtsUpChannelEntry 13 } 
           
    hwCmtsUpChannelMaxSnr OBJECT-TYPE
          SYNTAX     Integer32
          UNITS       "0.1dB"
          MAX-ACCESS read-only
          STATUS     current
          DESCRIPTION
               "The maximum SNR of a upstream channel. 
               -1 represents invalid value."
          ::= { hwCmtsUpChannelEntry 14 }  
          
    hwCmtsUpChannel31CmDataRateSum OBJECT-TYPE
          SYNTAX     Unsigned32
          UNITS      "kbps"
          MAX-ACCESS read-only
          STATUS     current
          DESCRIPTION
               "Rate sum of all DOCSIS 3.1 cable modem on the upstream channel.
                0 represents invalid value."
          ::= { hwCmtsUpChannelEntry 15 } 
          
    hwCmtsUpChannel31CmUtilization OBJECT-TYPE
          SYNTAX     Counter32
          UNITS      "%"
          MAX-ACCESS read-only
          STATUS     current
          DESCRIPTION
               "
               Traffic ratio of DOCSIS 3.1 on the upstream channel. 
               DOCSIS 3.1 traffic ratio on the upstream channel = All DOCSIS 3.1 service traffic on the upstream channel/Capacity of the upstream channel.
               0 represents invalid value.
               "  
          ::= { hwCmtsUpChannelEntry 16 }
                           
    -- Table hwdocsIfCmtsModulationTable
    hwdocsIfCmtsModulationTable OBJECT-TYPE
          SYNTAX     SEQUENCE OF HwdocsIfCmtsModulationEntry
          MAX-ACCESS not-accessible
          STATUS     current
          DESCRIPTION
               "Indicates the description of a Channel Modulation profile.
               The indexes of this table are docsIfCmtsModIndex and docsIfCmtsModIntervalUsageCode."
          ::= { hwCmtsObject 5 }

    hwdocsIfCmtsModulationEntry OBJECT-TYPE
          SYNTAX     HwdocsIfCmtsModulationEntry
          MAX-ACCESS not-accessible
          STATUS     current
          DESCRIPTION
               "Indicates the description of a Channel Modulation profile.
               The indexes of this entry are docsIfCmtsModIndex and docsIfCmtsModIntervalUsageCode."
          INDEX       { docsIfCmtsModIndex, docsIfCmtsModIntervalUsageCode }
          ::= { hwdocsIfCmtsModulationTable 1 }

    HwdocsIfCmtsModulationEntry ::=
          SEQUENCE {
                    hwdocsIfCmtsModDescription        OCTET STRING,
                    hwdocsIfCmtsModType               INTEGER,
                    hwdocsIfCmtsModGuardTimeSize      Integer32,
                    hwdocsIfCmtsBasedModIndex         Integer32
                   }

    hwdocsIfCmtsModDescription OBJECT-TYPE
          SYNTAX  OCTET STRING (SIZE (1..32))
          MAX-ACCESS  read-write
          STATUS  current
          DESCRIPTION
                "The Channel Modulation description."
          ::= { hwdocsIfCmtsModulationEntry 1 }
          
    hwdocsIfCmtsModType OBJECT-TYPE
        SYNTAX      INTEGER {
            other(1),
            qpsk(2),
            qam16(3),
            qam8(4),
            qam32(5),
            qam64(6),
            qam128(7),
            qam256(8)
        }
        MAX-ACCESS  read-write
        STATUS      current
        DESCRIPTION
            "The modulation type used on this channel.  Returns
             other(1) if the modulation type is not
             qpsk, qam16, qam8, qam32, qam64, qam128 or qam256.
             Type qam128 is used for SCDMA channels only.
             See the reference for the modulation profiles
             implied by different modulation types.
             Options:
             1.other(1)- Returns other(1) if the modulation type is not qpsk, qam16, qam8, qam32, qam64, qam128 or qam256
             2.qpsk(2) - qpsk
             3.qam16(3) - qam16
             4.qam8(4) - qam8
             5.qam32(5) - qam32
             6.qam64(6) - qam64
             7.qam128(7)- qam128
             8.qam256(8)- qam256"
        REFERENCE
            "Data-Over-Cable Service Interface Specifications: Radio
             Frequency Interface Specification SP-RFIv2.0-I10-051209,
             Tables 6-7, and 8-19."
        DEFVAL { qpsk }
        ::= { hwdocsIfCmtsModulationEntry 2 }

    hwdocsIfCmtsModGuardTimeSize OBJECT-TYPE
        SYNTAX      Integer32 (-1..255)
        UNITS       "Symbol-times"
        MAX-ACCESS  read-write
        STATUS      current
        DESCRIPTION
            "The number of symbol-times that MUST follow the end of
             this channel's burst.  Default value is the minimum time
             needed by the implementation for this modulation profile.
             If hwdocsIfCmtsModGuardTimeSize is -1, this parameter is invalid."
        REFERENCE
            "Data-Over-Cable Service Interface Specifications: Radio
             Frequency Interface Specification SP-RFIv2.0-I10-051209,
             Tables 6-7, and 8-19."
        ::= { hwdocsIfCmtsModulationEntry 3 }
        
    hwdocsIfCmtsBasedModIndex OBJECT-TYPE
        SYNTAX      Integer32 (-1|1..48)
        MAX-ACCESS  read-write
        STATUS      current
        DESCRIPTION
            "Indicates the basic modulation profile index.
             The basic modulation profile index must be the preconfigured modulation profile.
             The new modulation profile initialization is based upon the basic modulation profile.
             If hwdocsIfCmtsBasedModIndex is -1, this parameter is invalid."
        ::= { hwdocsIfCmtsModulationEntry 4 }
        
  -- Table hwdocsLoadbal3GeneralGrpCfgTable
    hwdocsLoadbal3GeneralGrpCfgTable OBJECT-TYPE
          SYNTAX     SEQUENCE OF HwdocsLoadbal3GeneralGrpCfgEntry
          MAX-ACCESS not-accessible
          STATUS     current
          DESCRIPTION
               "Indicates the method of a Load Balancing Group.
               The indexes of this table are ifIndex and docsLoadbal3GeneralGrpCfgNodeName."
          ::= { hwCmtsObject 6 }

    hwdocsLoadbal3GeneralGrpCfgEntry OBJECT-TYPE
          SYNTAX     HwdocsLoadbal3GeneralGrpCfgEntry
          MAX-ACCESS not-accessible
          STATUS     current
          DESCRIPTION
               "Indicates the method of a Load Balancing Group.
               The indexes of this entry are ifIndex and docsLoadbal3GeneralGrpCfgNodeName."
          INDEX       { ifIndex, docsLoadbal3GeneralGrpCfgNodeName }
          ::= { hwdocsLoadbal3GeneralGrpCfgTable 1 }

    HwdocsLoadbal3GeneralGrpCfgEntry ::=
          SEQUENCE {
                    hwdocsLoadbal3GeneralGrpMethod        INTEGER,
                    hwdocsLoadbal3GeneralGrpInitTech      BITS,
                    hwdocsLoadbal3GeneralGrpUpStreamMethod     INTEGER,
                    hwdocsLoadbal3GeneralGrpDownStreamMethod   INTEGER
                   }

    hwdocsLoadbal3GeneralGrpMethod OBJECT-TYPE
          SYNTAX  INTEGER {
                           cm(1),
                           flow(2),
                           utilization(3)
                          }
          MAX-ACCESS  read-write
          STATUS  current
          DESCRIPTION
                "The method of a Load Balancing Group.
                Options:
                1. cm(1) - Load balancing based on the number of CMs
                2. flow(2) - Load balancing based on service flow bandwidth
                3. utilization(3) - Load balancing based on the bandwidth usage of upstream channels
                Default value: 2
                "
          ::= { hwdocsLoadbal3GeneralGrpCfgEntry 1 }

    hwdocsLoadbal3GeneralGrpInitTech OBJECT-TYPE
          SYNTAX  BITS {
            reInit(0),
            broadcast(1),
            unicast(2),
            initRang(3),
            direct(4)
          }
          MAX-ACCESS  read-write
          STATUS  current
          DESCRIPTION
                "This attribute defines the load balancing initialization
                technique for the General Load Balancing Group associated with this instance.
                Options:
                0 - reinitializeMac(Reinitialize the MAC)
                1 - broadcastInitRanging(Perform broadcast initial ranging on new channel before normal operation)
                2 - unicastInitRanging(Perform unicast ranging on new channel before normal operation)
                3 - initRanging(Perform either broadcast or unicast ranging on new channel before normal operation)
                4 - direct(Use the new channel(s) directly without reinitializing or ranging)
                Default value: 1
                "
          ::= { hwdocsLoadbal3GeneralGrpCfgEntry 2 }

    hwdocsLoadbal3GeneralGrpUpStreamMethod OBJECT-TYPE
          SYNTAX  INTEGER {
                           cm(1),
                           flow(2),
                           utilization(3)
                          }
          MAX-ACCESS  read-write
          STATUS  current
          DESCRIPTION
                "The method of a upstream Load Balancing Group.
                Options:
                1. cm(1) - Load balancing based on the number of CMs
                2. flow(2) - Load balancing based on service flow bandwidth
                3. utilization(3) - Load balancing based on the bandwidth usage of upstream channels
                Default value: 2
                "
          ::= { hwdocsLoadbal3GeneralGrpCfgEntry 3 }

    hwdocsLoadbal3GeneralGrpDownStreamMethod OBJECT-TYPE
          SYNTAX  INTEGER {
                           cm(1),
                           flow(2),
                           utilization(3)
                          }
          MAX-ACCESS  read-write
          STATUS  current
          DESCRIPTION
                "The method of a downstream Load Balancing Group.
                Options:
                1. cm(1) - Load balancing based on the number of CMs
                2. flow(2) - Load balancing based on service flow bandwidth
                3. utilization(3) - Load balancing based on the bandwidth usage of upstream channels
                Default value: 2
                "
          ::= { hwdocsLoadbal3GeneralGrpCfgEntry 4 }

        hwDocsCableSchedulePriorityMappingMask OBJECT-TYPE
                SYNTAX Integer32 (0..125239296)
                MAX-ACCESS read-write
                STATUS current
                DESCRIPTION
                       "The mapping mask of schedule type (RTPS, UGS-AD, UGS) and priority of 802.1p of upstream.
                        Each four bits of mask defines the priority of one schedule type:
                        0000 0110 0101 0100 0000 0000 0000 0000
                        7     6    5    4    3    2    1   0
                        Definition of schedule type:
                        0-3, reserved
                        4, RTPS
                        5, UGS-AD
                        6, UGS
                        7, reserved
                        Definition of 802.1p priority: 0~7
                        Default: 106168320
                        "
                ::= { hwCmtsObject 7 }

        hwDocsCableModemMaxCpeNum OBJECT-TYPE
                SYNTAX Unsigned32 (1..8 | 4294967295)
                MAX-ACCESS read-write
                STATUS current
                DESCRIPTION
                       "The max CPE number on CM of CMTS.
                        The range of max CPE is 1 to 8.
                        4294967295 indicates no limit on the max CPE number.
                        "
                ::= { hwCmtsObject 8 }

    -- Table hwCmtsCfgTable
    hwCmtsCfgTable OBJECT-TYPE
          SYNTAX     SEQUENCE OF HwCmtsCfgEntry
          MAX-ACCESS not-accessible
          STATUS     current
          DESCRIPTION
               "The CMTS configuration table.
                The index of this table is ifIndex."
          ::= { hwCmtsObject 9 }

    hwCmtsCfgEntry OBJECT-TYPE
          SYNTAX     HwCmtsCfgEntry
          MAX-ACCESS not-accessible
          STATUS     current
          DESCRIPTION
               "The CMTS configuration table.
                The index of this entry is ifIndex."
          INDEX       { ifIndex }
          ::= { hwCmtsCfgTable 1 }

    HwCmtsCfgEntry ::=
          SEQUENCE {
                    hwCmtsProxyOption    INTEGER,
                    hwCmtsAuthKey        OCTET STRING
                   }

    hwCmtsProxyOption OBJECT-TYPE
          SYNTAX  INTEGER
              {
                  none(1),
                  mac(2),
                  ip(3)
              }
          MAX-ACCESS  read-write
          STATUS  current
          DESCRIPTION
                "
                Tftp proxy option. This attribute instructs the CMTS to insert the source
                IP address and/or MAC address of received TFTP packets into the TFTP option
                fields before forwarding the packets to the Config File server.
                Options:
                1. none(1) - With none TFTP option
                2. mac(2) - TFTP option with MAC address
                3. ip(3) -  TFTP option with IP address
                Default value: none(1)
                "
          ::= { hwCmtsCfgEntry 1 }

    hwCmtsAuthKey OBJECT-TYPE
          SYNTAX  OCTET STRING (SIZE (0..80))
          MAX-ACCESS  read-write
          STATUS  current
          DESCRIPTION
                "MIC authentication key.The key must be plain text consists of 2 to 80 characters.
                 Setting the key to 0 or an empty character string indicates that the current authentication key is deleted.
                "
          ::= { hwCmtsCfgEntry 2 }

    -- Table hwCmtsLoadBalanceTable begin
    hwCmtsLoadBalanceTable OBJECT-TYPE
          SYNTAX     SEQUENCE OF HwCmtsLoadBalanceEntry
          MAX-ACCESS not-accessible
          STATUS     current
          DESCRIPTION
               "The CMTS load balance parameter config table.
               The index of this table is ifIndex."
          ::= { hwCmtsObject 10 }

    hwCmtsLoadBalanceEntry OBJECT-TYPE
          SYNTAX     HwCmtsLoadBalanceEntry
          MAX-ACCESS not-accessible
          STATUS     current
          DESCRIPTION
               "The CMTS load balance parameter config table.
               The index of this entry is ifIndex."
          INDEX       { ifIndex }
          ::= { hwCmtsLoadBalanceTable 1 }

    HwCmtsLoadBalanceEntry ::=
          SEQUENCE {
                    hwCmtsLoadBalanceMaxMoveModems             Integer32,
                    hwCmtsLoadBalanceTriggerThreshold          Integer32,
                    hwCmtsLoadBalanceDifferenceThreshold       Integer32,
                    hwCmtsLoadBalanceCMMoveInterval            Integer32,
                    hwCmtsLoadBalanceNumofPeriod               Integer32,
                    hwCmtsLoadBalanceRangeOverrideMode         INTEGER,
                    hwCmtsLoadBalanceCmNumDifferenceThreshold  Integer32,
                    hwCmtsLoadBalanceDifferenceThresholdD3     Integer32,
                    hwCmtsLoadBalanceStaticDynamicThreshold    Integer32,
                    hwCmtsLoadBalanceDynamicStaticThreshold    Integer32                    
                   }

    hwCmtsLoadBalanceMaxMoveModems OBJECT-TYPE
          SYNTAX  Integer32 (1..32)
                MAX-ACCESS  read-write
                STATUS  current
                DESCRIPTION
               "Indicates maximum number of CMs adjusting to different channels during a period.
                Default value:32"
          ::= { hwCmtsLoadBalanceEntry 1 }

    hwCmtsLoadBalanceTriggerThreshold OBJECT-TYPE
          SYNTAX  Integer32 (1..100)
                MAX-ACCESS  read-write
                STATUS  current
                DESCRIPTION
               "Indicates the threshold for the channel bandwidth usage that triggers load balancing.
                Default value:60"
          ::= { hwCmtsLoadBalanceEntry 2 }


    hwCmtsLoadBalanceDifferenceThreshold OBJECT-TYPE
          SYNTAX  Integer32 (1..100)
          UNITS       "%"
                MAX-ACCESS  read-write
                STATUS  current
                DESCRIPTION
               "Indicates the threshold for channel bandwidth usage difference of DOCSIS 2.0 CM.
                Default value:10"
          ::= { hwCmtsLoadBalanceEntry 3 }

    hwCmtsLoadBalanceCMMoveInterval OBJECT-TYPE
          SYNTAX  Integer32 (60..86400)
          UNITS   "s"
                MAX-ACCESS  read-write
                STATUS  current
                DESCRIPTION
                "Indicates the minimum interval for CM adjusting to different channel.
                 Default value:240"
          ::= { hwCmtsLoadBalanceEntry 4 }

    hwCmtsLoadBalanceNumofPeriod OBJECT-TYPE
          SYNTAX  Integer32 (1..4)
                MAX-ACCESS  read-write
                STATUS  current
                DESCRIPTION
               "Indicates the period number for calculating the channel bandwidth usage.
                Default value:2"
          ::= { hwCmtsLoadBalanceEntry 5 }
    
    hwCmtsLoadBalanceRangeOverrideMode OBJECT-TYPE
          SYNTAX  INTEGER
              {
                  enable(1),
                  disable(2)
              }
          MAX-ACCESS  read-write
          STATUS  current
          DESCRIPTION
               "The switch for the ranging override.
                Options:
                1. enable(1) - enable the ranging channel override mode
                2. disable(2) - disable the ranging channel override mode
                Default value: disable(2)"
          ::= { hwCmtsLoadBalanceEntry 6 }
          
    hwCmtsLoadBalanceCmNumDifferenceThreshold OBJECT-TYPE
          SYNTAX  Integer32 (1..100)
          MAX-ACCESS  read-write
          STATUS  current
          DESCRIPTION
               "Indicates the threshold for CM number difference between channels."
          DEFVAL   { 5 }
          ::= { hwCmtsLoadBalanceEntry 7 }
          
    hwCmtsLoadBalanceDifferenceThresholdD3 OBJECT-TYPE
          SYNTAX  Integer32 (1..100)
          UNITS       "%"
                MAX-ACCESS  read-write
                STATUS  current
                DESCRIPTION
               "Indicates the threshold for channel bandwidth usage difference of DOCSIS 3.x CM.
                Default value:1"
          ::= { hwCmtsLoadBalanceEntry 8 }

    hwCmtsLoadBalanceStaticDynamicThreshold OBJECT-TYPE 
          SYNTAX  Integer32 (1..100)
          UNITS       "%"
                MAX-ACCESS  read-write
                STATUS  current
                DESCRIPTION
               "Indicates the switch threshold from static to dynamic.
                Default value:20"
          ::= { hwCmtsLoadBalanceEntry 9 }
          
    hwCmtsLoadBalanceDynamicStaticThreshold OBJECT-TYPE
          SYNTAX  Integer32 (1..100)
          UNITS       "%"
                MAX-ACCESS  read-write
                STATUS  current
                DESCRIPTION
               "Indicates the switch threshold from dynamic to static.
                Default value:10"
          ::= { hwCmtsLoadBalanceEntry 10 }          
    -- Table hwCmtsLoadBalanceTable  end

    hwCmtsAccessEqamObject OBJECT IDENTIFIER ::= { hwCmtsObject  19}

   -- Table hwCmtsEqamChannelTable
    hwCmtsEqamChannelTable OBJECT-TYPE
          SYNTAX     SEQUENCE OF HwCmtsEqamChannelEntry
          MAX-ACCESS not-accessible
          STATUS     current
          DESCRIPTION
               "This table describes the attributes of EQAM channels.
                The index of this table is ifIndex."
          ::= { hwCmtsAccessEqamObject 1 }

    hwCmtsEqamChannelEntry OBJECT-TYPE
          SYNTAX     HwCmtsEqamChannelEntry
          MAX-ACCESS not-accessible
          STATUS     current
          DESCRIPTION
               "This table describes the attributes of EQAM channels.
               The index of this entry is ifIndex."
          INDEX       { ifIndex }
          ::= { hwCmtsEqamChannelTable 1 }

    HwCmtsEqamChannelEntry ::=
          SEQUENCE {
                    hwCmtsEqamChannelId                    Integer32,
                    hwCmtsEqamChannelFrequency             Integer32,
                    hwCmtsEqamChannelModulation            INTEGER,
                    hwCmtsEqamChannelSymbolRate            INTEGER,
                    hwCmtsEqamChannelInterleaveDepth       INTEGER,
                    hwCmtsEqamChannelRfPower               Integer32,
                    hwCmtsEqamChannelAdminStatus           INTEGER,
                    hwCmtsEqamChannelOperStatus            INTEGER,
                    hwCmtsEqamChannelNotActiveReason       INTEGER
                   }

    hwCmtsEqamChannelId OBJECT-TYPE
          SYNTAX  Integer32 (1..254)
          MAX-ACCESS  read-only
          STATUS  current
          DESCRIPTION
                "The EQAM channel ID.
                 Range: 1..254
                "
          ::= { hwCmtsEqamChannelEntry 1 }

    hwCmtsEqamChannelFrequency OBJECT-TYPE
          SYNTAX     Integer32
          MAX-ACCESS read-write
          STATUS     current
          DESCRIPTION
                "The frequency of the EQAM channel.
                0 represents invalid value.
                Unit: Hz
                "
          ::= { hwCmtsEqamChannelEntry 2 }

    hwCmtsEqamChannelModulation OBJECT-TYPE
        SYNTAX      INTEGER  {
            unknown(1),
            other(2),
            qam64(3),
            qam256(4),
            qam1024(5)
        }
        MAX-ACCESS  read-write
        STATUS      current
        DESCRIPTION
            "The modulation type associated with this EQAM channel. 
             Options:
             1. unknown(1) - unknown
             2. other(2)   - Indicates the other modulation type
             3. qam64(3)   - QAM64
             4. qam256(4)  - QAM256
             5. qam1024(5) - QAM1024"
        DEFVAL       { qam256 }
        ::= { hwCmtsEqamChannelEntry 3 }

    hwCmtsEqamChannelSymbolRate OBJECT-TYPE
        SYNTAX      INTEGER {
            symbolRate6875(1),
            symbolRate6900(2),
            symbolRate6952(3),
            symbolRate5057(4),
            symbolRate5361(5)
        }
        MAX-ACCESS  read-write
        STATUS      current
        DESCRIPTION
            "Indicates the symbol rate of a CMTS EQAM channel,
             The channel symbol rate takes effect only for the EQAM channel complying with AnnexA.
             The symbol rate value must be 6.952 when the modulation value is 1024 qam
             Unit: Msym/s
             Options:
             1. symbolRate6875(1)  - the Annex A EQAM channel symbol rate is 6.875
             2. symbolRate6900(2)  - the Annex A EQAM channel symbol rate is 6.900
             3. symbolRate6952(3)  - the Annex A EQAM channel symbol rate is 6.952
             4. symbolRate5057(4)  - the Annex B EQAM channel symbol rate is 5.057
             5. symbolRate5361(5)  - the Annex B EQAM channel symbol rate is 5.361"
        DEFVAL       { symbolRate6952 }
        ::= { hwCmtsEqamChannelEntry 4 }

    hwCmtsEqamChannelInterleaveDepth OBJECT-TYPE
        SYNTAX      INTEGER {
            unknown(1),
            other(2),
            taps8Increment16(3),
            taps16Increment8(4),
            taps32Increment4(5),
            taps64Increment2(6),
            taps128Increment1(7),
            taps12increment17(8)
        }
        MAX-ACCESS  read-write
        STATUS      current
        DESCRIPTION
            "The Forward Error Correction (FEC) interleaving used
             for this EQAM channel.
             Options:
             1. unknown(1)            - unknown
             2. other(2)              - Indicates the other modulation type
             3. taps8Increment16(3)   - protection 5.9/4.1 usec, latency .22/.15 msec
             4. taps16Increment8(4)   - protection 12/8.2 usec, latency .48/.33 msec
             5. taps32Increment4(5)   - protection 24/16 usec, latency .98/.68 msec
             6. taps64Increment2(6)   - protection 47/33 usec, latency 2/1.4 msec
             7. taps128Increment1(7)  - protection 95/66 usec, latency 4/2.8 msec
             8. taps12increment17(8)  - protection 18/14 usec, latency 0.43/0.32 msec"
        DEFVAL       { taps8Increment16 }
        ::= { hwCmtsEqamChannelEntry 5 }

    hwCmtsEqamChannelRfPower OBJECT-TYPE
        SYNTAX Integer32
        UNITS "TenthdBmV"
        MAX-ACCESS read-write
        STATUS current
        DESCRIPTION
            "This attribute represents the Rx power of the CMTS EQAM channel.
            -2147483647 represents invalid value.
            "
        ::= { hwCmtsEqamChannelEntry 6 }

    hwCmtsEqamChannelAdminStatus OBJECT-TYPE
        SYNTAX     INTEGER{
            disable(1),
            enable(2),
            invalid(-1)
        }
        MAX-ACCESS read-write
        STATUS     current
        DESCRIPTION
          "Indicates the administrative status of CMTS EQAM channel.
           Options:
           1. disable(1)     - disable CMTS EQAM channel
           2. enable(2)      - enable CMTS EQAM channel
           3. invalid(-1)    - invalid value"
        DEFVAL      { disable }
        ::= { hwCmtsEqamChannelEntry 7 }

    hwCmtsEqamChannelOperStatus OBJECT-TYPE
        SYNTAX     INTEGER{
           down(1),
           up(2),
           invalid(-1)
        }
        MAX-ACCESS read-only
        STATUS     current
        DESCRIPTION
          "Indicates the operational status of CMTS EQAM channel.
           Options:
           1. down(1)        - down status
           2. up(2)          - up status
           3. invalid(-1)    - invalid value"
        ::= { hwCmtsEqamChannelEntry 8 }

    hwCmtsEqamChannelNotActiveReason OBJECT-TYPE
          SYNTAX     INTEGER
              {
        other(1),
              noLicense(2),
              modeError(3),                        
        exceedMaxChannelNum(4),
              exceedMaxFreq(5),
              exceedMaxFreqSpan(6),
              exceedMaxEqamRateNum(7),
              exceedMaxFreqGroup(9),
        exceedDocsisDsNum(13),
              exceedDsEqamNum(14),
        exceedDocsisAndVodEqamDsNum(16),
              notSupportChannelAnnex(20),
              freqProfMismatch(21), 
              channelIdOccupiedByOther(22),       
              overlapfreqwidth(23),
              invalid(-1)
              }
          MAX-ACCESS read-only
          STATUS     current
          DESCRIPTION
               "The reason of EQAM channel not active.
                Options:
                1.other(1)                          - Other reason                   
                2.noLicense(2)                      - No license                 
                3.channelModeErr(3)                 - Channel mode error            
                4.exceedMaxChannelNum(4)            - Channel ID exceeds actual capability      
                5.exceedMaxFreq(5)                  - The channel frequency exceeds actual capability             
                6.exceedMaxFreqSpan(6)              - Exceed maximum frequency span         
                7.exceedMaxEqamRateNum(7)           - The number of EQAM symbol-rate exceeds the actual capability       
                8.exceedMaxFreqGroup(9)             - Exceed maximum frequency group number 
                9.exceedDocsisDsNum(13)             - The number of DOCSIS downstream channel exceeds real capability 
                10.exceedDsEqamNum(14)              - The number of EQAM downstream channel exceeds real capability 
                11.exceedDocsisAndVodEqamDsNum(16)  - The total number of DOCSIS and EQAM VOD downstream channels exceeds the actual capability 
                12.notSupportChannelAnnex(20)       - Not support channel Annex
                13.freqProfMismatch(21)             - The frequency and the frequency profile configured for the port do not match 
                14.channelIdOccupiedByOther(22)     - The channel ID is occupied by another channel 
                15.overlapfreqwidth(23)             - The difference of frequency between two downstream channels is incorrect. It must be at least 8 MHz in AnnexA mode and 6 MHz in AnnexB mode
                16.invalid(-1)                      - Indicates the downstream channel is active    
               "
          ::= { hwCmtsEqamChannelEntry 9 }

   -- Table hwCmtsEqamChannelUtilizationTable
    hwCmtsEqamChannelUtilizationTable OBJECT-TYPE
          SYNTAX     SEQUENCE OF HwCmtsEqamChannelUtilizationEntry
          MAX-ACCESS not-accessible
          STATUS     current
          DESCRIPTION
               "Indicates the signal quality of a CMTS EQAM channel.
                The index of this table is ifIndex."
          ::= { hwCmtsAccessEqamObject 2 }

    hwCmtsEqamChannelUtilizationEntry OBJECT-TYPE
          SYNTAX     HwCmtsEqamChannelUtilizationEntry
          MAX-ACCESS not-accessible
          STATUS     current
          DESCRIPTION
               "Indicates the signal quality of a CMTS EQAM channel.
               The index of this entry is ifIndex."
          INDEX       { ifIndex }
          ::= { hwCmtsEqamChannelUtilizationTable 1 }

    HwCmtsEqamChannelUtilizationEntry ::=
          SEQUENCE {
                hwCmtsEqamChannelUtUtilization             Integer32,
                hwCmtsEqamChannelUtRealTimeDataRate        Integer32,
                hwCmtsEqamChannelUtMaxDataRate             Integer32
               }

    hwCmtsEqamChannelUtUtilization OBJECT-TYPE
        SYNTAX       Integer32 (0..100)
        UNITS        "percent"
        MAX-ACCESS  read-only
        STATUS  current
        DESCRIPTION
              "CMTS traffic ratio on the EQAM channel."
          ::= { hwCmtsEqamChannelUtilizationEntry 1 }

    hwCmtsEqamChannelUtRealTimeDataRate OBJECT-TYPE
          SYNTAX     Integer32
          MAX-ACCESS read-only
          STATUS     current
          DESCRIPTION
               "The real time data rate.
                Unit: kbps"
          ::= { hwCmtsEqamChannelUtilizationEntry 2 }

    hwCmtsEqamChannelUtMaxDataRate OBJECT-TYPE
        SYNTAX      Integer32
        MAX-ACCESS  read-only
        STATUS      current
        DESCRIPTION
               "The max data rate.
                Unit: kbps"
        ::= { hwCmtsEqamChannelUtilizationEntry 3 }

   -- Table hwCmtsEqamChannelStatisticsTable
    hwCmtsEqamChannelStatisticsTable OBJECT-TYPE
          SYNTAX     SEQUENCE OF HwCmtsEqamChannelStatisticsEntry
          MAX-ACCESS not-accessible
          STATUS     current
          DESCRIPTION
               "This table is implemented at the CMTS to collect
                EQAM channel statistics for utilization calculations.
                The index of this table is ifIndex."
          ::= { hwCmtsAccessEqamObject 3 }

    hwCmtsEqamChannelStatisticsEntry OBJECT-TYPE
          SYNTAX     HwCmtsEqamChannelStatisticsEntry
          MAX-ACCESS not-accessible
          STATUS     current
          DESCRIPTION
               "This table is implemented at the CMTS to collect
                EQAM channel statistics for utilization calculations.
               The index of this entry is ifIndex."
          INDEX       { ifIndex }
          ::= { hwCmtsEqamChannelStatisticsTable 1 }

    HwCmtsEqamChannelStatisticsEntry ::=
          SEQUENCE {
                hwCmtsEqamChannelStatisticsTotalTxPackets       Counter64,
                hwCmtsEqamChannelStatisticsTotalTxBytes         Counter64,
                hwCmtsEqamChannelStatisticsClear                INTEGER
               }

    hwCmtsEqamChannelStatisticsTotalTxPackets OBJECT-TYPE
        SYNTAX       Counter64
        MAX-ACCESS  read-only
        STATUS  current
        DESCRIPTION
              "At the CMTS, the total number of packets transported by this EQAM channel."
          ::= { hwCmtsEqamChannelStatisticsEntry 1 }

    hwCmtsEqamChannelStatisticsTotalTxBytes OBJECT-TYPE
          SYNTAX     Counter64
          MAX-ACCESS read-only
          STATUS     current
          DESCRIPTION
              "At the CMTS, the total number of bytes in the Payload
               portion of packets transported by this EQAM channel."
          ::= { hwCmtsEqamChannelStatisticsEntry 2 }

    hwCmtsEqamChannelStatisticsClear OBJECT-TYPE
        SYNTAX      INTEGER{
                clearStat(1),
                invalidValue(-1)
            }
        MAX-ACCESS  read-write
        STATUS      current
        DESCRIPTION
             "clear statistics of the EQAM channel on cable port.
              Options:
              1. clearStat(1)         - clear EQAM channel statistics.
              2. invalidValue(-1)     - invalid value.
             "
        ::= { hwCmtsEqamChannelStatisticsEntry 3 }

    hwCmtsAccessObject OBJECT IDENTIFIER ::= { hwCmtsObject  20}

    -- Table hwCmtsSpectrumGroupTable
    hwCmtsSpectrumGroupTable OBJECT-TYPE
          SYNTAX     SEQUENCE OF HwCmtsSpectrumGroupEntry
          MAX-ACCESS not-accessible
          STATUS     current
          DESCRIPTION
               "Indicates the configuration of a Spectrum Group.
               The index of this table is hwCmtsSpectrumGroupId."
          ::= { hwCmtsAccessObject 1 }

    hwCmtsSpectrumGroupEntry OBJECT-TYPE
          SYNTAX     HwCmtsSpectrumGroupEntry
          MAX-ACCESS not-accessible
          STATUS     current
          DESCRIPTION
               "Indicates the configuration of a Spectrum Group.
               The index of this entry is hwCmtsSpectrumGroupId."
          INDEX       { hwCmtsSpectrumGroupId }
          ::= { hwCmtsSpectrumGroupTable 1 }

    HwCmtsSpectrumGroupEntry ::=
          SEQUENCE {
                    hwCmtsSpectrumGroupId                   Integer32,
                    hwCmtsSpectrumGroupFrequencyList        OCTET STRING,
                    hwCmtsSpectrumGroupErrorCodeThreshold   Integer32,
                    hwCmtsSpectrumGroupHopPeriod            Integer32,
                    hwCmtsSpectrumGroupRowstatus            RowStatus,
                    hwCmtsSpectrumGroupSecondaryModulationType1     Integer32,
                    hwCmtsSpectrumGroupSecondaryModulationType2    Integer32,
                    hwCmtsSpectrumGroupChannelWidth                 Integer32,
                    hwCmtsSpectrumGroupFirstSnr                     Integer32,
                    hwCmtsSpectrumGroupSecondSnr                    Integer32,
                    hwCmtsSpectrumGroupProtectPower                 Integer32,
                    hwCmtsSpectrumGroupPriority                     Integer32

                   }

    hwCmtsSpectrumGroupId OBJECT-TYPE
          SYNTAX  Integer32
          MAX-ACCESS  not-accessible
          STATUS  current
          DESCRIPTION
                "The index of a Spectrum Group.
                -1 represent that the group id will be assigned by the host automatically."
          ::= { hwCmtsSpectrumGroupEntry 1 }

    hwCmtsSpectrumGroupFrequencyList OBJECT-TYPE
          SYNTAX  OCTET STRING (SIZE(0..35))
          UNITS   "Hz"
          MAX-ACCESS  read-write
          STATUS  current
          DESCRIPTION
                "The frequency list of a Spectrum Group.
                 It can contain as most as 4 frequencies.
                 Every 8 octets represent a frequency,
                 (,) used to indicate a separation of the different frequencies.
                 Only when set operation -1 represent that the frequency list are not assigned.
                 Range: 5000000-85000000 for AnnexA
                        5000000-85000000 for AnnexB
                "
          ::= { hwCmtsSpectrumGroupEntry 2 }

    hwCmtsSpectrumGroupErrorCodeThreshold OBJECT-TYPE
          SYNTAX  Integer32 (1..100)
          UNITS   "%"
          MAX-ACCESS  read-write
          STATUS  current
          DESCRIPTION
                "The threshold of a upstream channel average error code ratio
                 for the Spectrum Group.
                 Range: 1-100
                 Default: 5
                 "
          ::= { hwCmtsSpectrumGroupEntry 3 }

    hwCmtsSpectrumGroupHopPeriod OBJECT-TYPE
          SYNTAX  Integer32 (10..86400)
          UNITS   "s"
          MAX-ACCESS  read-write
          STATUS  current
          DESCRIPTION
                "The hop frequency period of the Spectrum Group.
                 Range: 10-86400
                 Default: 1800
                 "
          ::= { hwCmtsSpectrumGroupEntry 4 }

    hwCmtsSpectrumGroupRowstatus OBJECT-TYPE
          SYNTAX  RowStatus
          MAX-ACCESS  read-create
          STATUS  current
          DESCRIPTION
                "The row status of a Spectrum Group."
          ::= { hwCmtsSpectrumGroupEntry 5 }

    hwCmtsSpectrumGroupSecondaryModulationType1 OBJECT-TYPE
          SYNTAX  Integer32 (-1|1..128)
          MAX-ACCESS  read-write
          STATUS  current
          DESCRIPTION
                "The first standby modulation of a Spectrum Group.
                -1 represent that the modulation are not assigned."
          ::= { hwCmtsSpectrumGroupEntry 6 }

    hwCmtsSpectrumGroupSecondaryModulationType2 OBJECT-TYPE
          SYNTAX  Integer32 (-1|1..128)
          MAX-ACCESS  read-write
          STATUS  current
          DESCRIPTION
                "The second standby modulation of a Spectrum Group.
                -1 represent that the modulation are not assigned."
          ::= { hwCmtsSpectrumGroupEntry 7 }

    hwCmtsSpectrumGroupChannelWidth OBJECT-TYPE
          SYNTAX  Integer32 (-1|0..6400000)
          UNITS   "Hz"
          MAX-ACCESS  read-write
          STATUS  current
          DESCRIPTION
                "The channel width of a Spectrum Group.
                Only three width values are supported currently.
                -1 represent that the channel width is not assigned.
                Options:
                1600000,3200000,6400000"
          ::= { hwCmtsSpectrumGroupEntry 8 }

    hwCmtsSpectrumGroupFirstSnr OBJECT-TYPE
          SYNTAX  Integer32 (5..35)
          UNITS   "dB"
          MAX-ACCESS  read-write
          STATUS  current
          DESCRIPTION
                "The first snr threshold of a Spectrum Group.
                The first snr must be larger than the second snr.
                Default: 25.
                "
          ::= { hwCmtsSpectrumGroupEntry 9 }

    hwCmtsSpectrumGroupSecondSnr OBJECT-TYPE
          SYNTAX  Integer32 (5..35)
          UNITS   "dB"
          MAX-ACCESS  read-write
          STATUS  current
          DESCRIPTION
                "The second snr threshold of a Spectrum Group.
                Default: 15.
                "
          ::= { hwCmtsSpectrumGroupEntry 10 }

    hwCmtsSpectrumGroupProtectPower OBJECT-TYPE
          SYNTAX  Integer32 (0..10)
          UNITS   "dB"
          MAX-ACCESS  read-write
          STATUS  current
          DESCRIPTION
                "The snr protect power of a Spectrum Group.
                Default: 3.
                "
          ::= { hwCmtsSpectrumGroupEntry 11 }

    hwCmtsSpectrumGroupPriority OBJECT-TYPE
          SYNTAX  Integer32 (1..3)
          MAX-ACCESS  read-write
          STATUS  current
          DESCRIPTION
                "The priority of a Spectrum Group.
                 Only three priorities are supported currently.
                 Options:
                 1.Frequency > Modulation-Profile > Channel-Width
                 2.Frequency > Channel-Width > Modulation-Profile
                 3.Modulation-Profile > Frequency > Channel-Width
                 Default: 1.
               "
          ::= { hwCmtsSpectrumGroupEntry 12 }

  -- Table hwdocsIfUpstreamChannelTable
    hwdocsIfUpstreamChannelTable OBJECT-TYPE
          SYNTAX     SEQUENCE OF HwdocsIfUpstreamChannelEntry
          MAX-ACCESS not-accessible
          STATUS     current
          DESCRIPTION
               "This table describes the attributes of upstream channels.
               The index of this table is ifIndex."
          ::= { hwCmtsAccessObject 2 }

    hwdocsIfUpstreamChannelEntry OBJECT-TYPE
          SYNTAX     HwdocsIfUpstreamChannelEntry
          MAX-ACCESS not-accessible
          STATUS     current
          DESCRIPTION
               "This table describes the attributes of upstream channels.
               The index of this entry is ifIndex."
          INDEX       { ifIndex }
          ::= { hwdocsIfUpstreamChannelTable 1 }

    HwdocsIfUpstreamChannelEntry ::=
          SEQUENCE {
                    hwdocsIfUsChanneSpectrumGroupId             Integer32,
                    hwdocsIfUsChanneNoisecanCellation           INTEGER,
                    hwdocsIfUsChanneHopReset                    INTEGER,
                    hwdocsIfUsChannelPreEqEnable                INTEGER,
                    hwDocsIfUpstreamChannelRxPower              Integer32,
                    hwdocsIfUpstreamChannelRngHoldoffValidFlag  INTEGER,
                    hwdocsIfUpstreamChannelRngHoldoffPriority   Unsigned32,
                    hwDocsIfUpstreamChannelPowerAdjustThreshold Unsigned32,
                    hwDocsIfUpstreamChannelPowerAdjustContinue  Unsigned32,
                    hwDocsIfUpstreamChannelPowerAdjustMax       Unsigned32,
                    hwdocsIfUpstreamChannelMdUsSgId             Unsigned32,
                    hwdocsIfUpstreamChannelOperation            INTEGER,
                    hwdocsIfUpstreamChannelUcdType              INTEGER
                   }

    hwdocsIfUsChanneSpectrumGroupId OBJECT-TYPE
          SYNTAX  Integer32
          MAX-ACCESS  read-write
          STATUS  current
          DESCRIPTION
                "The ID of a Spectrum Group bound to the upstream channel.
                 -1 represent that the bonding between upstream channel and spectrum group
                 will be canceled.
                 Range: -1|1..40
                 Default: -1
                "
          ::= { hwdocsIfUpstreamChannelEntry 1 }

    hwdocsIfUsChanneNoisecanCellation OBJECT-TYPE
          SYNTAX  INTEGER {
                           enable(1),
                           disable(2)
                          }
          MAX-ACCESS  read-write
          STATUS  current
          DESCRIPTION
                "The switch for the noise suppression.
                Options:
                1. enable(1) - enable the noise suppression
                2. disable(2) - disable the noise suppression
                Default: enable
                "
          ::= { hwdocsIfUpstreamChannelEntry 2 }

    hwdocsIfUsChanneHopReset OBJECT-TYPE
          SYNTAX  INTEGER {
                           reset(1),
                           invalid(-1)
                          }
          MAX-ACCESS  read-write
          STATUS  current
          DESCRIPTION
                "Cancel the hop which has happened in the channel.
                If cancel the hop, the bonding between channel and
                spectrum group still exist.
                Options:
                1. reset(1) - Cancel the hop
                2. invalid(-1) - Getting is invalid
                "
          ::= { hwdocsIfUpstreamChannelEntry 3 }

    hwdocsIfUsChannelPreEqEnable OBJECT-TYPE
          SYNTAX  INTEGER {
                           true(1),
                           false(2)
                          }
          MAX-ACCESS  read-only
          STATUS  current
          DESCRIPTION
                "This object is used to enable or disable pre-equalization
                on the upstream channel represented by this table instance.
                Options:
                1. true(1) - enable the pre-equalization
                2. false(2) - disable the pre-equalization
                Default value: true(1)
                "
          ::= { hwdocsIfUpstreamChannelEntry 4 }

    hwDocsIfUpstreamChannelRxPower OBJECT-TYPE
          SYNTAX  Integer32
          UNITS   "0.1dBmV"
          MAX-ACCESS  read-write
          STATUS  current
          DESCRIPTION
                "This object indicates the receive power of the upstream channel. 
                 If -2147483647 is returned, the receive power is undefined or cannot be identified.
                 Value range: -2147483647|-130..230
                 Default value: 60
                "
          ::= { hwdocsIfUpstreamChannelEntry 5 }

    hwdocsIfUpstreamChannelRngHoldoffValidFlag OBJECT-TYPE
          SYNTAX  INTEGER {
                           invalid(1),
                           valid(2)
                          }
          MAX-ACCESS  read-write
          STATUS  current
          DESCRIPTION
                "This object indicates the effective identification of the ranging holdoff priority.
                Options:
                1. invalid(1)  - the invalid ranging holdoff priority
                2. valid(2)    - the valid ranging holdoff priority
                Default value: invalid(1)
                "
          ::= { hwdocsIfUpstreamChannelEntry 6 }
          
    hwdocsIfUpstreamChannelRngHoldoffPriority OBJECT-TYPE
          SYNTAX  Unsigned32
          MAX-ACCESS  read-write
          STATUS  current
          DESCRIPTION
                "This object indicates the ranging holdoff priority.                 
                "
          ::= { hwdocsIfUpstreamChannelEntry 7 }

    hwDocsIfUpstreamChannelPowerAdjustThreshold OBJECT-TYPE
          SYNTAX  Unsigned32 (0..2)
          UNITS   "dB"
          MAX-ACCESS  read-write
          STATUS  current
          DESCRIPTION
                "This object indicates transmit power adjustment threshold.
                 Default value: 1
                "
          ::= { hwdocsIfUpstreamChannelEntry 8}

    hwDocsIfUpstreamChannelPowerAdjustContinue OBJECT-TYPE
          SYNTAX  Unsigned32 (0..5)
          UNITS   "dB"
          MAX-ACCESS  read-write
          STATUS  current
          DESCRIPTION
                "This object indicates ranging continue status threshold.                 
                 Default value: 2
                "
          ::= { hwdocsIfUpstreamChannelEntry 9 }

    hwDocsIfUpstreamChannelPowerAdjustMax OBJECT-TYPE
          SYNTAX  Unsigned32 (1..32)
          UNITS   "dB"
          MAX-ACCESS  read-write
          STATUS  current
          DESCRIPTION
                "This object indicates maximum power adjustment.
                 Default value: 2
                "
          ::= { hwdocsIfUpstreamChannelEntry 10 }
          
    hwdocsIfUpstreamChannelMdUsSgId OBJECT-TYPE
          SYNTAX  Unsigned32 (1..2)
          MAX-ACCESS  read-write
          STATUS  current
          DESCRIPTION
                "This object indicates MAC domain upstream service group ID of this channel.
                 Default value: 1
                "
          ::= { hwdocsIfUpstreamChannelEntry 11 }     
          
    hwdocsIfUpstreamChannelOperation OBJECT-TYPE
          SYNTAX  INTEGER {
                           clearStat(1),
                           clearPerfStat(2),
                           invalidValue(-1)
                          }
          MAX-ACCESS  read-write
          STATUS  current
          DESCRIPTION
                "This object is used to clear statistics or performance statistics of the upstream channel on cable port.
                Options:
                1. clearStat(1)        - clear statistics.
                2. clearPerfStat(2)    - clear performance statistics.
                3. invalidValue(-1)    - invalid value.
                "
          ::= { hwdocsIfUpstreamChannelEntry 12 } 
          
    hwdocsIfUpstreamChannelUcdType OBJECT-TYPE
          SYNTAX  INTEGER {
                           type29(1),
                           type35(2),
                           invalidValue(-1)
                          }
          MAX-ACCESS  read-write
          STATUS  current
          DESCRIPTION
                "This object is used to set the type of UCD.
                The Type 29 UCD includes IUC1, 3, 4, 9, 10 and 11. 
                The channel described by the Type 29 UCD can be shared by DOCSIS 3.0 and DOCSIS 2.0 CMs.
    The Type 35 UCD includes IUC1, 3, 4, 5, 6, 9, 10 and 11. 
    The channel described by the Type 35 UCD can only be used by DOCSIS 3.0 CMs.
                Options:
                1. type29(1)        - type29.
                2. type35(2)        - type35.
                3. invalidValue(-1) - invalid value.
                "
          DEFVAL { type29 }      
          ::= { hwdocsIfUpstreamChannelEntry 13 } 
          
  -- Table hwDocsIf3CmtsCmRegStatusTable
    hwDocsIf3CmtsCmRegStatusTable OBJECT-TYPE
          SYNTAX     SEQUENCE OF HwDocsIf3CmtsCmRegStatusEntry
          MAX-ACCESS not-accessible
          STATUS     current
          DESCRIPTION
               "This table describes the information of cable modem.
                The index of this table is docsIf3CmtsCmRegStatusId."
          ::= { hwCmtsAccessObject 3 }

    hwDocsIf3CmtsCmRegStatusEntry OBJECT-TYPE
          SYNTAX     HwDocsIf3CmtsCmRegStatusEntry
          MAX-ACCESS not-accessible
          STATUS     current
          DESCRIPTION
               "This table describes the information of cable modem.
                The index of this entry is docsIf3CmtsCmRegStatusId."
          INDEX       { docsIf3CmtsCmRegStatusId }
          ::= { hwDocsIf3CmtsCmRegStatusTable 1 }

    HwDocsIf3CmtsCmRegStatusEntry ::=
          SEQUENCE {
                    hwDocsIf3CmtsCmRegStatusPrimSid                      Integer32,
                    hwDocsIf3CmtsCmRegStatusHostInterface                InterfaceIndexOrZero,
                    hwDocsIf3CmtsCmRegStatusMacDomainDsSvcGroup          Integer32,
                    hwDocsIf3CmtsCmRegStatusMacDomainUsSvcGroup          Integer32,
                    hwDocsIf3CmtsCmRegStatusMacDomainCmSvcGroup          Integer32,
                    hwDocsIf3CmtsCmRegStatusPrimaryDs                    Integer32,
                    hwDocsIf3CmtsCmRegStatusMTC                          INTEGER,
                    hwDocsIf3CmtsCmRegStatusUpChannelNum                 Integer32,
                    hwDocsIf3CmtsCmRegStatusDOCSISVersion                INTEGER,
                    hwDocsIf3CmtsCmRegStatusEnableDocsisTwo              INTEGER,
                    hwDocsIf3CmtsCmRegStatusFragmentation                INTEGER,
                    hwDocsIf3CmtsCmRegStatusConcatenation                INTEGER,
                    hwDocsIf3CmtsCmRegStatusPhs                          INTEGER,
                    hwDocsIf3CmtsCmRegStatusBpi                          INTEGER,
                    hwDocsIf3CmtsCmRegStatusL2VPNCapabilities            INTEGER,
                    hwDocsIf3CmtsCmRegStatusSidLimit                     Integer32,
                    hwDocsIf3CmtsCmRegStatusSaidLimit                    Integer32,
                    hwDocsIf3CmtsCmRegStatusOptionalFilteringSupport     Integer32,
                    hwDocsIf3CmtsCmRegStatusTxEqTapsPerSymbol            Integer32,
                    hwDocsIf3CmtsCmRegStatusCpeNum                       Integer32,
                    hwDocsIf3CmtsCmRegStatusMaxCpe                       Integer32,
                    hwDocsIf3CmtsCmRegStatusUsSFIDCnt                    Integer32,
                    hwDocsIf3CmtsCmRegStatusDsSFIDCnt                    Integer32,
                    hwDocsIf3CmtsCmRegStatusTotalUsPkt                   Counter64,
                    hwDocsIf3CmtsCmRegStatusTotalUsBytes                 Counter64,
                    hwDocsIf3CmtsCmRegStatusTotalDsPkt                   Counter64,
                    hwDocsIf3CmtsCmRegStatusTotalDsBytes                 Counter64,
                    hwDocsIf3CmtsCmRegStatusLbGroupId                    Unsigned32,
                    hwDocsIf3CmtsCmRegStatusLbGroupIdinCfgFile           Unsigned32,
                    hwDocsIf3CmtsCmRegStatusValue                        INTEGER,
                    hwDocsIf3CmtsCmCtrlOperStatus                        INTEGER,
                    hwDocsIf3CmtsCmRegStatusRemoteQuery                  INTEGER,
                    hwDocsIf3CmtsCmRegStatusPrimaryDsRxPower             Integer32,
                    hwDocsIf3CmtsCmRegStatusPrimaryDsSnr                 Integer32,
                    hwDocsIf3CmtsCmRegStatusSysDesc                      OCTET STRING,
                    hwDocsIf3CmtsCmRegStatusPortIfIndex                  Integer32,
                    hwDocsIf3CmtsCmRegStatusPrimaryUsTxTimingOffset      Integer32,
                    hwDocsIf3CmtsCmRegStatusOfflineTime                  OCTET STRING,
                    hwDocsIf3CmtsCmRegStatusPreviousStatusValue          INTEGER,
                    hwDocsIf3CmtsCmRegStatusGoodCodeWords                Counter64,
                    hwDocsIf3CmtsCmRegStatusCorrectedErrorCodeWords      Counter64,
                    hwDocsIf3CmtsCmRegStatusUncorrectedErrorCodeWords    Counter64,
                    hwDocsIf3CmtsCmRegStatusConfigFilename               OCTET STRING,
                    hwDocsIf3CmtsCmRegStatusPrimaryUs                    Integer32,
                    hwDocsIf3CmtsCmRegStatusPrimaryUsRxPower             Integer32,
                    hwDocsIf3CmtsCmRegStatusPrimaryUsTxPower             Integer32,
                    hwDocsIf3CmtsCmRegStatusPrimaryDsTxPower             Integer32,
                    hwDocsIf3CmtsCmRegStatusPrimaryUsSnr                 Integer32,
                    hwDocsIf3CmtsCmRegStatusVoiceEnabled                 INTEGER,
                    hwDocsIf3CmtsCmRegStatusDsChangeTimes                Counter32,
                    hwDocsIf3CmtsCmRegStatusSnmpProxyUpdateTime          DateAndTime,
                    hwDocsIf3CmtsCmRegStatusIPv6Prefix                   InetAddressIPv6,
                    hwDocsIf3CmtsCmRegStatusIPv6PrefixLength             Unsigned32,
                    hwDocsIf3CmtsCmRegStatusPeriodT1Timeouts             Integer32,
                    hwDocsIf3CmtsCmRegStatusPeriodT2Timeouts             Integer32,
                    hwDocsIf3CmtsCmRegStatusDsPer                        Integer32,
                    hwDocsIf3CmtsCmRegStatusConfigFilenameIPv6           OCTET STRING,
                    hwDocsIf3CmtsCmRegStatusUsPartialChannelMask         OCTET STRING,
                    hwDocsIf3CmtsCmRegStatusDsPartialChannelMask         OCTET STRING,
                    hwDocsIf3CmtsCmRegStatusRangingClassIDValidFlag      INTEGER,
                    hwDocsIf3CmtsCmRegStatusRangingClassID               Unsigned32,
                    hwDocsIf3CmtsCmRegStatusPrimaryUsGoodCodewords               Counter64,
                    hwDocsIf3CmtsCmRegStatusPrimaryUsCorrectedErrorCodewords     Counter64,
                    hwDocsIf3CmtsCmRegStatusPrimaryUsUncorrectedErrorCodewords   Counter64,
                    hwDocsIf3CmtsCmRegStatusPrimaryUsFrequency                   Integer32,
                    hwDocsIf3CmtsCmRegStatusPrimaryUsChannelWidth                Integer32,
                    hwDocsIf3CmtsCmRegStatusPrimaryDsGoodCodewords               Counter64,
                    hwDocsIf3CmtsCmRegStatusPrimaryDsCorrectedErrorCodewords     Counter64,
                    hwDocsIf3CmtsCmRegStatusPrimaryDsUncorrectedErrorCodewords   Counter64,
                    hwDocsIf3CmtsCmRegStatusPrimaryDsFrequency                   Integer32,
                    hwDocsIf3CmtsCmRegStatusServiceTypeID                        OCTET STRING,
                    hwDocsIf3CmtsCmRegStatusUsTxPowerReachMaxFlag                INTEGER,
                    hwDocsIf3CmtsCmRegStatusTotalUsPktErrorNum                   Counter64,
                    hwDocsIf3CmtsCmRegStatusUsPer                                Integer32,
                    hwDocsIf3CmtsCmRegStatusCrc                                  Counter64,
                    hwDocsIf3CmtsCmRegStatusHcs                                  Counter64,
                    hwDocsIf3CmtsCmRegStatusOfdmMTC                              INTEGER,
                    hwDocsIf3CmtsCmRegStatusOfdmProfileCapability                Integer32,
                    hwDocsIf3CmtsCmRegStatusUsBondingGroupId                     Unsigned32,
                    hwDocsIf3CmtsCmRegStatusDsBondingGroupId                     Unsigned32,
                    hwDocsIf3CmtsCmRegStatusRccCfgId                             Unsigned32,
                    hwDocsIf3CmtsCmRegStatusDsRequiredMask                       AttributeMask,
                    hwDocsIf3CmtsCmRegStatusDsForbiddenMask                      AttributeMask,
                    hwDocsIf3CmtsCmRegStatusUsRequiredMask                       AttributeMask,
                    hwDocsIf3CmtsCmRegStatusUsForbiddenMask                      AttributeMask,
                    hwDocsIf3CmtsCmRegStatusCurrentServiceTypeID                 OCTET STRING,
                    hwDocsIf3CmtsCmRegStatusCurrentPolicyID                      Unsigned32,
                    hwDocsIf3CmtsCmRegStatusPolicyIDinCfgFile                    Unsigned32,
                    hwDocsIf3CmtsCmRegStatusCurrentPriority                      Unsigned32,
                    hwDocsIf3CmtsCmRegStatusPriorityinCfgFile                    Unsigned32,
                    hwDocsIf3CmtsCmRegStatusOfdmaPartialChannelMask              OCTET STRING,
                    hwDocsIf3CmtsCmRegStatusOfdmPartialChannelMask               OCTET STRING
                   }

    hwDocsIf3CmtsCmRegStatusPrimSid OBJECT-TYPE
          SYNTAX  Integer32 (0..65535)
          MAX-ACCESS  read-only
          STATUS  current
          DESCRIPTION
                "The ID of the primary service flow which the cable modem using."
          ::= { hwDocsIf3CmtsCmRegStatusEntry 1 }

    hwDocsIf3CmtsCmRegStatusHostInterface OBJECT-TYPE
          SYNTAX  InterfaceIndexOrZero
          MAX-ACCESS  read-only
          STATUS  current
          DESCRIPTION
                "The Host Interface when a cable modem arrival."
          ::= { hwDocsIf3CmtsCmRegStatusEntry 2 }

    hwDocsIf3CmtsCmRegStatusMacDomainDsSvcGroup OBJECT-TYPE
          SYNTAX  Integer32 (0..255)
          MAX-ACCESS  read-only
          STATUS  current
          DESCRIPTION
                "The MAC domain downstream service group.
           0 represents invalid value."
          ::= { hwDocsIf3CmtsCmRegStatusEntry 3 }

    hwDocsIf3CmtsCmRegStatusMacDomainUsSvcGroup OBJECT-TYPE
          SYNTAX  Integer32 (0..255)
          MAX-ACCESS  read-only
          STATUS  current
          DESCRIPTION
                "The MAC domain upstream service group.
     0 represents invalid value."
          ::= { hwDocsIf3CmtsCmRegStatusEntry 4 }

    hwDocsIf3CmtsCmRegStatusMacDomainCmSvcGroup OBJECT-TYPE
          SYNTAX  Integer32 (0..65535)
          MAX-ACCESS  read-only
          STATUS  current
          DESCRIPTION
                "The mac domain cm service group.
     0 represents invalid value."
          ::= { hwDocsIf3CmtsCmRegStatusEntry 5 }

    hwDocsIf3CmtsCmRegStatusPrimaryDs OBJECT-TYPE
          SYNTAX  Integer32 
          MAX-ACCESS  read-only
          STATUS  current
          DESCRIPTION
                "The primary downstream channel which is a cable modem using.
                 Value range: -1|1..104. -1 represents invalid value.
                "
          ::= { hwDocsIf3CmtsCmRegStatusEntry 6 }

    hwDocsIf3CmtsCmRegStatusMTC OBJECT-TYPE
          SYNTAX  INTEGER {
                           enable(1),
                           disable(2),
                           invalidValue(-1)
                          }
          MAX-ACCESS  read-only
          STATUS  current
          DESCRIPTION
                "The status of the multi transmit channel.
                Options:
                1. enable(1) - enable the multi transmit channel
                2. disable(2) - disable the multi transmit channel
                3. invalidValue(-1) - invalid value
                "
          ::= { hwDocsIf3CmtsCmRegStatusEntry 7 }

    hwDocsIf3CmtsCmRegStatusUpChannelNum OBJECT-TYPE
          SYNTAX  Integer32 (0..16)
          MAX-ACCESS  read-write
          STATUS  current
          DESCRIPTION
                "The number of the CMC upstream bonding channels."
          ::= { hwDocsIf3CmtsCmRegStatusEntry 8 }

    hwDocsIf3CmtsCmRegStatusDOCSISVersion OBJECT-TYPE
          SYNTAX  INTEGER      {
                                doc10(1),
                                doc11(2),
                                doc20(3),
                                doc30(4),
                                doc31(5),
                                invalidValue(-1)
                               }
          MAX-ACCESS  read-only
          STATUS  current
          DESCRIPTION
                "The MAC version of the cable modem.
                Options:
                1. doc10(1) - docsis 1.0 version
                2. doc11(2) - docsis 1.1 version
                3. doc20(3) - docsis 2.0 version
                4. doc30(4) - docsis 3.0 version
                5. doc31(5) - docsis 3.1 version
                6. invalidValue(-1) - invalid value"
          ::= { hwDocsIf3CmtsCmRegStatusEntry 9 }

    hwDocsIf3CmtsCmRegStatusEnableDocsisTwo OBJECT-TYPE
          SYNTAX  INTEGER {
                           enable(1),
                           disable(2),
                           invalidValue(-1)
                          }
          MAX-ACCESS  read-only
          STATUS  current
          DESCRIPTION
                "The status of the DOCSIS2.0 Mode.
                Options:
                1. enable(1) - enable the DOCSIS2.0 Mode
                2. disable(2) - disable the DOCSIS2.0 Mode
                3. invalidValue(-1) -invalid value
                                                                "
          ::= { hwDocsIf3CmtsCmRegStatusEntry 10 }

    hwDocsIf3CmtsCmRegStatusFragmentation OBJECT-TYPE
          SYNTAX  INTEGER {
                           enable(1),
                           disable(2)
                          }
          MAX-ACCESS  read-only
          STATUS  current
          DESCRIPTION
                "The fragmentation capabilities.
                Options:
                1. enable(1) - enable the fragmentation capabilities
                2. disable(2) - disable the fragmentation capabilities
                                                                "
          ::= { hwDocsIf3CmtsCmRegStatusEntry 11 }

    hwDocsIf3CmtsCmRegStatusConcatenation OBJECT-TYPE
          SYNTAX  INTEGER {
                           enable(1),
                           disable(2)
                          }
          MAX-ACCESS  read-only
          STATUS  current
          DESCRIPTION
                "The concatenation capabilities.
                Options:
                1. enable(1) - enable the concatenation capabilities
                2. disable(2) - disable the concatenation capabilities
                                                                "
          ::= { hwDocsIf3CmtsCmRegStatusEntry 12 }

    hwDocsIf3CmtsCmRegStatusPhs OBJECT-TYPE
          SYNTAX  INTEGER {
                           enable(1),
                           disable(2)
                          }
          MAX-ACCESS  read-only
          STATUS  current
          DESCRIPTION
                "The packet header suppression capabilities.
                Options:
                1. enable(1) - enable the packet header suppression capabilities
                2. disable(2) - disable the packet header suppression capabilities
                                                                "
          ::= { hwDocsIf3CmtsCmRegStatusEntry 13 }

    hwDocsIf3CmtsCmRegStatusBpi OBJECT-TYPE
          SYNTAX  INTEGER {
                           disable(1),
                           bpi(2),
                           bpiPlus(3),
                           invalidValue(-1)
                          }
          MAX-ACCESS  read-only
          STATUS  current
          DESCRIPTION
                "The status of Baseline Privacy Interface.
                Options:
                1. disable(1) - disable the Baseline Privacy Interface
                2. bpi(2) - enable the Baseline Privacy Interface
                3. bpiPlus(3) - enable the Baseline Privacy Interface Plus
                4. invalidValue(-1) - invalid value
                "
          ::= { hwDocsIf3CmtsCmRegStatusEntry 14 }

    hwDocsIf3CmtsCmRegStatusL2VPNCapabilities OBJECT-TYPE
          SYNTAX  INTEGER {
                           enable(1),
                           disable(2)
                          }
          MAX-ACCESS  read-only
          STATUS  current
          DESCRIPTION
                "The Layer 2 Virtual Private Network capabilities.
                Options:
                1. enable(1) - enable the Layer 2 Virtual Private Network capabilities
                2. disable(2) - disable the Layer 2 Virtual Private Network capabilities
                                                                "
          ::= { hwDocsIf3CmtsCmRegStatusEntry 15 }

    hwDocsIf3CmtsCmRegStatusSidLimit OBJECT-TYPE
          SYNTAX  Integer32 (0..255)
          MAX-ACCESS  read-only
          STATUS  current
          DESCRIPTION
                "The limit of the Service Identifier when cable modem register."
          ::= { hwDocsIf3CmtsCmRegStatusEntry 16 }

    hwDocsIf3CmtsCmRegStatusSaidLimit OBJECT-TYPE
          SYNTAX  Integer32 (0..255)
          MAX-ACCESS  read-only
          STATUS  current
          DESCRIPTION
                "The limit of Security Association Identifiers when cable modem register."
          ::= { hwDocsIf3CmtsCmRegStatusEntry 17 }

    hwDocsIf3CmtsCmRegStatusOptionalFilteringSupport OBJECT-TYPE
          SYNTAX  Integer32 (0..255)
          MAX-ACCESS  read-only
          STATUS  current
          DESCRIPTION
                "Optional Filtering Support.
                Bit0 represent 802.1P, bit1 represent 802.1Q, bit2 represent DUT.
                "
          ::= { hwDocsIf3CmtsCmRegStatusEntry 18 }

    hwDocsIf3CmtsCmRegStatusTxEqTapsPerSymbol OBJECT-TYPE
          SYNTAX  Integer32 (0..255)
          MAX-ACCESS  read-only
          STATUS  current
          DESCRIPTION
                "Transmit Equalizer Support."
          ::= { hwDocsIf3CmtsCmRegStatusEntry 19 }

    hwDocsIf3CmtsCmRegStatusCpeNum OBJECT-TYPE
          SYNTAX  Integer32 (0..255)
          MAX-ACCESS  read-only
          STATUS  current
          DESCRIPTION
                "The number of CPE IPs."
          ::= { hwDocsIf3CmtsCmRegStatusEntry 20 }

    hwDocsIf3CmtsCmRegStatusMaxCpe OBJECT-TYPE
          SYNTAX  Integer32 (0..255)
          MAX-ACCESS  read-only
          STATUS  current
          DESCRIPTION
                "Configuration the max CPE number."
          ::= { hwDocsIf3CmtsCmRegStatusEntry 21 }

    hwDocsIf3CmtsCmRegStatusUsSFIDCnt OBJECT-TYPE
          SYNTAX  Integer32 (0..65535)
          MAX-ACCESS  read-only
          STATUS  current
          DESCRIPTION
                "The number of upstream service flow IDs setup for cable modem."
          ::= { hwDocsIf3CmtsCmRegStatusEntry 22 }

    hwDocsIf3CmtsCmRegStatusDsSFIDCnt OBJECT-TYPE
          SYNTAX  Integer32 (0..65535)
          MAX-ACCESS  read-only
          STATUS  current
          DESCRIPTION
                "The number of downstream service flow IDs setup for cable modem."
          ::= { hwDocsIf3CmtsCmRegStatusEntry 23 }

    hwDocsIf3CmtsCmRegStatusTotalUsPkt OBJECT-TYPE
          SYNTAX  Counter64
          MAX-ACCESS  read-only
          STATUS  current
          DESCRIPTION
                "Total upstream data."
          ::= { hwDocsIf3CmtsCmRegStatusEntry 24 }

    hwDocsIf3CmtsCmRegStatusTotalUsBytes OBJECT-TYPE
          SYNTAX  Counter64
          MAX-ACCESS  read-only
          STATUS  current
          DESCRIPTION
                "Total upstream throughput."
          ::= { hwDocsIf3CmtsCmRegStatusEntry 25 }

    hwDocsIf3CmtsCmRegStatusTotalDsPkt OBJECT-TYPE
          SYNTAX  Counter64
          MAX-ACCESS  read-only
          STATUS  current
          DESCRIPTION
                "Total downstream Data."
          ::= { hwDocsIf3CmtsCmRegStatusEntry 26 }

    hwDocsIf3CmtsCmRegStatusTotalDsBytes OBJECT-TYPE
          SYNTAX  Counter64
          MAX-ACCESS  read-only
          STATUS  current
          DESCRIPTION
                "Total downstream throughput."
          ::= { hwDocsIf3CmtsCmRegStatusEntry 27 }

    hwDocsIf3CmtsCmRegStatusLbGroupId OBJECT-TYPE
          SYNTAX  Unsigned32 (0..4294967295)
          MAX-ACCESS  read-only
          STATUS  current
          DESCRIPTION
                "The load balance group ID assigned.
                 "
          ::= { hwDocsIf3CmtsCmRegStatusEntry 28 }

    hwDocsIf3CmtsCmRegStatusLbGroupIdinCfgFile OBJECT-TYPE
          SYNTAX  Unsigned32 (0..4294967295)
          MAX-ACCESS  read-only
          STATUS  current
          DESCRIPTION
                "The load balance group ID in the configuration file.
                 0 represents invalid value."
          ::= { hwDocsIf3CmtsCmRegStatusEntry 29 }

    hwDocsIf3CmtsCmRegStatusValue OBJECT-TYPE
          SYNTAX  INTEGER {
                   other(1),
                           initialRanging(2),
                           rangingAutoAdjComplete(4),
                           dhcpv4Complete(5),
                           registrationComplete(6),
                           operational(8),
                           bpiInit(9),
                           startEae(10),
                           startDhcpv4(11),
                           startDhcpv6(12),
                           dhcpv6Complete(13),
                           startConfigFileDownload(14),
                           configFileDownloadComplete(15),
                           startRegistration(16),
                           forwardingDisabled(17),
                           rfMuteAll(18),
                           offline(31),
                           dhcpOffer(32),
                           dhcpRequest(33),
                           online(34),
                           onlineBpiSucc(35),
                           onlineBpiSuccAndNetAccessDisabled(36),
                           onlineNetAccessDisabled(37),
                           wonline(38),
                           wonlineBpiSucc(39),
                           wonlineBpiSuccAndNetAccessDisabled(40),
                           wonlineNetAccessDisabled(41),
                           ponline(42),
                           ponlineBpiSucc(43),
                           ponlineBpiSuccAndNetAccessDisabled(44),
                           ponlineNetAccessDisabled(45),
                           rejectMic(46),
                           rejectBpi(47),
                           rejectOther(48),
                           dhcpv6Advertise(49),
                           dhcpv6Request(50),
                           onlinePk(51),
                           onlineNetAccessDisabledPk(52),
                           wonlinePk(53),
                           wonlineNetAccessDisabledPk(54),
                           ponlinePk(55),
                           ponlineNetAccessDisabledPk(56),
                           ofdmInitialRanging(57) 
                          }
          MAX-ACCESS  read-only
          STATUS  current
          DESCRIPTION
                "
                Indicates current register status of the CM.
                Options:
                1. other(1) - other
                2. initialRanging(2) - initialRanging
                3. rangingAutoAdjComplete(4) - rangingAutoAdjComplete
                4. dhcpv4Complete(5) - dhcpv4Complete
                5. registrationComplete(6) - registrationComplete
                6. operational(8) - operational
                7. bpiInit(9) - bpiInit
                8. startEae(10) - startEae
                9. startDhcpv4(11) - startDhcpv4
                10. startDhcpv6(12) - startDhcpv6
                11. dhcpv6Complete(13) - dhcpv6Complete
                12. startConfigFileDownload(14) - startConfigFileDownload
                13. configFileDownloadComplete(15) - configFileDownloadComplete
                14. startRegistration(16) - startRegistration
                15. forwardingDisabled(17) - forwardingDisabled
                16. rfMuteAll(18) - rfMuteAll
                17. offline(31) - offline
                18. dhcpOffer(32) - dhcpOffer
                19. dhcpRequest(33) - dhcpRequest
                20. online(34) - online
                21. onlineBpiSucc(35) - onlineBpiSucc
                22. onlineBpiSuccAndNetAccessDisabled(36) - onlineBpiSuccAndNetAccessDisabled
                23. onlineNetAccessDisabled(37) - onlineNetAccessDisabled
                24. wonline(38) - wonline
                25. wonlineBpiSucc(39) - wonlineBpiSucc
                26. wonlineBpiSuccAndNetAccessDisabled(40) - wonlineBpiSuccAndNetAccessDisabled
                27. wonlineNetAccessDisabled(41) - wonlineNetAccessDisabled
                28. ponline(42) - ponline
                29. ponlineBpiSucc(43) - ponlineBpiSucc
                30. ponlineBpiSuccAndNetAccessDisabled(44) - ponlineBpiSuccAndNetAccessDisabled
                31. ponlineNetAccessDisabled(45) - ponlineNetAccessDisabled
                32. rejectMic(46) - rejectMic
                33. rejectBpi(47) - rejectBpi
                34. rejectOther(48) - rejectOther
                35. dhcpv6Advertise(49) - dhcpv6Advertise
                36. dhcpv6Request(50) - dhcpv6Request
                37. onlinePk(51) - onlinePk
                38. onlineNetAccessDisabledPk(52) - onlineNetAccessDisabledPk
                39. wonlinePk(53) - wonlinePk
                40. wonlineNetAccessDisabledPk(54) - wonlineNetAccessDisabledPk
                41. ponlinePk(55) - ponlinePk
                42. ponlineNetAccessDisabledPk(56) - ponlineNetAccessDisabledPk
                43. ofdmInitialRanging(57) - ofdmInitialRanging
                "
          ::= { hwDocsIf3CmtsCmRegStatusEntry 30 }

    hwDocsIf3CmtsCmCtrlOperStatus OBJECT-TYPE
          SYNTAX  INTEGER {
                           reset(1),
                           delete(2), 
                           clearStat(3),
                           invalidValue(-1)
                          }
          MAX-ACCESS  read-write
          STATUS  current
          DESCRIPTION
                "Indicates the operating mode.
                Options:
                1. reset(1)  - Reset the operating mode
                2. delete(2) - Delete the operating mode  
                3. clearStat(3) - Clear CM statistics
                4. invalidValue(-1) -Invalid value
                "
          ::= { hwDocsIf3CmtsCmRegStatusEntry 31 }

    hwDocsIf3CmtsCmRegStatusRemoteQuery OBJECT-TYPE
          SYNTAX  INTEGER {
                           start(1),
                           stop(2)
                          }
          MAX-ACCESS  read-write
          STATUS  current
          DESCRIPTION
                "Indicates querying the information about a remote CM.
                 Options:
                1. start(1) - Start querying the information about a remote CM
                2. stop(2)  - Stop querying the information about a remote CM
                "
          ::= { hwDocsIf3CmtsCmRegStatusEntry 32 }

    hwDocsIf3CmtsCmRegStatusPrimaryDsRxPower OBJECT-TYPE
          SYNTAX  Integer32
          UNITS       "0.1dBmV"
          MAX-ACCESS  read-only
          STATUS  current
          DESCRIPTION
                "
                Indicates the downstream receive power of cable modem.
                -2147483647 represent NULL.
                "
          ::= { hwDocsIf3CmtsCmRegStatusEntry 33 }

    hwDocsIf3CmtsCmRegStatusPrimaryDsSnr OBJECT-TYPE
          SYNTAX  Integer32
          UNITS       "0.1dB"
          MAX-ACCESS  read-only
          STATUS  current
          DESCRIPTION
                "
                The primary downstream snr of cable modem.
                -1 represent NULL.
                "
          ::= { hwDocsIf3CmtsCmRegStatusEntry 34 }

    hwDocsIf3CmtsCmRegStatusSysDesc OBJECT-TYPE
          SYNTAX  OCTET STRING(SIZE (0..255))
          MAX-ACCESS  read-only
          STATUS  current
          DESCRIPTION
                "
                The system description information of CM.
                Return a zero-length OCTET STRING to indicate that the description is not achieved.
                "
          ::= { hwDocsIf3CmtsCmRegStatusEntry 35 }

    hwDocsIf3CmtsCmRegStatusPortIfIndex OBJECT-TYPE
          SYNTAX  Integer32
          MAX-ACCESS  read-only
          STATUS  current
          DESCRIPTION
                "
                The port ifindex of CM.
                "
          ::= { hwDocsIf3CmtsCmRegStatusEntry 36 }

    hwDocsIf3CmtsCmRegStatusPrimaryUsTxTimingOffset OBJECT-TYPE
          SYNTAX  Integer32
          UNITS      "97.6ns(6.25/64 microseconds)"
          MAX-ACCESS  read-only
          STATUS  current
          DESCRIPTION
                "
                The send time offset of the main up channel of CM.
                -1 represent NULL.
                "
          ::= { hwDocsIf3CmtsCmRegStatusEntry 37 }

    hwDocsIf3CmtsCmRegStatusOfflineTime OBJECT-TYPE
          SYNTAX  OCTET STRING
          MAX-ACCESS  read-only
          STATUS  current
          DESCRIPTION
                "
                The value of this node is DateAndTime.
                "
          ::= { hwDocsIf3CmtsCmRegStatusEntry 38 }

    hwDocsIf3CmtsCmRegStatusPreviousStatusValue OBJECT-TYPE
          SYNTAX  INTEGER {
                           other(1),
                           initialRanging(2),
                           rangingAutoAdjComplete(4),
                           dhcpv4Complete(5),
                           registrationComplete(6),
                           operational(8),
                           bpiInit(9),
                           startEae(10),
                           startDhcpv4(11),
                           startDhcpv6(12),
                           dhcpv6Complete(13),
                           startConfigFileDownload(14),
                           configFileDownloadComplete(15),
                           startRegistration(16),
                           forwardingDisabled(17),
                           rfMuteAll(18),
                           offline(31),
                           dhcpOffer(32),
                           dhcpRequest(33),
                           online(34),
                           onlineBpiSucc(35),
                           onlineBpiSuccAndNetAccessDisabled(36),
                           onlineNetAccessDisabled(37),
                           wonline(38),
                           wonlineBpiSucc(39),
                           wonlineBpiSuccAndNetAccessDisabled(40),
                           wonlineNetAccessDisabled(41),
                           rejectMic(46),
                           rejectBpi(47),
                           rejectOther(48),
                           dhcpv6Advertise(49),
                           dhcpv6Request(50),
                           onlinePk(51),
                           onlineNetAccessDisabledPk(52),
                           wonlinePk(53),
                           wonlineNetAccessDisabledPk(54),
                           ofdmInitialRanging(57)
                          }
          MAX-ACCESS  read-only
          STATUS  current
          DESCRIPTION
                "
                Indicates previous register status of the offline CM.
                Options:
                1. other(1) - other
                2. initialRanging(2) - initialRanging
                3. rangingAutoAdjComplete(4) - rangingAutoAdjComplete
                4. dhcpv4Complete(5) - dhcpv4Complete
                5. registrationComplete(6) - registrationComplete
                6. operational(8) - operational
                7. bpiInit(9) - bpiInit
                8. startEae(10) - startEae
                9. startDhcpv4(11) - startDhcpv4
                10. startDhcpv6(12) - startDhcpv6
                11. dhcpv6Complete(13) - dhcpv6Complete
                12. startConfigFileDownload(14) - startConfigFileDownload
                13. configFileDownloadComplete(15) - configFileDownloadComplete
                14. startRegistration(16) - startRegistration
                15. forwardingDisabled(17) - forwardingDisabled
                16. rfMuteAll(18) - rfMuteAll
                17. offline(31) - offline
                18. dhcpOffer(32) - dhcpOffer
                19. dhcpRequest(33) - dhcpRequest
                20. online(34) - online
                21. onlineBpiSucc(35) - onlineBpiSucc
                22. onlineBpiSuccAndNetAccessDisabled(36) - onlineBpiSuccAndNetAccessDisabled
                23. onlineNetAccessDisabled(37) - onlineNetAccessDisabled
                24. wonline(38) - wonline
                25. wonlineBpiSucc(39) - wonlineBpiSucc
                26. wonlineBpiSuccAndNetAccessDisabled(40) - wonlineBpiSuccAndNetAccessDisabled
                27. wonlineNetAccessDisabled(41) - wonlineNetAccessDisabled
                28. rejectMic(46) - rejectMic
                29. rejectBpi(47) - rejectBpi
                30. rejectOther(48) - rejectOther
                31. dhcpv6Advertise(49) - dhcpv6Advertise
                32. dhcpv6Request(50) - dhcpv6Request
                33. onlinePk(51) - onlinePk
                34. onlineNetAccessDisabledPk(52) - onlineNetAccessDisabledPk
                35. wonlinePk(53)  - wonlinePk
                36. wonlineNetAccessDisabledPk(54) - wonlineNetAccessDisabledPk
                37. ofdmInitialRanging(57)  - ofdmInitialRanging
                "
          ::= { hwDocsIf3CmtsCmRegStatusEntry 39 }

    hwDocsIf3CmtsCmRegStatusGoodCodeWords OBJECT-TYPE
          SYNTAX  Counter64
          MAX-ACCESS  read-only
          STATUS  current
          DESCRIPTION
                "
                This attribute represents the good codewords received
                from the CM on this interface.
                "
          ::= { hwDocsIf3CmtsCmRegStatusEntry 40 }

    hwDocsIf3CmtsCmRegStatusCorrectedErrorCodeWords OBJECT-TYPE
          SYNTAX  Counter64
          MAX-ACCESS  read-only
          STATUS  current
          DESCRIPTION
                "
                This attribute represents the codewords received
                with correctable errors from the CM on this interface.
                "
          ::= { hwDocsIf3CmtsCmRegStatusEntry 41 }

    hwDocsIf3CmtsCmRegStatusUncorrectedErrorCodeWords OBJECT-TYPE
          SYNTAX  Counter64
          MAX-ACCESS  read-only
          STATUS  current
          DESCRIPTION
                "
                This attribute represents the codewords received
                with uncorrectable errors from the CM on this interface.
                "
          ::= { hwDocsIf3CmtsCmRegStatusEntry 42 }

    hwDocsIf3CmtsCmRegStatusConfigFilename OBJECT-TYPE
          SYNTAX  OCTET STRING(SIZE (0..256))
          MAX-ACCESS  read-only
          STATUS  current
          DESCRIPTION
                "
                This attribute represents the CM config-file Name for IPv4.
                "
          ::= { hwDocsIf3CmtsCmRegStatusEntry 43 }

    hwDocsIf3CmtsCmRegStatusPrimaryUs OBJECT-TYPE
          SYNTAX  Integer32
          MAX-ACCESS  read-only
          STATUS  current
          DESCRIPTION
                "This object indicates the ID of the CM's active upstream channel. 
                 If -1 is returned, the index is undefined or cannot be identified. 
                 Value range: -1|1..20.
                "
          ::= { hwDocsIf3CmtsCmRegStatusEntry 44 }

    hwDocsIf3CmtsCmRegStatusPrimaryUsRxPower OBJECT-TYPE
          SYNTAX  Integer32
          UNITS       "0.1dBmV"
          MAX-ACCESS  read-only
          STATUS  current
          DESCRIPTION
                "This object indicates the receive power of the CM's primary upstream channel.
                 -2147483647 represent NULL.
                "
          ::= { hwDocsIf3CmtsCmRegStatusEntry 45 }

    hwDocsIf3CmtsCmRegStatusPrimaryUsTxPower OBJECT-TYPE
          SYNTAX  Integer32
          UNITS       "0.1dBmV"
          MAX-ACCESS  read-only
          STATUS  current
          DESCRIPTION
                "This object indicates the transmit power of the CM's primary upstream channel.
                 -2147483647 represent NULL.
                "
          ::= { hwDocsIf3CmtsCmRegStatusEntry 46 }

    hwDocsIf3CmtsCmRegStatusPrimaryDsTxPower OBJECT-TYPE
          SYNTAX  Integer32
          UNITS       "0.1dBmV"
          MAX-ACCESS  read-only
          STATUS  current
          DESCRIPTION
                "This object indicates the transmit power of the CM's primary downstream channel.
                 -1 represent NULL.
                "
          ::= { hwDocsIf3CmtsCmRegStatusEntry 47 }

    hwDocsIf3CmtsCmRegStatusPrimaryUsSnr OBJECT-TYPE
          SYNTAX  Integer32
          UNITS       "0.1dB"
          MAX-ACCESS  read-only
          STATUS  current
          DESCRIPTION
                "This object indicates the signal-to-noise ratio (SNR) of the CM's primary upstream channel."
          ::= { hwDocsIf3CmtsCmRegStatusEntry 48 }
          
    hwDocsIf3CmtsCmRegStatusVoiceEnabled OBJECT-TYPE
          SYNTAX  INTEGER 
                 {              
                 enable(1),
                 disable(2)
                 }
          MAX-ACCESS  read-only
          STATUS    current
          DESCRIPTION
                "This object indicates whether use voice or not.
                 Options:
                1. enable(1) - Voice is enable
                2. disable(2) - Voice is disable"
          ::= { hwDocsIf3CmtsCmRegStatusEntry 49 }

    hwDocsIf3CmtsCmRegStatusDsChangeTimes OBJECT-TYPE
          SYNTAX  Counter32 
          MAX-ACCESS  read-only
          STATUS    current
          DESCRIPTION
                "This object indicates the times that the CM 
                 changes to use different downstream channels. 
                 4294967295 represents invalid value.
                "
          ::= { hwDocsIf3CmtsCmRegStatusEntry 50 }
                      
    hwDocsIf3CmtsCmRegStatusSnmpProxyUpdateTime OBJECT-TYPE
         SYNTAX  DateAndTime
          MAX-ACCESS  read-only
          STATUS  current
          DESCRIPTION
                "This object indicates time of the latest update of remote cycle query result."
          ::= { hwDocsIf3CmtsCmRegStatusEntry 51 }
                                                                        
    hwDocsIf3CmtsCmRegStatusIPv6Prefix OBJECT-TYPE
          SYNTAX  InetAddressIPv6
          MAX-ACCESS  read-only
          STATUS  current
          DESCRIPTION
                "This attribute indicates the IPv6 prefix of the CM. 
                If the CM has no IPv6 prefix, or the IPv6 prefix is 
                unknown, the value of this attribute is the all zeros prefix."
          ::= { hwDocsIf3CmtsCmRegStatusEntry 52 }

    hwDocsIf3CmtsCmRegStatusIPv6PrefixLength OBJECT-TYPE
          SYNTAX  Unsigned32 (0..128)
          MAX-ACCESS  read-only
          STATUS  current
          DESCRIPTION
                "This attribute indicates the length of the IPv6 prefix."
          ::= { hwDocsIf3CmtsCmRegStatusEntry 53 }

   hwDocsIf3CmtsCmRegStatusPeriodT1Timeouts OBJECT-TYPE
        SYNTAX      Integer32
        UNITS       "timeouts"
        MAX-ACCESS  read-only
        STATUS      current
        DESCRIPTION
                "
                The number of T1 timeouts.
                T1 represents waiting for UCD.
                -1 represents invalid value.
                "
        ::= { hwDocsIf3CmtsCmRegStatusEntry 54 }

   hwDocsIf3CmtsCmRegStatusPeriodT2Timeouts OBJECT-TYPE
        SYNTAX      Integer32
        UNITS       "timeouts"
        MAX-ACCESS  read-only
        STATUS      current
        DESCRIPTION
                "
                The number of T2 timeouts.
                T2 represents waiting for broadcast ranging.
                -1 represents invalid value.
                "
        ::= { hwDocsIf3CmtsCmRegStatusEntry 55 }
  
    hwDocsIf3CmtsCmRegStatusDsPer OBJECT-TYPE
          SYNTAX  Integer32
          UNITS   "0.00001"
          MAX-ACCESS  read-only
          STATUS  current
          DESCRIPTION
                "
                The rate of package error received on the downstream channels.
                -1 represent NULL.
                "
          ::= { hwDocsIf3CmtsCmRegStatusEntry 56 }
          
   hwDocsIf3CmtsCmRegStatusConfigFilenameIPv6 OBJECT-TYPE
          SYNTAX  OCTET STRING(SIZE (0..256))
          MAX-ACCESS  read-only
          STATUS  current
          DESCRIPTION
                "
                This attribute represents the CM config-file Name for IPv6.
                "
          ::= { hwDocsIf3CmtsCmRegStatusEntry 57 }

   hwDocsIf3CmtsCmRegStatusUsPartialChannelMask OBJECT-TYPE
          SYNTAX  OCTET STRING (SIZE (0..16)) 
          MAX-ACCESS  read-only
          STATUS    current
          DESCRIPTION
                "
                Indicates whether the upstream channels is at partial status.
                Indicates the upstream channels 1-16 from left to right.
                The first character represents upstream channel 1.
                The bit value is 1 means the channel is at partial status.
                Empty string indicates the default value. 
                Return a zero-length OCTET STRING to indicate that the modem is not in a partial service mode.
                "
          ::= { hwDocsIf3CmtsCmRegStatusEntry 58 }

   hwDocsIf3CmtsCmRegStatusDsPartialChannelMask OBJECT-TYPE
          SYNTAX  OCTET STRING (SIZE (0..32)) 
          MAX-ACCESS  read-only
          STATUS    current
          DESCRIPTION
                "
                Indicates whether the downstream channels is at partial status.
                Indicates the downstream channels 1-32 from left to right.
                The first character represents downstream channel 1.
                The bit value is 1 means the channel is at partial status.
                Empty string indicates the default value. 
                Return a zero-length OCTET STRING to indicate that the modem is not in a partial service mode.
                "
          ::= { hwDocsIf3CmtsCmRegStatusEntry 59 } 
          
   hwDocsIf3CmtsCmRegStatusRangingClassIDValidFlag OBJECT-TYPE
          SYNTAX  INTEGER {
                           invalid(1),
                           valid(2)
                          }
          MAX-ACCESS  read-only
          STATUS  current
          DESCRIPTION
                "This object indicates the effective identification of the ranging Class ID.
                Options:
                1. invalid(1)  - the invalid ranging Class ID
                2. valid(2)    - the valid ranging Class ID
                Default value: invalid(1)
                "
          ::= { hwDocsIf3CmtsCmRegStatusEntry 60 }
          
    hwDocsIf3CmtsCmRegStatusRangingClassID OBJECT-TYPE
          SYNTAX  Unsigned32
          MAX-ACCESS  read-only
          STATUS  current
          DESCRIPTION
                "This object indicates the ranging Class ID. 
                 The CM indicates support for the Ranging Hold-Off Feature by reporting its Ranging Class ID in the value field.
                 The low order 16 bits of the Ranging Class ID are comprised of a static bit map which indicates the device type.
                 The CM sets the bits of the devices to 1 in the bit map. Only a stand-alone CM will set Bit#0. For example, a
                 standalone CM would report a value of 1; a CM with a CableHome PS or an eRouter would report a value of 2; a
                 CM with a PacketCable MTA and an ePS would report a value of 6; an eSTB would report a value of 8 although it
                 contained an eCM. Bits 16 thru 31 are derived from the Configuration File as described in Annex C.1.1.18.1.4. The
                 Ranging Class ID is not negotiable. The CM MUST ignore the value field in the REG-RSP or REG-RSP-MP.
                 Bit #0: CM                                       
                 Bit #1: ePS or eRouter                           
                 Bit #2: eMTA or EDVA                             
                 Bit #3: DSG/eSTB                                 
                 Bits 4 through 15: Reserved                      
                 Bits 16 through 31: CM Ranging Class ID Extension                
                "
          ::= { hwDocsIf3CmtsCmRegStatusEntry 61 }
          
     hwDocsIf3CmtsCmRegStatusPrimaryUsGoodCodewords OBJECT-TYPE
          SYNTAX  Counter64
          MAX-ACCESS  read-only
          STATUS  current
          DESCRIPTION
                "This attribute represents the codewords received without error from the CM on the primary channel.
                18446744073709551615(0xFFFFFFFFFFFFFFFF) represents invalid value.
                "
          ::= { hwDocsIf3CmtsCmRegStatusEntry 62 }  
       
     hwDocsIf3CmtsCmRegStatusPrimaryUsCorrectedErrorCodewords OBJECT-TYPE
          SYNTAX  Counter64
          MAX-ACCESS  read-only
          STATUS  current
          DESCRIPTION
                "This attribute represents the codewords received with correctable errors from the CM on the primary channel.
                18446744073709551615(0xFFFFFFFFFFFFFFFF) represents invalid value.
                "
          ::= { hwDocsIf3CmtsCmRegStatusEntry 63 }   
     
     hwDocsIf3CmtsCmRegStatusPrimaryUsUncorrectedErrorCodewords OBJECT-TYPE
          SYNTAX  Counter64
          MAX-ACCESS  read-only
          STATUS  current
          DESCRIPTION
                "This attribute represents the codewords received with uncorrectable errors from the CM on the primary channel.
                18446744073709551615(0xFFFFFFFFFFFFFFFF) represents invalid value.
                "
          ::= { hwDocsIf3CmtsCmRegStatusEntry 64 }  
     hwDocsIf3CmtsCmRegStatusPrimaryUsFrequency OBJECT-TYPE
          SYNTAX  Integer32
          UNITS   "Hz"
          MAX-ACCESS  read-only
          STATUS  current
          DESCRIPTION
                "The current used center frequency of the primary upstream interface.
                 This object returns 0 if the frequency is undefined or unknown.
                 Range: 5000000-85000000 for AnnexA
                        5000000-85000000 for AnnexB
                "
          ::= { hwDocsIf3CmtsCmRegStatusEntry 65 }  
                            
     hwDocsIf3CmtsCmRegStatusPrimaryUsChannelWidth OBJECT-TYPE
          SYNTAX  Integer32 (0..64000000)
          UNITS   "Hz"
          MAX-ACCESS  read-only
          STATUS  current
          DESCRIPTION
                "The width of the Primary upstream channel.
                 Range:0..6400000
                "
          ::= { hwDocsIf3CmtsCmRegStatusEntry 66 }  
           
     hwDocsIf3CmtsCmRegStatusPrimaryDsGoodCodewords OBJECT-TYPE
          SYNTAX  Counter64
          MAX-ACCESS  read-only
          STATUS  current
          DESCRIPTION
                "This attribute represents the codewords received without error from the CM on the primary downstream channel.
                18446744073709551615(0xFFFFFFFFFFFFFFFF) represents invalid value.
                "
          ::= { hwDocsIf3CmtsCmRegStatusEntry 67 }  
     
     hwDocsIf3CmtsCmRegStatusPrimaryDsCorrectedErrorCodewords OBJECT-TYPE
          SYNTAX  Counter64
          MAX-ACCESS  read-only
          STATUS  current
          DESCRIPTION
                "This attribute represents the codewords received with correctable errors from the CM on the primary downstream channel.
                18446744073709551615(0xFFFFFFFFFFFFFFFF) represents invalid value.
                "
          ::= { hwDocsIf3CmtsCmRegStatusEntry 68 }  
   
     hwDocsIf3CmtsCmRegStatusPrimaryDsUncorrectedErrorCodewords OBJECT-TYPE
          SYNTAX  Counter64
          MAX-ACCESS  read-only
          STATUS  current
          DESCRIPTION
                "This attribute represents the codewords received with uncorrectable errors from the CM on the primary downstream channel.
                18446744073709551615(0xFFFFFFFFFFFFFFFF) represents invalid value.
                "
          ::= { hwDocsIf3CmtsCmRegStatusEntry 69 } 
   
     hwDocsIf3CmtsCmRegStatusPrimaryDsFrequency OBJECT-TYPE
          SYNTAX  Integer32
          MAX-ACCESS  read-only
          STATUS  current
          DESCRIPTION
                "The frequency of the primary downstream channel.
                 0 represents invalid value.
               "
          ::= { hwDocsIf3CmtsCmRegStatusEntry 70 } 
          
     hwDocsIf3CmtsCmRegStatusServiceTypeID OBJECT-TYPE
            SYNTAX OCTET STRING (SIZE (0..16))
            MAX-ACCESS  read-only
            STATUS current
            DESCRIPTION
                "Indicates the service type identifier in the configuration file.
     Return a zero-length OCTET STRING to indicate that the service type identifier does not exist.                          
                "
         ::= { hwDocsIf3CmtsCmRegStatusEntry 71 }
          
     hwDocsIf3CmtsCmRegStatusUsTxPowerReachMaxFlag OBJECT-TYPE
          SYNTAX  INTEGER {
                           no(1),
                           yes(2)
                          }
          MAX-ACCESS  read-only
          STATUS  current
          DESCRIPTION
                "This object indicates the maximum identification of the uptream channel transmission power.
                Options:
                1. no(1) - CM has not reached the maximum transmit power
                2. yes(2) - CM has reached the maximum transmit power
                Default value: no(1)
                "
          ::= { hwDocsIf3CmtsCmRegStatusEntry 72 }

     hwDocsIf3CmtsCmRegStatusTotalUsPktErrorNum OBJECT-TYPE
          SYNTAX  Counter64
          MAX-ACCESS  read-only
          STATUS  current
          DESCRIPTION
                "This object indicates the error packets received from the CM on the upstream channel.
                 18446744073709551615(0xFFFFFFFFFFFFFFFF) represents invalid value.
          "
          ::= { hwDocsIf3CmtsCmRegStatusEntry 73 } 

     hwDocsIf3CmtsCmRegStatusUsPer OBJECT-TYPE
          SYNTAX  Integer32
          UNITS   "0.00001"
          MAX-ACCESS  read-only
          STATUS  current
          DESCRIPTION
                "The rate of error packets received on the upstream channels.
           -1 represent NULL."
          ::= { hwDocsIf3CmtsCmRegStatusEntry 74 }
          
     hwDocsIf3CmtsCmRegStatusCrc OBJECT-TYPE
          SYNTAX  Counter64
          MAX-ACCESS  read-only
          STATUS  current
          DESCRIPTION
                "This object indicates the CRC failures of the upstream channel for the CM.
                 18446744073709551615(0xFFFFFFFFFFFFFFFF) represents invalid value.
          "
          ::= { hwDocsIf3CmtsCmRegStatusEntry 75 }
          
     hwDocsIf3CmtsCmRegStatusHcs OBJECT-TYPE
          SYNTAX  Counter64
          MAX-ACCESS  read-only
          STATUS  current
          DESCRIPTION
                "This object indicates the HCS failures of the upstream channel for the CM.
                 18446744073709551615(0xFFFFFFFFFFFFFFFF) represents invalid value.
          "
          ::= { hwDocsIf3CmtsCmRegStatusEntry 76 }          

     hwDocsIf3CmtsCmRegStatusOfdmMTC OBJECT-TYPE
          SYNTAX  INTEGER {
                           enable(1),
                           disable(2),
                           invalidValue(-1)
                          }
          MAX-ACCESS  read-only
          STATUS  current
          DESCRIPTION
                "The status of the multi transmit OFDM channel.
                Options:
                1. enable(1) - enable the multi transmit channel
                2. disable(2) - disable the multi transmit channel
                3. invalidValue(-1) - invalid value
                "
          ::= { hwDocsIf3CmtsCmRegStatusEntry 77 } 
 
     hwDocsIf3CmtsCmRegStatusOfdmProfileCapability OBJECT-TYPE
          SYNTAX  Integer32(0|5..16)
          MAX-ACCESS  read-only
          STATUS  current
          DESCRIPTION
                "Indicates the number of the OFAM downstream channel profile support.
                 0 represents invalid value.
          "
          ::= { hwDocsIf3CmtsCmRegStatusEntry 78 }

     hwDocsIf3CmtsCmRegStatusUsBondingGroupId OBJECT-TYPE
          SYNTAX  Unsigned32  (0..4294967295)
          MAX-ACCESS  read-only
          STATUS  current
          DESCRIPTION
                "Indicates the upstream bonding group ID. 4294967295(0xFFFFFFFF) represents invalid value.
          "
          ::= { hwDocsIf3CmtsCmRegStatusEntry 79 } 
          
     hwDocsIf3CmtsCmRegStatusDsBondingGroupId OBJECT-TYPE
          SYNTAX  Unsigned32  (0..4294967295)
          MAX-ACCESS  read-only
          STATUS  current
          DESCRIPTION
                "Indicates the downstream bonding group ID. 4294967295(0xFFFFFFFF) represents invalid value.
          "
          ::= { hwDocsIf3CmtsCmRegStatusEntry 80 } 
          
     hwDocsIf3CmtsCmRegStatusRccCfgId OBJECT-TYPE
          SYNTAX  Unsigned32  (0..4294967295)
          MAX-ACCESS  read-only
          STATUS  current
          DESCRIPTION
                "Indicates the MAC RCC template ID. 4294967295(0xFFFFFFFF) represents invalid value.
          "
          ::= { hwDocsIf3CmtsCmRegStatusEntry 81 }    
          
     hwDocsIf3CmtsCmRegStatusDsRequiredMask OBJECT-TYPE
          SYNTAX  AttributeMask
          MAX-ACCESS  read-only
          STATUS  current
          DESCRIPTION
                "Indicates the downstream required mask of CM register status.
          "
          ::= { hwDocsIf3CmtsCmRegStatusEntry 82 }    
          
     hwDocsIf3CmtsCmRegStatusDsForbiddenMask OBJECT-TYPE
          SYNTAX  AttributeMask
          MAX-ACCESS  read-only
          STATUS  current
          DESCRIPTION
                "Indicates the downstream forbidden mask of CM register status.
          "
          ::= { hwDocsIf3CmtsCmRegStatusEntry 83 }    
          
     hwDocsIf3CmtsCmRegStatusUsRequiredMask OBJECT-TYPE
          SYNTAX  AttributeMask
          MAX-ACCESS  read-only
          STATUS  current
          DESCRIPTION
                "Indicates the upstream required mask of CM register status.
          "
          ::= { hwDocsIf3CmtsCmRegStatusEntry 84 }    
          
     hwDocsIf3CmtsCmRegStatusUsForbiddenMask OBJECT-TYPE
          SYNTAX  AttributeMask
          MAX-ACCESS  read-only
          STATUS  current
          DESCRIPTION
                "Indicates the upstream forbidden mask of CM register status.
          "
          ::= { hwDocsIf3CmtsCmRegStatusEntry 85 }        
            
     hwDocsIf3CmtsCmRegStatusCurrentServiceTypeID OBJECT-TYPE
          SYNTAX OCTET STRING (SIZE (0..16))
          MAX-ACCESS read-only
          STATUS current 

          DESCRIPTION
           "This attribute represents the service type ID the
            CMTS picked from the restricted group of restricted
            CM list, or the service type ID TLV the CM signaled 
            to the CMTS during registration, or the zero-length 
            string if none was used.
                "
        ::= { hwDocsIf3CmtsCmRegStatusEntry 86 }

     hwDocsIf3CmtsCmRegStatusCurrentPolicyID OBJECT-TYPE
          SYNTAX  Unsigned32  (0..4294967295)
          MAX-ACCESS  read-only
          STATUS  current
          DESCRIPTION
                "This attribute references the load balancing policy ID
                associated to the cable modem either from the configuration
                file or from the general or restrictedload balancing groups 
                CMTS configuration. 
                4294967295(0xFFFFFFFF) represents invalid value.
              "
          ::= { hwDocsIf3CmtsCmRegStatusEntry 87 }        

     hwDocsIf3CmtsCmRegStatusPolicyIDinCfgFile OBJECT-TYPE
          SYNTAX  Unsigned32  (0..4294967295)
          MAX-ACCESS  read-only
          STATUS  current
          DESCRIPTION
                "Indicates the policy ID in the configuration file.
                4294967295(0xFFFFFFFF) represents invalid value. 
                "
          ::= { hwDocsIf3CmtsCmRegStatusEntry 88 }  

     hwDocsIf3CmtsCmRegStatusCurrentPriority OBJECT-TYPE
          SYNTAX  Unsigned32  (0..4294967295)
          MAX-ACCESS  read-write
          STATUS  current
          DESCRIPTION
             "This attribute references the load balancing priority
           associated to the cable modem either from the configuration
           file or from the general or restricted load balancing groups 
           CMTS configuration.
           4294967295(0xFFFFFFFF) represents invalid value. 
           "
          ::= { hwDocsIf3CmtsCmRegStatusEntry 89 }    
      
     hwDocsIf3CmtsCmRegStatusPriorityinCfgFile OBJECT-TYPE
          SYNTAX  Unsigned32  (0..4294967295)
          MAX-ACCESS  read-write
          STATUS  current
          DESCRIPTION
                "Indicates the priority in the configuration file.
                4294967295(0xFFFFFFFF) represents invalid value.  
                "
          ::= { hwDocsIf3CmtsCmRegStatusEntry 90 }    
        
     hwDocsIf3CmtsCmRegStatusOfdmaPartialChannelMask OBJECT-TYPE
          SYNTAX  OCTET STRING (SIZE (0..4)) 
          MAX-ACCESS  read-only
          STATUS    current
          DESCRIPTION
                "
                Indicates whether the ofdma upstream channels is at partial status.
                Indicates the upstream channels 17-20 from left to right.
                The first character represents upstream channel 17.
                The bit value is 1 means the channel is at partial status.
                Empty string indicates the default value. 
                Return a zero-length OCTET STRING to indicate that the modem is not in a partial service mode.
                "
          ::= { hwDocsIf3CmtsCmRegStatusEntry 91 } 
          
     hwDocsIf3CmtsCmRegStatusOfdmPartialChannelMask OBJECT-TYPE
          SYNTAX  OCTET STRING (SIZE (0..8)) 
          MAX-ACCESS  read-only
          STATUS    current
          DESCRIPTION
                "
                Indicates whether the ofdm downstream channels is at partial status.
                Indicates the downstream channels 97-104 from left to right.
                The first character represents downstream channel 97.
                The bit value is 1 means the channel is at partial status.
                Empty string indicates the default value. 
                Return a zero-length OCTET STRING to indicate that the modem is not in a partial service mode.
                "
          ::= { hwDocsIf3CmtsCmRegStatusEntry 92 }                   
  -- Table hwDocsIf3CmtsCmUsStatusTable
    hwDocsIf3CmtsCmUsStatusTable OBJECT-TYPE
          SYNTAX     SEQUENCE OF HwDocsIf3CmtsCmUsStatusEntry
          MAX-ACCESS not-accessible
          STATUS     current
          DESCRIPTION
               "This table describes the information of the upstream channel
                which the cable modem location.
                The indexes of this table are docsIf3CmtsCmRegStatusId
                and docsIf3CmtsCmUsStatusChIfIndex.
               "
          ::= { hwCmtsAccessObject 4 }

    hwDocsIf3CmtsCmUsStatusEntry OBJECT-TYPE
          SYNTAX     HwDocsIf3CmtsCmUsStatusEntry
          MAX-ACCESS not-accessible
          STATUS     current
          DESCRIPTION
               "This table describes the information of the upstream channel
                which the cable modem location.
                The indexes of this entry are docsIf3CmtsCmRegStatusId
                and docsIf3CmtsCmUsStatusChIfIndex.
               "
          INDEX       { docsIf3CmtsCmRegStatusId, docsIf3CmtsCmUsStatusChIfIndex }
          ::= { hwDocsIf3CmtsCmUsStatusTable 1 }

    HwDocsIf3CmtsCmUsStatusEntry ::=
          SEQUENCE {
                    hwDocsIf3CmtsCmUsStatusTxPower               Integer32,
                    hwDocsIf3CmtsCmUsStatusInitialTimingOffset   Unsigned32,
                    hwDocsIf3CmtsCmUsStatusPhyOperatingMode      INTEGER,
                    hwDocsIf3CmtsCmUsStatusTxTimingOffset        Integer32,
                    hwDocsIf3CmtsCmUsGoodCodewords                 Counter64,
                    hwDocsIf3CmtsCmUsCorrectedErrorCodewords       Counter64,
                    hwDocsIf3CmtsCmUsUncorrectedErrorCodewords     Counter64,
                    hwDocsIf3CmtsCmUsStatusMaxTxPower              Integer32,
                    hwDocsIf3CmtsCmUsStatusMinTxPower              Integer32,
                    hwDocsIf3CmtsCmUsStatusPeriodT3Timeouts        Integer32,
                    hwDocsIf3CmtsCmUsStatusPeriodT4Timeouts        Integer32,
                    hwDocsIf3CmtsCmUsStatusUtilization             Counter32,
                    hwDocsIf3CmtsCmUsStatusEqdData                 DocsEqualizerData,
                    hwdocsIf3CmtsCmUsStatusFrequency               Integer32,
                    hwdocsIf3CmtsCmUsStatusChannelWidth            Integer32,
                    hwDocsIf3CmtsCmUsStatusMinSignalNoise          Integer32,
                    hwDocsIf3CmtsCmUsStatusMaxSignalNoise          Integer32
                   }

    hwDocsIf3CmtsCmUsStatusTxPower OBJECT-TYPE
          SYNTAX  Integer32
          UNITS   "0.1 dBmV"
          MAX-ACCESS  read-only
          STATUS  current
          DESCRIPTION
                "Upstream Transmit Power.
                 -2147483647 represent NULL.
                "
          ::= { hwDocsIf3CmtsCmUsStatusEntry 1 }

    hwDocsIf3CmtsCmUsStatusInitialTimingOffset OBJECT-TYPE
          SYNTAX  Unsigned32 (0..4294967295)
          MAX-ACCESS  read-only
          STATUS  current
          DESCRIPTION
                "Initial Timing Offset.
                4294967295 represent NULL"
          ::= { hwDocsIf3CmtsCmUsStatusEntry 2 }

    hwDocsIf3CmtsCmUsStatusPhyOperatingMode OBJECT-TYPE
          SYNTAX  INTEGER {
                           tdma(1),
                           atdma(2),
                           scdma(3),
                           tdmaandatdma(4)
                          }
          MAX-ACCESS  read-only
          STATUS  current
          DESCRIPTION
                "Phy Operating Mode.
                Options:
                1. tdma(1) - Time Division Multiple Access
                2. atdma(2) - Advanced Time Division Multiple Access
                3. scdma(3) - Synchronous Code Division Multiple Access
                4. tdmaandatdma(4) - Time Division Multiple Access and Advanced Time Division Multiple Access
                                                                "
          ::= { hwDocsIf3CmtsCmUsStatusEntry 3 }

    hwDocsIf3CmtsCmUsStatusTxTimingOffset OBJECT-TYPE
          SYNTAX  Integer32
          UNITS   "97.6ns(6.25/64 microseconds)"
          MAX-ACCESS  read-only
          STATUS  current
          DESCRIPTION
                "
                Indicates the send time offset of up channel of CM.
                -1 represent NULL.
                "
           ::= { hwDocsIf3CmtsCmUsStatusEntry 4 }
    hwDocsIf3CmtsCmUsGoodCodewords OBJECT-TYPE
          SYNTAX  Counter64
          MAX-ACCESS  read-only
          STATUS  current
          DESCRIPTION
                "
                This attribute represents the codewords received
                without error from the CM on this channel.
                18446744073709551615(0xFFFFFFFFFFFFFFFF) represents invalid value.
                "
          ::= { hwDocsIf3CmtsCmUsStatusEntry 5 }

    hwDocsIf3CmtsCmUsCorrectedErrorCodewords OBJECT-TYPE
          SYNTAX  Counter64
          MAX-ACCESS  read-only
          STATUS  current
          DESCRIPTION
                "
                This attribute represents the codewords received
                with correctable errors from the CM on this channel.
                18446744073709551615(0xFFFFFFFFFFFFFFFF) represents invalid value.
                "
          ::= { hwDocsIf3CmtsCmUsStatusEntry 6 }

    hwDocsIf3CmtsCmUsUncorrectedErrorCodewords OBJECT-TYPE
          SYNTAX  Counter64
          MAX-ACCESS  read-only
          STATUS  current
          DESCRIPTION
                "
                This attribute represents the codewords received
                with uncorrectable errors from the CM on this channel.
                18446744073709551615(0xFFFFFFFFFFFFFFFF) represents invalid value.
                "
          ::= { hwDocsIf3CmtsCmUsStatusEntry 7 }
                  
    hwDocsIf3CmtsCmUsStatusMaxTxPower OBJECT-TYPE
          SYNTAX  Integer32
          UNITS   "0.1dBmV"
          MAX-ACCESS  read-only
          STATUS  current
          DESCRIPTION
                "
                This attribute represents the maximum transmit power of the upstream channel.
                -2147483647 represents invalid value.
                "
          ::= { hwDocsIf3CmtsCmUsStatusEntry 8 }
                  
    hwDocsIf3CmtsCmUsStatusMinTxPower OBJECT-TYPE
          SYNTAX  Integer32
          UNITS   "0.1dBmV"
          MAX-ACCESS  read-only
          STATUS  current
          DESCRIPTION
                "
                This attribute represents the minimum transmit power of the upstream channel.
                -2147483647 represents invalid value.
                "
          ::= { hwDocsIf3CmtsCmUsStatusEntry 9 }

   hwDocsIf3CmtsCmUsStatusPeriodT3Timeouts OBJECT-TYPE
        SYNTAX      Integer32
        UNITS       "timeouts"
        MAX-ACCESS  read-only
        STATUS      current
        DESCRIPTION
            "Number of times counter T3 expired in the CM.
             T3 represents waiting for ranging response.
             -1 represents invalid value.
            "
        ::= { hwDocsIf3CmtsCmUsStatusEntry 10 }

   hwDocsIf3CmtsCmUsStatusPeriodT4Timeouts OBJECT-TYPE
        SYNTAX      Integer32
        UNITS       "timeouts"
        MAX-ACCESS  read-only
        STATUS      current
        DESCRIPTION
            "Number of times counter T4 expired in the CM.
             T4 represents waiting for unicast ranging opportunity.
             -1 represents invalid value.
            "
        ::= { hwDocsIf3CmtsCmUsStatusEntry 11 }
                  
                  
    hwDocsIf3CmtsCmUsStatusUtilization OBJECT-TYPE
          SYNTAX  Counter32
          UNITS   "%"
          MAX-ACCESS  read-only
          STATUS  current
          DESCRIPTION
                "
                CM traffic ratio on the upstream channel.
                "
          ::= { hwDocsIf3CmtsCmUsStatusEntry 12 }
          
    hwDocsIf3CmtsCmUsStatusEqdData OBJECT-TYPE
     SYNTAX      DocsEqualizerData
     MAX-ACCESS  read-only
     STATUS      current
     DESCRIPTION
        "This attribute indicates the pre-equalization data
        for the specified upstream Channel on this CM after
        convolution with data indicated in the RNG-RSP. This
        data is valid when hwdocsIf3MdCfgUsPreEqEnable RFC 
        4546 is set to true."
     ::= { hwDocsIf3CmtsCmUsStatusEntry 13 }           
  
    hwdocsIf3CmtsCmUsStatusFrequency OBJECT-TYPE
          SYNTAX  Integer32
          UNITS   "Hz"
          MAX-ACCESS  read-only
          STATUS  current
          DESCRIPTION
                "The current used center frequency of the primary upstream interface.
                 This object returns 0 if the frequency is undefined or unknown.
                 Range: 5000000-85000000 for AnnexA
                        5000000-85000000 for AnnexB
                "
          ::= { hwDocsIf3CmtsCmUsStatusEntry 14 }  
                            
     hwdocsIf3CmtsCmUsStatusChannelWidth OBJECT-TYPE
          SYNTAX  Integer32 (0..64000000)
          UNITS   "Hz"
          MAX-ACCESS  read-only
          STATUS  current
          DESCRIPTION
                "The width of the Primary upstream channel.
                 Range:0..6400000
                "
          ::= { hwDocsIf3CmtsCmUsStatusEntry 15 }              
              
          
     hwDocsIf3CmtsCmUsStatusMinSignalNoise OBJECT-TYPE
          SYNTAX      Integer32
          UNITS       "TenthdB"
          MAX-ACCESS  read-only
          STATUS      current
          DESCRIPTION
             "This attribute represents minimum Signal/Noise ratio as
             perceived for upstream data from the CM on this upstream
             channel. -0x7fffffff represents invalid value."
          ::= { hwDocsIf3CmtsCmUsStatusEntry 16 } 
          
     hwDocsIf3CmtsCmUsStatusMaxSignalNoise OBJECT-TYPE
          SYNTAX      Integer32
          UNITS       "TenthdB"
          MAX-ACCESS  read-only
          STATUS      current
          DESCRIPTION
             "This attribute represents maximum Signal/Noise ratio as
             perceived for upstream data from the CM on this upstream
             channel. -0x7fffffff represents invalid value."
          ::= { hwDocsIf3CmtsCmUsStatusEntry 17 }
                            
  -- Table hwDocsIf3CmtsCmDownChannelInfoTable
    hwDocsIf3CmtsCmDownChannelInfoTable OBJECT-TYPE
          SYNTAX     SEQUENCE OF HwDocsIf3CmtsCmDownChannelInfoEntry
          MAX-ACCESS not-accessible
          STATUS     current
          DESCRIPTION
               "This table describes the information of the downstream channel
                which the cable modem location.
                The indexes of this table are docsIf3CmtsCmRegStatusId
                and hwDocsIf3CmtsCmDownChannelInfoChannelId.
               "
          ::= { hwCmtsAccessObject 5 }

    hwDocsIf3CmtsCmDownChannelInfoEntry OBJECT-TYPE
          SYNTAX     HwDocsIf3CmtsCmDownChannelInfoEntry
          MAX-ACCESS not-accessible
          STATUS     current
          DESCRIPTION
               "This table describes the information of the downstream channel
                which the cable modem location.
                The indexes of this entry are docsIf3CmtsCmRegStatusId
                and hwDocsIf3CmtsCmDownChannelInfoChannelId.
               "
          INDEX       { docsIf3CmtsCmRegStatusId, hwDocsIf3CmtsCmDownChannelInfoChannelId }
          ::= { hwDocsIf3CmtsCmDownChannelInfoTable 1 }

    HwDocsIf3CmtsCmDownChannelInfoEntry ::=
          SEQUENCE {
                    hwDocsIf3CmtsCmDownChannelInfoChannelId  Integer32,
                    hwDocsIf3CmtsCmDownChannelInfoPower      Integer32,
                    hwDocsIf3CmtsCmDownChannelInfoRxPower    Integer32,
                    hwDocsIf3CmtsCmDownChannelInfoSnr        Integer32,
                    hwDocsIf3CmtsCmDownChannelInfoMer        Integer32,
                    hwDocsIf3CmtsCmDownChannelInfoMerSamples Unsigned32,
                    hwDocsIf3CmtsCmDownChannelInfoMicroreflections Integer32,
        hwDocsIf3CmtsCmDownChannelInfoUncorrectedErrorCode Counter64,
                    hwDocsIf3CmtsCmDownChannelInfoCorrectedErrorCode   Counter64,
                    hwDocsIf3CmtsCmDownChannelInfoGoodCode    Counter64,
                    hwDocsIf3CmtsCmDownChannelInfoUtilization Counter32,
                    hwDocsIf3CmtsCmDownChannelInfoFrequency   Integer32,
                    hwDocsIf3CmtsCmDownChannelInfoMinRxPower  Integer32,
                    hwDocsIf3CmtsCmDownChannelInfoMaxRxPower  Integer32,
                    hwDocsIf3CmtsCmDownChannelInfoMinSnr      Integer32,
                    hwDocsIf3CmtsCmDownChannelInfoMaxSnr      Integer32
                   }

    hwDocsIf3CmtsCmDownChannelInfoChannelId OBJECT-TYPE
          SYNTAX  Integer32 (1..32)
          MAX-ACCESS  not-accessible
          STATUS  current
          DESCRIPTION
                "The downstream channel ID.
                 Range: 1..32
                "
          ::= { hwDocsIf3CmtsCmDownChannelInfoEntry 1 }

    hwDocsIf3CmtsCmDownChannelInfoPower OBJECT-TYPE
          SYNTAX  Integer32
          UNITS   "0.1 dBmV"
          MAX-ACCESS  read-only
          STATUS  current
          DESCRIPTION
                "Downstream Transmit Power.
                 -1 represent NULL.
                "
          ::= { hwDocsIf3CmtsCmDownChannelInfoEntry 2 }
    hwDocsIf3CmtsCmDownChannelInfoRxPower OBJECT-TYPE
          SYNTAX  Integer32
          UNITS   "0.1dBmV"
          MAX-ACCESS  read-only
          STATUS  current
          DESCRIPTION
                "
                Indicates the downstream receive power of cable modem.
                -2147483647 represent NULL.
                "
          ::= { hwDocsIf3CmtsCmDownChannelInfoEntry 3 }
    hwDocsIf3CmtsCmDownChannelInfoSnr OBJECT-TYPE
          SYNTAX  Integer32
          UNITS   "0.1dB"
          MAX-ACCESS  read-only
          STATUS  current
          DESCRIPTION
                "
                The downstream snr of cable modem.
                -1 represent NULL.
                "
          ::= { hwDocsIf3CmtsCmDownChannelInfoEntry 4 }
          
    hwDocsIf3CmtsCmDownChannelInfoMer OBJECT-TYPE
          SYNTAX  Integer32(-2147483648..2147483647)
          UNITS   "0.1dB"
          MAX-ACCESS  read-only
          STATUS  current
          DESCRIPTION
                "
                 The modulation error ratio (MER) of downstream channel.
                2147483647 represent NULL.
                "
          ::= { hwDocsIf3CmtsCmDownChannelInfoEntry 5 }
          
          
    hwDocsIf3CmtsCmDownChannelInfoMerSamples OBJECT-TYPE
          SYNTAX  Unsigned32
          MAX-ACCESS  read-only
          STATUS  current
          DESCRIPTION
                "
                The modulation error ratio (MER) samples of downstream channel.
                0xffffffff represent NULL.
                "
          ::= { hwDocsIf3CmtsCmDownChannelInfoEntry 6 }
          
    hwDocsIf3CmtsCmDownChannelInfoMicroreflections OBJECT-TYPE
          SYNTAX  Integer32
          UNITS   "-dBc"
          MAX-ACCESS  read-only
          STATUS  current
          DESCRIPTION
                "
                The micro reflections of downstream channel.
                -1 represent NULL.
                "
          ::= { hwDocsIf3CmtsCmDownChannelInfoEntry 7 }
          
    hwDocsIf3CmtsCmDownChannelInfoUncorrectedErrorCode OBJECT-TYPE
          SYNTAX  Counter64
          MAX-ACCESS  read-only
          STATUS  current
          DESCRIPTION
                "
                This attribute represents the codewords received
                with uncorrectable errors from the CM on this downstream channel.
                18446744073709551615(0xFFFFFFFFFFFFFFFF) represents invalid value.
                "
          ::= { hwDocsIf3CmtsCmDownChannelInfoEntry 8 }                    
          
    hwDocsIf3CmtsCmDownChannelInfoCorrectedErrorCode OBJECT-TYPE
          SYNTAX  Counter64
          MAX-ACCESS  read-only
          STATUS  current
          DESCRIPTION
                "
                This attribute represents the codewords received
                with correctable errors from the CM on this downstream channel.
                18446744073709551615(0xFFFFFFFFFFFFFFFF) represents invalid value.
                "
          ::= { hwDocsIf3CmtsCmDownChannelInfoEntry 9 }
          
    hwDocsIf3CmtsCmDownChannelInfoGoodCode OBJECT-TYPE
          SYNTAX  Counter64
          MAX-ACCESS  read-only
          STATUS  current
          DESCRIPTION
                "
                This attribute represents the codewords received
                without error from the CM on this downstream channel.
                18446744073709551615(0xFFFFFFFFFFFFFFFF) represents invalid value.
                "
          ::= { hwDocsIf3CmtsCmDownChannelInfoEntry 10 }
    
    hwDocsIf3CmtsCmDownChannelInfoUtilization OBJECT-TYPE
          SYNTAX  Counter32
          UNITS   "%"
          MAX-ACCESS  read-only
          STATUS  current
          DESCRIPTION
                "
                CM traffic ratio on the downstream channel.
                "
          ::= { hwDocsIf3CmtsCmDownChannelInfoEntry 11 }
    hwDocsIf3CmtsCmDownChannelInfoFrequency OBJECT-TYPE
          SYNTAX  Integer32 (0|54000000..1002000000)
          UNITS   "Hz"
          MAX-ACCESS  read-only
          STATUS  current
          DESCRIPTION
                "
                The frequency of the downstream channel.
                Range: 0|54000000-1002000000                
                0 represents invalid value.
                "
          ::= { hwDocsIf3CmtsCmDownChannelInfoEntry 12 }
          
    hwDocsIf3CmtsCmDownChannelInfoMinRxPower OBJECT-TYPE
          SYNTAX  Integer32
          UNITS   "0.1dBmV"
          MAX-ACCESS  read-only
          STATUS  current
          DESCRIPTION
                "
                Indicates the minimum downstream receive power of cable modem.
                -0x7fffffff represent NULL.
                "
          ::= { hwDocsIf3CmtsCmDownChannelInfoEntry 13 }      
              
    hwDocsIf3CmtsCmDownChannelInfoMaxRxPower OBJECT-TYPE
          SYNTAX  Integer32
          UNITS   "0.1dBmV"
          MAX-ACCESS  read-only
          STATUS  current
          DESCRIPTION
                "
                Indicates the maximum downstream receive power of cable modem.
                -0x7fffffff represent NULL.
                "
          ::= { hwDocsIf3CmtsCmDownChannelInfoEntry 14 }    
                
    hwDocsIf3CmtsCmDownChannelInfoMinSnr OBJECT-TYPE
          SYNTAX  Integer32
          UNITS   "0.1dB"
          MAX-ACCESS  read-only
          STATUS  current
          DESCRIPTION
                "
                The minimum downstream snr of cable modem.
                -1 represent NULL.
                "
          ::= { hwDocsIf3CmtsCmDownChannelInfoEntry 15 }    
          
    hwDocsIf3CmtsCmDownChannelInfoMaxSnr OBJECT-TYPE
          SYNTAX  Integer32
          UNITS   "0.1dB"
          MAX-ACCESS  read-only
          STATUS  current
          DESCRIPTION
                "
                The maximum downstream snr of cable modem.
                -1 represent NULL.
                "
          ::= { hwDocsIf3CmtsCmDownChannelInfoEntry 16}
                          
      -- Table hwDocsIf3CmtsCmCpeInfoTable begin
    hwDocsIf3CmtsCmCpeInfoTable OBJECT-TYPE
          SYNTAX     SEQUENCE OF HwDocsIf3CmtsCmCpeInfoEntry
          MAX-ACCESS not-accessible
          STATUS     current
          DESCRIPTION
               "This table describes the information of the CPE.
                The indexes of this table are docsIf3CmtsCmRegStatusId
                and hwDocsIf3CmtsCmCpeInfoCpeId.
               "
          ::= { hwCmtsAccessObject 6 }

    hwDocsIf3CmtsCmCpeInfoEntry OBJECT-TYPE
          SYNTAX     HwDocsIf3CmtsCmCpeInfoEntry
          MAX-ACCESS not-accessible
          STATUS     current
          DESCRIPTION
               "This table describes the information of the CPE.
                The indexes of this entry are docsIf3CmtsCmRegStatusId
                and hwDocsIf3CmtsCmCpeInfoCpeId.
               "
          INDEX       { docsIf3CmtsCmRegStatusId, hwDocsIf3CmtsCmCpeInfoCpeId }
          ::= { hwDocsIf3CmtsCmCpeInfoTable 1 }

    HwDocsIf3CmtsCmCpeInfoEntry ::=
          SEQUENCE {
                    hwDocsIf3CmtsCmCpeInfoCpeId       Integer32,
                    hwDocsIf3CmtsCmCpeInfoMacAddr     MacAddress,
                    hwDocsIf3CmtsCmCpeInfoIPv4Addr    IpAddress,
                    hwDocsIf3CmtsCmCpeInfoDeviceDesc  OCTET STRING,
                    hwDocsIf3CmtsCmCpeInfoIPv6Addr    InetAddressIPv6,
                    hwDocsIf3CmtsCmCpeInfoIPv6Prefix  InetAddressIPv6,
                    hwDocsIf3CmtsCmCpeInfoIPv6PrefixLength Unsigned32,
                    hwDocsIf3CmtsCmCpeInfoIPv6LinkLocal InetAddressIPv6
                   }

    hwDocsIf3CmtsCmCpeInfoCpeId OBJECT-TYPE
          SYNTAX  Integer32 (0..511)
          MAX-ACCESS  not-accessible
          STATUS  current
          DESCRIPTION
                "The CPE ID.
                 Range: 0..511
                "
          ::= { hwDocsIf3CmtsCmCpeInfoEntry 1 }

    hwDocsIf3CmtsCmCpeInfoMacAddr OBJECT-TYPE
          SYNTAX  MacAddress
          MAX-ACCESS  read-only
          STATUS  current
          DESCRIPTION
                "This attribute represents the MAC address of the CPE."
          ::= { hwDocsIf3CmtsCmCpeInfoEntry 2 }

    hwDocsIf3CmtsCmCpeInfoIPv4Addr OBJECT-TYPE
          SYNTAX  IpAddress
          MAX-ACCESS  read-only
          STATUS  current
          DESCRIPTION
                "This attribute represents the IPv4 address of the CPE.
                If the CPE has no Internet address assigned, or the 
                Internet address is unknown, the value of this attribute
                is the all zeros address."
          ::= { hwDocsIf3CmtsCmCpeInfoEntry 3 }

    hwDocsIf3CmtsCmCpeInfoDeviceDesc OBJECT-TYPE
          SYNTAX  OCTET STRING (SIZE(0..8))
          MAX-ACCESS  read-only
          STATUS  current
          DESCRIPTION
                "This object indicates the CPE description."
          ::= { hwDocsIf3CmtsCmCpeInfoEntry 4 }
                  
    hwDocsIf3CmtsCmCpeInfoIPv6Addr OBJECT-TYPE
          SYNTAX  InetAddressIPv6
          MAX-ACCESS   read-only
          STATUS  current
          DESCRIPTION
                "This attribute represents the IPv6 address of the CPE. 
                 If the CPE has no Internet address assigned, or the 
                 Internet address is unknown, the value of this attribute
                 is the all zeros address."
          ::= { hwDocsIf3CmtsCmCpeInfoEntry 5 }
    
    hwDocsIf3CmtsCmCpeInfoIPv6Prefix OBJECT-TYPE
          SYNTAX  InetAddressIPv6
          MAX-ACCESS  read-only
          STATUS  current
          DESCRIPTION
                "This attribute represents the IPv6 prefix of the CPE. 
                If the CPE has no IPv6 prefix, or the IPv6 prefix is 
                unknown, the value of this attribute is the all zeros prefix."
          ::= { hwDocsIf3CmtsCmCpeInfoEntry 6 }

    hwDocsIf3CmtsCmCpeInfoIPv6PrefixLength OBJECT-TYPE
          SYNTAX  Unsigned32 (0..128)
          MAX-ACCESS  read-only
          STATUS  current
          DESCRIPTION
                "This attribute indicates the length of the IPv6 prefix."
          ::= { hwDocsIf3CmtsCmCpeInfoEntry 7 }
          
    hwDocsIf3CmtsCmCpeInfoIPv6LinkLocal OBJECT-TYPE
          SYNTAX  InetAddressIPv6
          MAX-ACCESS   read-only
          STATUS  current
          DESCRIPTION
                "This attribute represents the IPv6 local scope address
                 of the CPE. If the CPE has no link local address assigned,
                 or the Internet address is unknown, the value
                 of this attribute is the all zeros address."
          ::= { hwDocsIf3CmtsCmCpeInfoEntry 8 }
                    
      -- Table hwDocsIf3CmtsCmCpeInfoTable end

  hwCmtsAdmissionCtrlTable OBJECT IDENTIFIER ::= { hwCmtsAccessObject  8}
    -- Table hwCmtsAdmissionCtrlTable
    hwCmtsAdmissionCtrlCmRegistrationSwitch OBJECT-TYPE
          SYNTAX  INTEGER {enable(1),disable(2)}
          MAX-ACCESS  read-write
          STATUS  current
          DESCRIPTION
                "Indicates the switch of cable modem register admission.
                Options:
                1. enable(1)     -Enable the cable modem registration switch
                2. disable(2)    -Disable the cable modem registration switch
                "
          ::= { hwCmtsAdmissionCtrlTable 1 }

    hwCmtsAdmissionCtrlDynamicServiceSwitch OBJECT-TYPE
          SYNTAX  INTEGER {enable(1),disable(2)}
          MAX-ACCESS  read-write
          STATUS  current
          DESCRIPTION
                "Indicates the switch of dynamic service admission control.
                Options:
                1. enable(1)     -Enable the dynamic service admission switch
                2. disable(2)    -Disable the dynamic service admission switch
                "
          ::= { hwCmtsAdmissionCtrlTable 2 }

 -- Table hwCmtsAdmissionCtrlTypeTable
    hwCmtsAdmissionCtrlTypeTable OBJECT-TYPE
          SYNTAX     SEQUENCE OF HwCmtsAdmissionCtrlTypeEntry
          MAX-ACCESS not-accessible
          STATUS     current
          DESCRIPTION
               "Indicates the admission control type configuration.
               The index of this table is hwCmtsAdmissionCtrlType.
               "
          ::= { hwCmtsAccessObject 9 }

    hwCmtsAdmissionCtrlTypeEntry OBJECT-TYPE
          SYNTAX     HwCmtsAdmissionCtrlTypeEntry
          MAX-ACCESS not-accessible
          STATUS     current
          DESCRIPTION
               "Indicates the admission control type configuration.
               The index of this entry is hwCmtsAdmissionCtrlType.
               "
          INDEX       { hwCmtsAdmissionCtrlType }
          ::= { hwCmtsAdmissionCtrlTypeTable 1 }

    HwCmtsAdmissionCtrlTypeEntry ::=
          SEQUENCE {
                    hwCmtsAdmissionCtrlType      Integer32,
                    hwCmtsAdmissionCtrlTypeName  OCTET STRING
                   }

    hwCmtsAdmissionCtrlType OBJECT-TYPE
          SYNTAX  Integer32 (0..7)
          MAX-ACCESS  not-accessible
          STATUS  current
          DESCRIPTION
                "Indicates the admission control type."
          ::= { hwCmtsAdmissionCtrlTypeEntry 1 }

    hwCmtsAdmissionCtrlTypeName OBJECT-TYPE
          SYNTAX      OCTET STRING(SIZE (0..32))
          MAX-ACCESS  read-write
          STATUS  current
          DESCRIPTION
                "Indicates the name of admission control type."
          ::= { hwCmtsAdmissionCtrlTypeEntry 2 }

  -- Table hwCmtsAdmissionCtrlMappingTable
    hwCmtsAdmissionCtrlMappingTable OBJECT-TYPE
          SYNTAX     SEQUENCE OF HwCmtsAdmissionCtrlMappingEntry
          MAX-ACCESS not-accessible
          STATUS     current
          DESCRIPTION
               "Indicates the admission control type mapping configuration.
               The index of this table is hwCmtsAdmissionCtrlMappingIndex.
               "
          ::= { hwCmtsAccessObject 10 }

    hwCmtsAdmissionCtrlMappingEntry OBJECT-TYPE
          SYNTAX     HwCmtsAdmissionCtrlMappingEntry
          MAX-ACCESS not-accessible
          STATUS     current
          DESCRIPTION
               "Indicates the admission control type mapping configuration.
               The index of this entry is hwCmtsAdmissionCtrlMappingIndex.
               "
          INDEX       { hwCmtsAdmissionCtrlMappingIndex }
          ::= { hwCmtsAdmissionCtrlMappingTable 1 }

    HwCmtsAdmissionCtrlMappingEntry ::=
          SEQUENCE {
                    hwCmtsAdmissionCtrlMappingIndex               Integer32,
                    hwCmtsAdmissionCtrlMappingType     Integer32,
                    hwCmtsAdmissionCtrlMappingTypeName OCTET STRING,
                    hwCmtsAdmissionCtrlMappingSubType             INTEGER,
                    hwCmtsAdmissionCtrlMappingPacketCablePriority INTEGER,
                    hwCmtsAdmissionCtrlMappingPcmmPriority        Integer32,
                    hwCmtsAdmissionCtrlMappingPcmmApplicationType Integer32,
                    hwCmtsAdmissionCtrlMappingSchedulingType      INTEGER,
                    hwCmtsAdmissionCtrlMappingServiceClassName    OCTET STRING,
                    hwCmtsAdmissionCtrlMappingRowStatus           RowStatus
                   }

    hwCmtsAdmissionCtrlMappingIndex OBJECT-TYPE
          SYNTAX     Integer32 (-1|0..31)
          MAX-ACCESS not-accessible
          STATUS     current
          DESCRIPTION
                "Indicates the index of admission control type mapping.
                 -1 is used only when a user adds admission control mapping.
                 "
          ::= { hwCmtsAdmissionCtrlMappingEntry 1 }

    hwCmtsAdmissionCtrlMappingType OBJECT-TYPE
          SYNTAX     Integer32(0..7)
          MAX-ACCESS read-write
          STATUS     current
          DESCRIPTION
                "Indicates the admission control type."
              DEFVAL      { 0 }
          ::= { hwCmtsAdmissionCtrlMappingEntry 2 }

    hwCmtsAdmissionCtrlMappingTypeName OBJECT-TYPE
          SYNTAX      OCTET STRING(SIZE (0..32))
          MAX-ACCESS  read-only
          STATUS  current
          DESCRIPTION
                "Indicates the name of admission control type."
          ::= { hwCmtsAdmissionCtrlMappingEntry 3 }

    hwCmtsAdmissionCtrlMappingSubType OBJECT-TYPE
          SYNTAX     INTEGER{pcLdotxPriority(1),pcmmPriority(2),pcmmApplicationType(3),schedulingType(4),serviceClassName(5),dynamicService(6)}
          MAX-ACCESS read-write
          STATUS     current
          DESCRIPTION
                "
                Indicates the admission control sub-type.
                Options:
                1. pcLdotxPriority(1)     -Indicates PacketCable 1.x priority
                2. pcmmPriority(2)         -Indicates PacketCable multimedia priority
                3. pcmmApplicationType(3) -Indicates PacketCable multimedia application type
                4. schedulingType(4)       -Indicates scheduling type
                5. serviceClassName(5)    -Indicates service class name
                6. dynamicService(6)      -Indicates dynamic service
                "
              DEFVAL      { 1 }
          ::= { hwCmtsAdmissionCtrlMappingEntry 4 }

    hwCmtsAdmissionCtrlMappingPacketCablePriority OBJECT-TYPE
          SYNTAX     INTEGER{normalPriority(1),highPriority(2)}
          MAX-ACCESS read-write
          STATUS     current
          DESCRIPTION
                "
                Indicates the PacketCable priority.
                Options:
                1. normalPriority(1) -Indicates the PacketCable priority is normal
                2. highPriority(2)   -Indicates the PacketCable priority is high
                "
              DEFVAL      { 1 }
          ::= { hwCmtsAdmissionCtrlMappingEntry 5 }

    hwCmtsAdmissionCtrlMappingPcmmPriority OBJECT-TYPE
          SYNTAX     Integer32 (0..7)
          MAX-ACCESS read-write
          STATUS     current
          DESCRIPTION
                "Indicates the PacketCable Multimedia priority."
              DEFVAL      { 0 }
          ::= { hwCmtsAdmissionCtrlMappingEntry 6 }

    hwCmtsAdmissionCtrlMappingPcmmApplicationType OBJECT-TYPE
          SYNTAX     Integer32 (0..65535)
          MAX-ACCESS read-write
          STATUS     current
          DESCRIPTION
                "Indicates the PacketCable Multimedia application type."
              DEFVAL      { 0 }
          ::= { hwCmtsAdmissionCtrlMappingEntry 7 }

    hwCmtsAdmissionCtrlMappingSchedulingType OBJECT-TYPE
          SYNTAX     INTEGER{ugs(1),ugsAd(2),rtps(3),nrtps(4),be(5)}
          MAX-ACCESS read-write
          STATUS     current
          DESCRIPTION
                "Indicates the scheduling type.
                Options:
                1. ugs(1)    -Indicates the scheduling type of unsolicited grant service
                2. ugsAd(2) -Indicates the scheduling type of unsolicited grant service with activity detection
                3. rtps(3)   -Indicates the scheduling type of real-time polling service
                4. nrtps(4)  -Indicates the scheduling type of non-real-time polling service
                5. be(5)     -Indicates the scheduling type of best-effort
                "
              DEFVAL      { 1 }
          ::= { hwCmtsAdmissionCtrlMappingEntry 8 }

    hwCmtsAdmissionCtrlMappingServiceClassName OBJECT-TYPE
          SYNTAX     OCTET STRING(SIZE (0..15))
          MAX-ACCESS read-write
          STATUS     current
          DESCRIPTION
                "Indicates the service class name."
              DEFVAL      { 0 }
          ::= { hwCmtsAdmissionCtrlMappingEntry 9 }

    hwCmtsAdmissionCtrlMappingRowStatus OBJECT-TYPE
          SYNTAX     RowStatus
          MAX-ACCESS read-create
          STATUS     current
          DESCRIPTION
                "Indicates the row status to create or delete a admission control type mapping."
          ::= { hwCmtsAdmissionCtrlMappingEntry 10 }

  -- Table hwCmtsAdmissionCtrlPortBandwidthTable
    hwCmtsAdmissionCtrlPortBandwidthTable OBJECT-TYPE
          SYNTAX     SEQUENCE OF HwCmtsAdmissionCtrlPortBandwidthEntry
          MAX-ACCESS not-accessible
          STATUS     current
          DESCRIPTION
               "Indicates the admission control port bandwidth configuration.
               The indexes of this table are hwCmtsAdmissionCtrlPortBandwidthIfIndex and hwCmtsAdmissionCtrlPortBandwidthChannelType.
               "
          ::= { hwCmtsAccessObject 11 }

    hwCmtsAdmissionCtrlPortBandwidthEntry OBJECT-TYPE
          SYNTAX     HwCmtsAdmissionCtrlPortBandwidthEntry
          MAX-ACCESS not-accessible
          STATUS     current
          DESCRIPTION
               "Indicates the admission control port bandwidth configuration.
               The indexes of this entry are hwCmtsAdmissionCtrlPortBandwidthIfIndex and hwCmtsAdmissionCtrlPortBandwidthChannelType.
               "
          INDEX       { hwCmtsAdmissionCtrlPortBandwidthIfIndex, hwCmtsAdmissionCtrlPortBandwidthChannelType }
          ::= { hwCmtsAdmissionCtrlPortBandwidthTable 1 }

    HwCmtsAdmissionCtrlPortBandwidthEntry ::=
          SEQUENCE {
                    hwCmtsAdmissionCtrlPortBandwidthIfIndex       Integer32,
                    hwCmtsAdmissionCtrlPortBandwidthChannelType   INTEGER,
                    hwCmtsAdmissionCtrlPortBandwidthExclusiveList     OCTET STRING,
                    hwCmtsAdmissionCtrlPortBandwidthNonExclusiveList     OCTET STRING,
                    hwCmtsAdmissionCtrlPortBandwidthMinorList       OCTET STRING,
                    hwCmtsAdmissionCtrlPortBandwidthMajorList       OCTET STRING
                   }

    hwCmtsAdmissionCtrlPortBandwidthIfIndex OBJECT-TYPE
          SYNTAX  Integer32
          MAX-ACCESS  not-accessible
          STATUS  current
          DESCRIPTION
                "The index of admission control bandwidth table."
          ::= { hwCmtsAdmissionCtrlPortBandwidthEntry 1 }

    hwCmtsAdmissionCtrlPortBandwidthChannelType OBJECT-TYPE
          SYNTAX      INTEGER{uschannel(59),dschannel(60)}
          MAX-ACCESS  not-accessible
          STATUS  current
          DESCRIPTION
                "Indicates the channel type.
                Options:
                1. uschannel(59) -Indicates the channel type is upstream channel
                2. dschannel(60) -Indicates the channel type is downstream channel
                "
          ::= { hwCmtsAdmissionCtrlPortBandwidthEntry 2 }

    hwCmtsAdmissionCtrlPortBandwidthExclusiveList OBJECT-TYPE
          SYNTAX      OCTET STRING(SIZE (0..8))
          UNITS   "%"
          MAX-ACCESS  read-write
          STATUS  current
          DESCRIPTION
                "Indicates the exclusive threshold.Each byte represents an
                exclusive threshold for a admission control type.
                Bytes 0-7 indicate admission control types 0-7.
                The value for each byte is 0-100.
                When the value is 255, no exclusive threshold is
                configured for a admission control type. The sum of the
                exclusive and non-exclusive thresholds of all the admission control types cannot exceed 100"
          ::= { hwCmtsAdmissionCtrlPortBandwidthEntry 3 }
          
    hwCmtsAdmissionCtrlPortBandwidthNonExclusiveList OBJECT-TYPE
          SYNTAX      OCTET STRING(SIZE (0..8))
          UNITS   "%"
          MAX-ACCESS  read-write
          STATUS  current
          DESCRIPTION
                "Indicates the non-exclusive threshold.Each byte represents an
                non-exclusive threshold for a admission control type.
                Bytes 0-7 indicate admission control types 0-7.
                The value for each byte is 0-100.
                When the value is 255, no non-exclusive threshold is
                configured for a admission control type. The sum of the
                exclusive and non-exclusive thresholds of all the admission control types cannot exceed 100."
          ::= { hwCmtsAdmissionCtrlPortBandwidthEntry 4 }

   hwCmtsAdmissionCtrlPortBandwidthMinorList OBJECT-TYPE
          SYNTAX      OCTET STRING(SIZE (0..8))
          UNITS   "%"
          MAX-ACCESS  read-write
          STATUS  current
          DESCRIPTION
                "Indicates the minor alarm threshold.Each byte represents an
                minor alarm threshold for a admission control type.
                Bytes 0-7 indicate admission control types 0-7.
                The value for each byte is 0-100.
                When the value is 255, no minor alarm threshold is
                configured for a admission control type."
          ::= { hwCmtsAdmissionCtrlPortBandwidthEntry 5 }

   hwCmtsAdmissionCtrlPortBandwidthMajorList OBJECT-TYPE
          SYNTAX      OCTET STRING(SIZE (0..8))
          UNITS   "%"
          MAX-ACCESS  read-write
          STATUS  current
          DESCRIPTION
                "Indicates the major alarm threshold.Each byte represents an
                major alarm threshold for a admission control type.
                Bytes 0-7 indicate admission control types 0-7.
                The value for each byte is 0-100.
                When the value is 255, no major alarm threshold is
                configured for a admission control type."
          ::= { hwCmtsAdmissionCtrlPortBandwidthEntry 6 }

   -- Table hwCmtsAdmissionCtrlChannelBandwidthTable
    hwCmtsAdmissionCtrlChannelBandwidthTable OBJECT-TYPE
          SYNTAX     SEQUENCE OF HwCmtsAdmissionCtrlChannelBandwidthEntry
          MAX-ACCESS not-accessible
          STATUS     current
          DESCRIPTION
               "Indicates the admission control channel bandwidth query.
               The indexes of this table are hwCmtsAdmissionCtrlChannelBandwidthIfIndex, hwCmtsAdmissionCtrlChannelBandwidthChannelType
               and hwCmtsAdmissionCtrlChannelBandwidthChannelId.
               "
          ::= { hwCmtsAccessObject 12 }

    hwCmtsAdmissionCtrlChannelBandwidthEntry OBJECT-TYPE
          SYNTAX     HwCmtsAdmissionCtrlChannelBandwidthEntry
          MAX-ACCESS not-accessible
          STATUS     current
          DESCRIPTION
               "Indicates the admission control channel bandwidth query.
               The indexes of this entry are hwCmtsAdmissionCtrlChannelBandwidthIfIndex, hwCmtsAdmissionCtrlChannelBandwidthChannelType
               and hwCmtsAdmissionCtrlChannelBandwidthChannelId.
               "
          INDEX       { hwCmtsAdmissionCtrlChannelBandwidthIfIndex,
                        hwCmtsAdmissionCtrlChannelBandwidthChannelType,
                        hwCmtsAdmissionCtrlChannelBandwidthChannelId }
          ::= { hwCmtsAdmissionCtrlChannelBandwidthTable 1 }

    HwCmtsAdmissionCtrlChannelBandwidthEntry ::=
          SEQUENCE {
                    hwCmtsAdmissionCtrlChannelBandwidthIfIndex       Integer32,
                    hwCmtsAdmissionCtrlChannelBandwidthChannelType   INTEGER,
                    hwCmtsAdmissionCtrlChannelBandwidthChannelId     Integer32,
                    hwCmtsAdmissionCtrlChannelBandwidthExclusiveList     OCTET STRING,
                    hwCmtsAdmissionCtrlChannelBandwidthCurrOccupyList    OCTET STRING,
                    hwCmtsAdmissionCtrlChannelBandwidthNonExclusiveList  OCTET STRING,
                    hwCmtsAdmissionCtrlChannelBandwidthMinorList         OCTET STRING,
                    hwCmtsAdmissionCtrlChannelBandwidthMajorList         OCTET STRING
                   }

    hwCmtsAdmissionCtrlChannelBandwidthIfIndex OBJECT-TYPE
          SYNTAX  Integer32
          MAX-ACCESS  not-accessible
          STATUS  current
          DESCRIPTION
                "Indicates the the index of channel bandwidth table."
          ::= { hwCmtsAdmissionCtrlChannelBandwidthEntry 1 }

    hwCmtsAdmissionCtrlChannelBandwidthChannelType OBJECT-TYPE
          SYNTAX  INTEGER{uschannel(59),dschannel(60)}
          MAX-ACCESS  accessible-for-notify
          STATUS  current
          DESCRIPTION
                "Indicates the channel type.
                Options:
                1. uschannel(59) -Indicates the channel type is upstream channel
                2. dschannel(60) -Indicates the channel type is downstream channel
                "
          ::= { hwCmtsAdmissionCtrlChannelBandwidthEntry 2 }

    hwCmtsAdmissionCtrlChannelBandwidthChannelId OBJECT-TYPE
          SYNTAX  Integer32(1..104)
          MAX-ACCESS  not-accessible
          STATUS  current
          DESCRIPTION
                "Indicates the channel ID.
                 Options:
                 Range is 1..20 if the channel type is upstream channel.
                 Range is 1..104 if the channel type is downstream channel.
                "
          ::= { hwCmtsAdmissionCtrlChannelBandwidthEntry 3 }

    hwCmtsAdmissionCtrlChannelBandwidthExclusiveList OBJECT-TYPE
          SYNTAX      OCTET STRING(SIZE (0..8))
          MAX-ACCESS  read-only
          STATUS  current
          DESCRIPTION
                "Indicates the exclusive threshold.
                Each byte represents an exclusive threshold for a
                admission control type.
                Bytes 0-7 indicate admission control types 0-7."
          ::= { hwCmtsAdmissionCtrlChannelBandwidthEntry 4 }

    hwCmtsAdmissionCtrlChannelBandwidthCurrOccupyList OBJECT-TYPE
          SYNTAX      OCTET STRING(SIZE (0..8))
          MAX-ACCESS  read-only
          STATUS  current
          DESCRIPTION
                " Indicates the usage of the minimum assured bandwidth."
          ::= { hwCmtsAdmissionCtrlChannelBandwidthEntry 5 }

    hwCmtsAdmissionCtrlChannelBandwidthNonExclusiveList OBJECT-TYPE
          SYNTAX      OCTET STRING(SIZE (0..8))
          MAX-ACCESS  read-only
          STATUS  current
          DESCRIPTION
                "Indicates the non-exclusive threshold.
                Each byte represents an non-exclusive threshold for a
                admission control type.
                Bytes 0-7 indicate admission control types 0-7."
          ::= { hwCmtsAdmissionCtrlChannelBandwidthEntry 6 }

    hwCmtsAdmissionCtrlChannelBandwidthMinorList OBJECT-TYPE
          SYNTAX      OCTET STRING(SIZE (0..8))
          MAX-ACCESS  read-only
          STATUS  current
          DESCRIPTION
                "Indicates the minor alarm threshold.
                Each byte represents an minor alarm threshold for a
                admission control type.
                Bytes 0-7 indicate admission control types 0-7."
          ::= { hwCmtsAdmissionCtrlChannelBandwidthEntry 7 }

    hwCmtsAdmissionCtrlChannelBandwidthMajorList OBJECT-TYPE
          SYNTAX      OCTET STRING(SIZE (0..8))
          MAX-ACCESS  read-only
          STATUS  current
          DESCRIPTION
                "Indicates the major alarm threshold.
                Each byte represents an major alarm threshold for a
                admission control type.
                Bytes 0-7 indicate admission control types 0-7."
          ::= { hwCmtsAdmissionCtrlChannelBandwidthEntry 8 }

  -- Table hwCmtsAdmissionCtrlStatisticsTable
    hwCmtsAdmissionCtrlStatisticsTable OBJECT-TYPE
          SYNTAX     SEQUENCE OF  HwCmtsAdmissionCtrlStatisticsEntry
          MAX-ACCESS not-accessible
          STATUS     current
          DESCRIPTION
               "Indicates the statistics of admission control admission.
               The indexes of this table are hwCmtsAdmissionCtrlStatisticsIfIndex,
               hwCmtsAdmissionCtrlStatisticsChannelType and hwCmtsAdmissionCtrlStatisticsChannelId.
               "
          ::= { hwCmtsAccessObject 13 }

    hwCmtsAdmissionCtrlStatisticsEntry OBJECT-TYPE
          SYNTAX     HwCmtsAdmissionCtrlStatisticsEntry
          MAX-ACCESS not-accessible
          STATUS     current
          DESCRIPTION
               "Indicates the statistics of admission control admission.
               The indexes of this entry are hwCmtsAdmissionCtrlStatisticsIfIndex,
               hwCmtsAdmissionCtrlStatisticsChannelType and hwCmtsAdmissionCtrlStatisticsChannelId.
               "
          INDEX       { hwCmtsAdmissionCtrlStatisticsIfIndex,
                        hwCmtsAdmissionCtrlStatisticsChannelType,
                        hwCmtsAdmissionCtrlStatisticsChannelId }
          ::= { hwCmtsAdmissionCtrlStatisticsTable 1 }

    HwCmtsAdmissionCtrlStatisticsEntry ::=
          SEQUENCE {
                    hwCmtsAdmissionCtrlStatisticsIfIndex                           Integer32,
                    hwCmtsAdmissionCtrlStatisticsChannelType                       INTEGER,
                    hwCmtsAdmissionCtrlStatisticsChannelId                         Integer32,
                    hwCmtsAdmissionCtrlExceedCmRegCountList                        OCTET STRING,
                    hwCmtsAdmissionCtrlExceedDynamicCountList                      OCTET STRING,
                    hwCmtsAdmissionCtrlCmRegRejectCountList                        OCTET STRING,
                    hwCmtsAdmissionCtrlDynamicRejectCountList                      OCTET STRING,
                    hwCmtsAdmissionCtrlStatisticsOper                               INTEGER
                   }

    hwCmtsAdmissionCtrlStatisticsIfIndex OBJECT-TYPE
          SYNTAX  Integer32
          MAX-ACCESS  not-accessible
          STATUS  current
          DESCRIPTION
                "Indicates the index of cable port."
          ::= { hwCmtsAdmissionCtrlStatisticsEntry 1 }

    hwCmtsAdmissionCtrlStatisticsChannelType OBJECT-TYPE
          SYNTAX  INTEGER{uschannel(59),dschannel(60)}
          MAX-ACCESS  not-accessible
          STATUS  current
          DESCRIPTION
                "Indicates the channel type of cable port.
                Options:
                1. uschannel(59) -Indicates the channel type of cable port is upstream channel
                2. dschannel(60) -Indicates the channel type of cable port is downstream channel
                "
          ::= { hwCmtsAdmissionCtrlStatisticsEntry 2 }

    hwCmtsAdmissionCtrlStatisticsChannelId OBJECT-TYPE
          SYNTAX  Integer32(1..104)
          MAX-ACCESS  not-accessible
          STATUS  current
          DESCRIPTION
                "Indicates the channel ID of cable port.
                 Options:
                 Range is 1..20 if the channel type is upstream channel.
                 Range is 1..104 if the channel type is downstream channel.
                "
          ::= { hwCmtsAdmissionCtrlStatisticsEntry 3 }

    hwCmtsAdmissionCtrlExceedCmRegCountList OBJECT-TYPE
          SYNTAX      OCTET STRING(SIZE (0..32))
          MAX-ACCESS  read-only
          STATUS  current
          DESCRIPTION
                "Indicates the number of CM registrations that exceed the exclusive threshold."
          ::= { hwCmtsAdmissionCtrlStatisticsEntry 4 }

    hwCmtsAdmissionCtrlExceedDynamicCountList OBJECT-TYPE
          SYNTAX      OCTET STRING(SIZE (0..32))
          MAX-ACCESS  read-only
          STATUS  current
          DESCRIPTION
                "Indicates the number of dynamic service flows that exceed the exclusive threshold."
          ::= { hwCmtsAdmissionCtrlStatisticsEntry 5 }

    hwCmtsAdmissionCtrlCmRegRejectCountList OBJECT-TYPE
          SYNTAX      OCTET STRING(SIZE (0..32))
          MAX-ACCESS  read-only
          STATUS  current
          DESCRIPTION
                "Indicates the Number of CM registrations rejected by the admission control entry mechanism."
          ::= { hwCmtsAdmissionCtrlStatisticsEntry 6 }

    hwCmtsAdmissionCtrlDynamicRejectCountList OBJECT-TYPE
          SYNTAX      OCTET STRING(SIZE (0..32))
          MAX-ACCESS  read-only
          STATUS  current
          DESCRIPTION
                "Indicates the number of dynamic service flows rejected by the admission control entry mechanism."
          ::= { hwCmtsAdmissionCtrlStatisticsEntry 7 }


    hwCmtsAdmissionCtrlStatisticsOper OBJECT-TYPE
          SYNTAX      INTEGER{clear(1) }
          MAX-ACCESS  read-write
          STATUS  current
          DESCRIPTION
                "Indicates the the operating mode.
                Options:
                1. clear(1) -Indicates clearing the statistics informations in the channel
                "
          ::= { hwCmtsAdmissionCtrlStatisticsEntry 8 }

  -- Table hwCmtsMtaBasicTable
    hwCmtsMtaBasicTable OBJECT-TYPE
          SYNTAX     SEQUENCE OF  HwCmtsMtaBasicEntry
          MAX-ACCESS not-accessible
          STATUS     current
          DESCRIPTION
               "Indicates the MTA info.
               The indexes of this table are hwCmtsMtaBasicIfIndex and hwCmtsMtaBasicMtaMacAddress."
          ::= { hwCmtsAccessObject 14 }

    hwCmtsMtaBasicEntry OBJECT-TYPE
          SYNTAX     HwCmtsMtaBasicEntry
          MAX-ACCESS not-accessible
          STATUS     current
          DESCRIPTION
               "Indicates the MTA info.
               The indexes of this entry are hwCmtsMtaBasicIfIndex and hwCmtsMtaBasicMtaMacAddress."
          INDEX       { hwCmtsMtaBasicIfIndex, hwCmtsMtaBasicMtaMacAddress }
          ::= { hwCmtsMtaBasicTable 1 }

    HwCmtsMtaBasicEntry ::=
          SEQUENCE {
                    hwCmtsMtaBasicIfIndex         Integer32,
                    hwCmtsMtaBasicMtaMacAddress   MacAddress,
                    hwCmtsMtaBasicCmIndex         Unsigned32,
                    hwCmtsMtaBasicCmMacAddress    MacAddress,
                    hwCmtsMtaBasicMtaIPAddress    IpAddress,
                    hwCmtsMtaBasicMtaPktcVersion        Integer32
                   }

    hwCmtsMtaBasicIfIndex OBJECT-TYPE
          SYNTAX  Integer32
          MAX-ACCESS  not-accessible
          STATUS  current
          DESCRIPTION
                "Indicates the index of cable port."
          ::= { hwCmtsMtaBasicEntry 1 }

    hwCmtsMtaBasicMtaMacAddress OBJECT-TYPE
          SYNTAX      MacAddress
          MAX-ACCESS  not-accessible
          STATUS  current
          DESCRIPTION
                "Indicates the MAC address of MTA."
          ::= { hwCmtsMtaBasicEntry 2 }

    hwCmtsMtaBasicCmIndex OBJECT-TYPE
          SYNTAX      Unsigned32 (1..4294967295)
          MAX-ACCESS  read-only
          STATUS  current
          DESCRIPTION
                "Indicates the index of CM."
          ::= { hwCmtsMtaBasicEntry 3 }

    hwCmtsMtaBasicCmMacAddress OBJECT-TYPE
          SYNTAX      MacAddress
          MAX-ACCESS  read-only
          STATUS  current
          DESCRIPTION
                "Indicates the MAC address of CM.
                The CM's MAC address cannot be a
                broadcast MAC address,multicast
                MAC address, or a MAC address
                consisting of all 0s."
          ::= { hwCmtsMtaBasicEntry 4 }

    hwCmtsMtaBasicMtaIPAddress OBJECT-TYPE
          SYNTAX      IpAddress
          MAX-ACCESS  read-only
          STATUS  current
          DESCRIPTION
                "Indicates the IP address of MTA."
          ::= { hwCmtsMtaBasicEntry 5 }

    hwCmtsMtaBasicMtaPktcVersion OBJECT-TYPE
          SYNTAX      Integer32(1..3)
          MAX-ACCESS  read-only
          STATUS  current
          DESCRIPTION
                "
                Indicates the version of PacketCable.
                1-PacketCable version 1.0
                2-PacketCable version 1.5
                3-PacketCable version 2.0
                -1 represent invalid version of PacketCable.
                "
          ::= { hwCmtsMtaBasicEntry 6 }


    -- Table hwCmtsCmOverCapaTable
    hwCmtsCmOverCapaTable OBJECT-TYPE
          SYNTAX     SEQUENCE OF HwCmtsCmOverCapaEntry
          MAX-ACCESS not-accessible
          STATUS     current
          DESCRIPTION
                "The table is used for the CMs that fail to go online
                 because the port has connected to the maximum number of CMs or the port is overloaded
                 or over access number and so on.
                 The index of this table is ifIndex.
                "
          ::= { hwCmtsAccessObject 15 }

    hwCmtsCmOverCapaEntry OBJECT-TYPE
          SYNTAX     HwCmtsCmOverCapaEntry
          MAX-ACCESS not-accessible
          STATUS     current
          DESCRIPTION
                "The table is used for the CMs that fail to go online
                 because the port has connected to the maximum number of CMs or the port is overloaded
                 or over access number and so on.
                 The index of this entry is ifIndex.
                "
          INDEX       { ifIndex }
          ::= { hwCmtsCmOverCapaTable 1 }

    HwCmtsCmOverCapaEntry ::=
          SEQUENCE {
                    hwCmtsCmOverCapaNum             Unsigned32,
                    hwCmtsCmOverCapaMacAddrList     OCTET STRING,
                    hwCmtsCmOverCapaTimeList        OCTET STRING,
                    hwCmtsCmOverCapaReasonList      OCTET STRING
                   }

    hwCmtsCmOverCapaNum OBJECT-TYPE
          SYNTAX  Unsigned32 (0..256)
          MAX-ACCESS  read-only
          STATUS  current
          DESCRIPTION
                "This node indicates the number of the CMs that fail to go online
                 because the port has connected to the maximum number of CMs or the port is overloaded,
                 or over access number and so on.
                "
          ::= { hwCmtsCmOverCapaEntry 1 }

    hwCmtsCmOverCapaMacAddrList OBJECT-TYPE
          SYNTAX  OCTET STRING (SIZE (0..1536))
          MAX-ACCESS  read-only
          STATUS  current
          DESCRIPTION
                "This node indicates the MAC list. The MAC list records the MAC addresses of the CMs one by one.
                 The data type of the MAC address for each CM is MacAddress. Each record takes 6 bytes.
                "
          ::= { hwCmtsCmOverCapaEntry 2 }


    hwCmtsCmOverCapaTimeList OBJECT-TYPE
          SYNTAX  OCTET STRING (SIZE (0..3072))
          MAX-ACCESS  read-only
          STATUS  current
          DESCRIPTION
                "This node indicates the time list. The time list records the time of the CMs one by one.
                 The data type of the time for each CM is DateAndTime. Each record takes 11 bytes.
                "
          ::= { hwCmtsCmOverCapaEntry 3 }

    hwCmtsCmOverCapaReasonList OBJECT-TYPE
          SYNTAX  OCTET STRING (SIZE (0..512))
          MAX-ACCESS  read-only
          STATUS  current
          DESCRIPTION
                "This node indicates the reason list of the CMs that fail to go online
                 because the port has connected to the maximum number of CMs or the port is overloaded,
                 or over access number and so on.
                 The reason list records the reason of the CMs one by one. Each record takes 1 bytes.
                 The value of the reason for each CM is
                 Option:
                 1: overspec(1)                               - The port has connected to the maximum number of CMs
                 2: overload(2)                               - The port is overloaded
                 3: over access number(3)                     - The number of CMs connected to this port is over the threshold
                 4: The total number of ONTs and CMs has reached the maximum specifications of the system(4)  - The total number of ONTs and CMs has reached the maximum specifications of the system
                 5: MAC conflicts with CPE MAC(5)             - The CM MAC conflicts with CPE MAC   
                 6: Malloc flow(6)                            - The status is reserved
                 7: Not in whitelist(7)                       - The CM is not in whitelist
                 8: CM arrival board check fail(8)            - The information about a CM in ranging fails to be checked on the board
                "
          ::= { hwCmtsCmOverCapaEntry 4 }

    hwCmtsSnrDetectTable OBJECT IDENTIFIER ::= { hwCmtsAccessObject  16 }
    -- Table hwCmtsSnrDetectTable

    hwCmtsSnrDetectPeriod OBJECT-TYPE
          SYNTAX  Integer32 (0..60000)
          UNITS   "ms"
          MAX-ACCESS  read-write
          STATUS  current
          DESCRIPTION
                "The snr detect period of a Spectrum Group.
                Set to 0 means close the snr detect. 1-999 is reserved
                Default: 0."
          ::= { hwCmtsSnrDetectTable 1 }

    -- Table hwCmtsCmCurrTable
    hwCmtsCmCurrTable OBJECT-TYPE
          SYNTAX     SEQUENCE OF HwCmtsCmCurrEntry
          MAX-ACCESS not-accessible
          STATUS     current
          DESCRIPTION
                "
                Indicates the current performance statistics.
                The index of this table is hwCmtsCmCurrId.
                "
          ::= { hwCmtsAccessObject 17 }

    hwCmtsCmCurrEntry OBJECT-TYPE
          SYNTAX     HwCmtsCmCurrEntry
          MAX-ACCESS not-accessible
          STATUS     current
          DESCRIPTION
                "
                Indicates the current performance statistics.
                The index of this entry is hwCmtsCmCurrId.
                "
          INDEX       { hwCmtsCmCurrId }
          ::= { hwCmtsCmCurrTable 1 }

    HwCmtsCmCurrEntry ::=
          SEQUENCE {
                    hwCmtsCmCurrId                              Integer32,
                    hwCmtsCmCurr15MStartTime                    OCTET STRING,
                    hwCmtsCmCurr15MElapsedTime                  Integer32,
                    hwCmtsCmCurr15MValidityFlag                 Integer32,
                    hwCmtsCmCurr15MSuccessReg                   Counter32,
                    hwCmtsCmCurr15MFailReg                      Counter32,
                    hwCmtsCmCurr15MRepeatReg                    Counter32,
                    hwCmtsCmCurr15MSuccessPeriodRng             Counter32,
                    hwCmtsCmCurr15MPeriodRngLoss                Counter32,
                    hwCmtsCmCurr15MSeriousPeriodRngLoss         Counter32,
                    hwCmtsCmCurr15MPowerAdjust                  Counter32,
                    hwCmtsCmCurr15MSeriousPowerAdjust           Counter32,
                    hwCmtsCmCurr1DayStartTime                   OCTET STRING,
                    hwCmtsCmCurr1DayElapsedTime                 Integer32,
                    hwCmtsCmCurr1DayValidityFlag                Integer32,
                    hwCmtsCmCurr1DaySuccessReg                  Counter32,
                    hwCmtsCmCurr1DayFailReg                     Counter32,
                    hwCmtsCmCurr1DayRepeatReg                   Counter32,
                    hwCmtsCmCurr1DaySuccessPeriodRng            Counter32,
                    hwCmtsCmCurr1DayPeriodRngLoss               Counter32,
                    hwCmtsCmCurr1DaySeriousPeriodRngLoss        Counter32,
                    hwCmtsCmCurr1DayPowerAdjust                 Counter32,
                    hwCmtsCmCurr1DaySeriousPowerAdjust          Counter32,
                    hwCmtsCmCurrEverBeforeStartTime             OCTET STRING,
                    hwCmtsCmCurrEverBeforeElapsedTime           Integer32,
                    hwCmtsCmCurrEverBeforeValidityFlag          Integer32,
                    hwCmtsCmCurrEverBeforeSuccessReg            Counter32,
                    hwCmtsCmCurrEverBeforeFailReg               Counter32,
                    hwCmtsCmCurrEverBeforeRepeatReg             Counter32,
                    hwCmtsCmCurrEverBeforeSuccessPeriodRng      Counter32,
                    hwCmtsCmCurrEverBeforePeriodRngLoss         Counter32,
                    hwCmtsCmCurrEverBeforeSeriousPeriodRngLoss  Counter32,
                    hwCmtsCmCurrEverBeforePowerAdjust           Counter32,
                    hwCmtsCmCurrEverBeforeSeriousPowerAdjust    Counter32,
                    hwCmtsCmCurrEverBeforeUnstableConnectionCount     Integer32,
                    hwCmtsCmCurrEverBeforeLastUnstableConnectionTime  DateAndTime,
                    hwCmtsCmCurrEverBeforeFirstUnstableConnectionTime DateAndTime,
                    hwCmtsCmCurrEverBeforeLastRepeatRegTime     DateAndTime,
                    hwCmtsCmCurrEverBeforeFirstRepeatRegTime    DateAndTime,
                    hwCmtsCmCurrEverBeforeLastSeriousPeriodRngLossTime  DateAndTime,
                    hwCmtsCmCurrEverBeforeFirstSeriousPeriodRngLossTime DateAndTime,
                    hwCmtsCmCurrEverBeforeLastSeriousPowerAdjustTime    DateAndTime,
                    hwCmtsCmCurrEverBeforeFirstSeriousPowerAdjustTime   DateAndTime,
                    hwCmtsCmCurr15MCrc                                  Counter64,
                    hwCmtsCmCurr1DayCrc                                 Counter64,
                    hwCmtsCmCurrEverBeforeCrc                           Counter64
                   }

    hwCmtsCmCurrId OBJECT-TYPE
          SYNTAX  Integer32
          MAX-ACCESS   not-accessible
          STATUS  current
          DESCRIPTION
                "
                Indicates a CM index.
                "
          ::= { hwCmtsCmCurrEntry 1 }

    hwCmtsCmCurr15MStartTime OBJECT-TYPE
          SYNTAX  OCTET STRING
          MAX-ACCESS  read-only
          STATUS  current
          DESCRIPTION
                "
                Indicates the start time of the current 15-minute statistical period.
                "
          ::= { hwCmtsCmCurrEntry 2 }


    hwCmtsCmCurr15MElapsedTime OBJECT-TYPE
          SYNTAX  Integer32
          UNITS   "s"
          MAX-ACCESS  read-only
          STATUS  current
          DESCRIPTION
                "
                Indicates the elapsed time in the current 15-minute statistical period.
                "
          ::= { hwCmtsCmCurrEntry 3 }

    hwCmtsCmCurr15MValidityFlag OBJECT-TYPE
          SYNTAX  Integer32 (1..2)
          MAX-ACCESS  read-only
          STATUS  current
          DESCRIPTION
                "
                Indicates the flag for statistical information.
                Options:
                1-Yes
                2-No
                "
          ::= { hwCmtsCmCurrEntry 4 }

    hwCmtsCmCurr15MSuccessReg OBJECT-TYPE
          SYNTAX  Counter32
          MAX-ACCESS  read-only
          STATUS  current
          DESCRIPTION
                "
                Indicates the number of registration requests initiated by a CM during the current 15-minute.
                "
          ::= { hwCmtsCmCurrEntry 5 }

    hwCmtsCmCurr15MFailReg OBJECT-TYPE
          SYNTAX  Counter32
          MAX-ACCESS  read-only
          STATUS  current
          DESCRIPTION
                "
                Indicates the number of CM registration failures during the current 15-minute.
                "
          ::= { hwCmtsCmCurrEntry 6 }

    hwCmtsCmCurr15MRepeatReg OBJECT-TYPE
          SYNTAX  Counter32
          MAX-ACCESS  read-only
          STATUS  current
          DESCRIPTION
                "
                Indicates the number of repeated registrations during the current 15-minute.
                "
          ::= { hwCmtsCmCurrEntry 7 }

    hwCmtsCmCurr15MSuccessPeriodRng OBJECT-TYPE
          SYNTAX  Counter32
          MAX-ACCESS  read-only
          STATUS  current
          DESCRIPTION
                "
                Indicates the number of periodic ranging requests initiated by a CM during the current 15-minute.
                "
          ::= { hwCmtsCmCurrEntry 8 }

    hwCmtsCmCurr15MPeriodRngLoss OBJECT-TYPE
          SYNTAX  Counter32
          MAX-ACCESS  read-only
          STATUS  current
          DESCRIPTION
                "
                Indicates the number of lost periodic ranging requests initiated by a CM during the current 15-minute.
                "
          ::= { hwCmtsCmCurrEntry 9 }

    hwCmtsCmCurr15MSeriousPeriodRngLoss OBJECT-TYPE
          SYNTAX  Counter32
          MAX-ACCESS  read-only
          STATUS  current
          DESCRIPTION
                "
                Indicates the number of consecutive periodic ranging request failures during the current 15-minute.
                "
          ::= { hwCmtsCmCurrEntry 10 }

    hwCmtsCmCurr15MPowerAdjust OBJECT-TYPE
          SYNTAX  Counter32
          MAX-ACCESS  read-only
          STATUS  current
          DESCRIPTION
                "
                Indicates the number of CM transmit power adjustments during the current 15-minute.
                "
          ::= { hwCmtsCmCurrEntry 11 }

    hwCmtsCmCurr15MSeriousPowerAdjust OBJECT-TYPE
          SYNTAX  Counter32
          MAX-ACCESS  read-only
          STATUS  current
          DESCRIPTION
                "
                Indicates the number of severe CM transmit power adjustments during the current 15-minute.
                "
          ::= { hwCmtsCmCurrEntry 12 }


    hwCmtsCmCurr1DayStartTime OBJECT-TYPE
          SYNTAX  OCTET STRING
          MAX-ACCESS  read-only
          STATUS  current
          DESCRIPTION
                "
                Indicates the start time of the current 24-hour statistical period.
                "
          ::= { hwCmtsCmCurrEntry 13 }


    hwCmtsCmCurr1DayElapsedTime OBJECT-TYPE
          SYNTAX  Integer32
          UNITS   "s"
          MAX-ACCESS  read-only
          STATUS  current
          DESCRIPTION
                "
                Indicates the elapsed time in the current 24-hour statistical period.
                "
          ::= { hwCmtsCmCurrEntry 14 }

    hwCmtsCmCurr1DayValidityFlag OBJECT-TYPE
          SYNTAX  Integer32 (1..2)
          MAX-ACCESS  read-only
          STATUS  current
          DESCRIPTION
                "
                Indicates the flag for statistical information.
                Options:
                1-Yes
                2-No
                "
          ::= { hwCmtsCmCurrEntry 15 }

    hwCmtsCmCurr1DaySuccessReg OBJECT-TYPE
          SYNTAX  Counter32
          MAX-ACCESS  read-only
          STATUS  current
          DESCRIPTION
                "
                Indicates the number of registration requests initiated by a CM during the current 24-hour.
                "
          ::= { hwCmtsCmCurrEntry 16 }

    hwCmtsCmCurr1DayFailReg OBJECT-TYPE
          SYNTAX  Counter32
          MAX-ACCESS  read-only
          STATUS  current
          DESCRIPTION
                "
                Indicates the number of CM registration failures during the current 24-hour.
                "
          ::= { hwCmtsCmCurrEntry 17 }

    hwCmtsCmCurr1DayRepeatReg OBJECT-TYPE
          SYNTAX  Counter32
          MAX-ACCESS  read-only
          STATUS  current
          DESCRIPTION
                "
                Indicates the number of repeated registrations during the current 24-hour.
                "
          ::= { hwCmtsCmCurrEntry 18 }

    hwCmtsCmCurr1DaySuccessPeriodRng OBJECT-TYPE
          SYNTAX  Counter32
          MAX-ACCESS  read-only
          STATUS  current
          DESCRIPTION
                "
                Indicates the number of periodic ranging requests initiated by a CM during the current 24-hour.
                "
          ::= { hwCmtsCmCurrEntry 19 }

    hwCmtsCmCurr1DayPeriodRngLoss OBJECT-TYPE
          SYNTAX  Counter32
          MAX-ACCESS  read-only
          STATUS  current
          DESCRIPTION
                "
                Indicates the number of lost periodic ranging requests initiated by a CM during the current 24-hour.
                "
          ::= { hwCmtsCmCurrEntry 20 }

    hwCmtsCmCurr1DaySeriousPeriodRngLoss OBJECT-TYPE
          SYNTAX  Counter32
          MAX-ACCESS  read-only
          STATUS  current
          DESCRIPTION
                "
                Indicates the number of consecutive periodic ranging request failures during the current 24-hour.
                "
          ::= { hwCmtsCmCurrEntry 21 }

    hwCmtsCmCurr1DayPowerAdjust OBJECT-TYPE
          SYNTAX  Counter32
          MAX-ACCESS  read-only
          STATUS  current
          DESCRIPTION
                "
                Indicates the number of CM transmit power adjustments during the current 24-hour.
                "
          ::= { hwCmtsCmCurrEntry 22 }

    hwCmtsCmCurr1DaySeriousPowerAdjust OBJECT-TYPE
          SYNTAX  Counter32
          MAX-ACCESS  read-only
          STATUS  current
          DESCRIPTION
                "
                Indicates the number of severe CM transmit power adjustments during the current 24-hour.
                "
          ::= { hwCmtsCmCurrEntry 23 }

    hwCmtsCmCurrEverBeforeStartTime OBJECT-TYPE
          SYNTAX  OCTET STRING
          MAX-ACCESS  read-only
          STATUS  current
          DESCRIPTION
                "
                Indicates the start time of the statistical period.
                "
          ::= { hwCmtsCmCurrEntry 24 }


    hwCmtsCmCurrEverBeforeElapsedTime OBJECT-TYPE
          SYNTAX  Integer32
          UNITS   "s"
          MAX-ACCESS  read-only
          STATUS  current
          DESCRIPTION
                "
                Indicates the elapsed time in the statistical period.
                "
          ::= { hwCmtsCmCurrEntry 25 }

    hwCmtsCmCurrEverBeforeValidityFlag OBJECT-TYPE
          SYNTAX  Integer32 (1..2)
          MAX-ACCESS  read-only
          STATUS  current
          DESCRIPTION
                "
                Indicates the flag for statistical information.
                Options:
                1-Yes
                2-No
                "
          ::= { hwCmtsCmCurrEntry 26 }

    hwCmtsCmCurrEverBeforeSuccessReg OBJECT-TYPE
          SYNTAX  Counter32
          MAX-ACCESS  read-only
          STATUS  current
          DESCRIPTION
                "
                Indicates the number of previous successfully registered.
                "
          ::= { hwCmtsCmCurrEntry 27 }

    hwCmtsCmCurrEverBeforeFailReg OBJECT-TYPE
          SYNTAX  Counter32
          MAX-ACCESS  read-only
          STATUS  current
          DESCRIPTION
                "
                Indicates the number of previous registration failed.
                "
          ::= { hwCmtsCmCurrEntry 28 }

    hwCmtsCmCurrEverBeforeRepeatReg OBJECT-TYPE
          SYNTAX  Counter32
          MAX-ACCESS  read-only
          STATUS  current
          DESCRIPTION
                "
                Indicates the number of previous repeated registration.
                "
          ::= { hwCmtsCmCurrEntry 29 }

    hwCmtsCmCurrEverBeforeSuccessPeriodRng OBJECT-TYPE
          SYNTAX  Counter32
          MAX-ACCESS  read-only
          STATUS  current
          DESCRIPTION
                "
                Indicates the number of previous periodic ranging request.
                "
          ::= { hwCmtsCmCurrEntry 30 }

    hwCmtsCmCurrEverBeforePeriodRngLoss OBJECT-TYPE
          SYNTAX  Counter32
          MAX-ACCESS  read-only
          STATUS  current
          DESCRIPTION
                "
                Indicates the number of previous loss of periodic ranging request.
                "
          ::= { hwCmtsCmCurrEntry 31 }

    hwCmtsCmCurrEverBeforeSeriousPeriodRngLoss OBJECT-TYPE
          SYNTAX  Counter32
          MAX-ACCESS  read-only
          STATUS  current
          DESCRIPTION
                "
                Indicates the number of previous loss of the severe periodic ranging request.
                "
          ::= { hwCmtsCmCurrEntry 32 }

    hwCmtsCmCurrEverBeforePowerAdjust OBJECT-TYPE
          SYNTAX  Counter32
          MAX-ACCESS  read-only
          STATUS  current
          DESCRIPTION
                "
                Indicates the number of previous transmit power adjustment.
                "
          ::= { hwCmtsCmCurrEntry 33 }

    hwCmtsCmCurrEverBeforeSeriousPowerAdjust OBJECT-TYPE
          SYNTAX  Counter32
          MAX-ACCESS  read-only
          STATUS  current
          DESCRIPTION
                " 
                Indicates the number of previous severe power adjustment.
                "
          ::= { hwCmtsCmCurrEntry 34 }          
          
   hwCmtsCmCurrEverBeforeUnstableConnectionCount OBJECT-TYPE
          SYNTAX  Integer32
          MAX-ACCESS  read-only
          STATUS  current
          DESCRIPTION
                " 
                Indicates the number of previous unstable connection.
                "
          ::= { hwCmtsCmCurrEntry 35 } 
          
    hwCmtsCmCurrEverBeforeLastUnstableConnectionTime OBJECT-TYPE
          SYNTAX  DateAndTime
          MAX-ACCESS  read-only
          STATUS  current
          DESCRIPTION
                " 
                Indicates the time of the latest unstable connection.
                "
          ::= { hwCmtsCmCurrEntry 36 }
          
    hwCmtsCmCurrEverBeforeFirstUnstableConnectionTime OBJECT-TYPE
          SYNTAX  DateAndTime
          MAX-ACCESS  read-only
          STATUS  current
          DESCRIPTION
                " 
                Indicates the time of the first unstable connection.
                "
          ::= { hwCmtsCmCurrEntry 37 }
      
       hwCmtsCmCurrEverBeforeLastRepeatRegTime OBJECT-TYPE
          SYNTAX  DateAndTime
          MAX-ACCESS  read-only
          STATUS  current
          DESCRIPTION
                " 
                Indicates the time of the latest repeated registration.
                "
          ::= { hwCmtsCmCurrEntry 38 }
          
        hwCmtsCmCurrEverBeforeFirstRepeatRegTime OBJECT-TYPE
          SYNTAX  DateAndTime
          MAX-ACCESS  read-only
          STATUS  current
          DESCRIPTION
                " 
                Indicates the time of the first repeated registration.
                "
          ::= { hwCmtsCmCurrEntry 39 }
          
        hwCmtsCmCurrEverBeforeLastSeriousPeriodRngLossTime OBJECT-TYPE
          SYNTAX  DateAndTime
          MAX-ACCESS  read-only
          STATUS  current
          DESCRIPTION
                " 
                Indicates the time of the latest loss of the severe periodic ranging request.
                "                           
          ::= { hwCmtsCmCurrEntry 40 }
          
        hwCmtsCmCurrEverBeforeFirstSeriousPeriodRngLossTime OBJECT-TYPE
          SYNTAX  DateAndTime
          MAX-ACCESS  read-only
          STATUS  current
          DESCRIPTION
                " 
                 Indicates the time of the first loss of the severe periodic ranging request.
                "
          ::= { hwCmtsCmCurrEntry 41 }
          
         hwCmtsCmCurrEverBeforeLastSeriousPowerAdjustTime OBJECT-TYPE
          SYNTAX  DateAndTime
          MAX-ACCESS  read-only
          STATUS  current
          DESCRIPTION
                "
                Indicates the time of the latest severe power adjustment.
                "
          ::= { hwCmtsCmCurrEntry 42 }
          
         hwCmtsCmCurrEverBeforeFirstSeriousPowerAdjustTime OBJECT-TYPE
          SYNTAX  DateAndTime
          MAX-ACCESS  read-only
          STATUS  current
          DESCRIPTION
                " 
                Indicates the time of the first severe power adjustment.
                "
          ::= { hwCmtsCmCurrEntry 43 }
          
         hwCmtsCmCurr15MCrc OBJECT-TYPE
          SYNTAX  Counter64
          MAX-ACCESS  read-only
          STATUS  current
          DESCRIPTION
                " 
                Indicates the number of CRC failures during the current 15-minute.
                0 represents invalid value.
                "
          ::= { hwCmtsCmCurrEntry 44 }
          
         hwCmtsCmCurr1DayCrc OBJECT-TYPE
          SYNTAX  Counter64
          MAX-ACCESS  read-only
          STATUS  current
          DESCRIPTION
                " 
                Indicates the number of CRC failures during the current 24-hour.
                0 represents invalid value.
                "
          ::= { hwCmtsCmCurrEntry 45 }
          
          hwCmtsCmCurrEverBeforeCrc OBJECT-TYPE
          SYNTAX  Counter64
          MAX-ACCESS  read-only
          STATUS  current
          DESCRIPTION
                " 
                Indicates the number of CRC failures.
                0 represents invalid value.
                "
          ::= { hwCmtsCmCurrEntry 46 }

    -- Table hwCmtsCmHist15MinTable
    hwCmtsCmHist15MinTable OBJECT-TYPE
          SYNTAX     SEQUENCE OF HwCmtsCmHist15MinEntry
          MAX-ACCESS not-accessible
          STATUS     current
          DESCRIPTION
                "
                Indicates the historical 15-minute performance statistics.
                The indexes of this table are hwCmtsCmHist15MId and hwCmtsCmHist15MInterval.
                "
          ::= { hwCmtsAccessObject 18 }

    hwCmtsCmHist15MinEntry OBJECT-TYPE
          SYNTAX     HwCmtsCmHist15MinEntry
          MAX-ACCESS not-accessible
          STATUS     current
          DESCRIPTION
                "
                Indicates the historical 15-minute performance statistics.
                The indexes of this entry are hwCmtsCmHist15MId and hwCmtsCmHist15MInterval.
                "
          INDEX       { hwCmtsCmHist15MId, hwCmtsCmHist15MInterval }
          ::= { hwCmtsCmHist15MinTable 1 }

    HwCmtsCmHist15MinEntry ::=
          SEQUENCE {
                    hwCmtsCmHist15MId                    Integer32,
                    hwCmtsCmHist15MInterval              Integer32,
                    hwCmtsCmHist15MStartTime             OCTET STRING,
                    hwCmtsCmHist15MElapsedTime           Integer32,
                    hwCmtsCmHist15MValidityFlag          Integer32,
                    hwCmtsCmHist15MSuccessReg            Counter32,
                    hwCmtsCmHist15MFailReg               Counter32,
                    hwCmtsCmHist15MRepeatReg             Counter32,
                    hwCmtsCmHist15MSuccessPeriodRng      Counter32,
                    hwCmtsCmHist15MPeriodRngLoss         Counter32,
                    hwCmtsCmHist15MSeriousPeriodRngLoss  Counter32,
                    hwCmtsCmHist15MPowerAdjust           Counter32,
                    hwCmtsCmHist15MSeriousPowerAdjust    Counter32,
                    hwCmtsCmHist15MCrc                   Counter64
                   }



    hwCmtsCmHist15MId OBJECT-TYPE
          SYNTAX  Integer32
          MAX-ACCESS   not-accessible
          STATUS  current
          DESCRIPTION
                "
                Indicates a CM index.
                "
          ::= { hwCmtsCmHist15MinEntry 1 }

    hwCmtsCmHist15MInterval OBJECT-TYPE
          SYNTAX  Integer32 (1..96)
          MAX-ACCESS   not-accessible
          STATUS  current
          DESCRIPTION
                "
                The previous 15 minutes are considered as the first range.
                The greater the value, the earlier the time.
                "
          ::= { hwCmtsCmHist15MinEntry 2 }

    hwCmtsCmHist15MStartTime OBJECT-TYPE
          SYNTAX  OCTET STRING
          MAX-ACCESS  read-only
          STATUS  current
          DESCRIPTION
                "
                Indicates the start time of a statistical period.
                "
          ::= { hwCmtsCmHist15MinEntry 3 }

    hwCmtsCmHist15MElapsedTime OBJECT-TYPE
          SYNTAX  Integer32
          UNITS   "s"
          MAX-ACCESS  read-only
          STATUS  current
          DESCRIPTION
                "
                Indicates the elapsed time in a statistical period.
                "
          ::= { hwCmtsCmHist15MinEntry 4 }

    hwCmtsCmHist15MValidityFlag OBJECT-TYPE
          SYNTAX  Integer32 (1..2)
          MAX-ACCESS  read-only
          STATUS  current
          DESCRIPTION
                "
                Indicates the flag for statistical information.
                Options:
                1-Yes
                2-No
                "
          ::= { hwCmtsCmHist15MinEntry 5 }





    hwCmtsCmHist15MSuccessReg OBJECT-TYPE
          SYNTAX  Counter32
          MAX-ACCESS  read-only
          STATUS  current
          DESCRIPTION
                "
                Indicates the number of registration requests initiated by a CM during the historical 15-minute.
                "
          ::= { hwCmtsCmHist15MinEntry 6 }

    hwCmtsCmHist15MFailReg OBJECT-TYPE
          SYNTAX  Counter32
          MAX-ACCESS  read-only
          STATUS  current
          DESCRIPTION
                "
                Indicates the number of CM registration failures during the historical 15-minute.
                "
          ::= { hwCmtsCmHist15MinEntry 7 }

    hwCmtsCmHist15MRepeatReg OBJECT-TYPE
          SYNTAX  Counter32
          MAX-ACCESS  read-only
          STATUS  current
          DESCRIPTION
                "
                Indicates the number of repeated registrations during the historical 15-minute.
                "
          ::= { hwCmtsCmHist15MinEntry 8 }

    hwCmtsCmHist15MSuccessPeriodRng OBJECT-TYPE
          SYNTAX  Counter32
          MAX-ACCESS  read-only
          STATUS  current
          DESCRIPTION
                "
                Indicates the number of periodic ranging requests initiated by a CM during the historical 15-minute.
                "
          ::= { hwCmtsCmHist15MinEntry 9 }

    hwCmtsCmHist15MPeriodRngLoss OBJECT-TYPE
          SYNTAX  Counter32
          MAX-ACCESS  read-only
          STATUS  current
          DESCRIPTION
                "
                Indicates the number of lost periodic ranging requests initiated by a CM during the historical 15-minute.
                "
          ::= { hwCmtsCmHist15MinEntry 10 }

    hwCmtsCmHist15MSeriousPeriodRngLoss OBJECT-TYPE
          SYNTAX  Counter32
          MAX-ACCESS  read-only
          STATUS  current
          DESCRIPTION
                "
                Indicates the number of consecutive periodic ranging request failures during the historical 15-minute.
                "
          ::= { hwCmtsCmHist15MinEntry 11 }

    hwCmtsCmHist15MPowerAdjust OBJECT-TYPE
          SYNTAX  Counter32
          MAX-ACCESS  read-only
          STATUS  current
          DESCRIPTION
                "
                Indicates the number of CM transmit power adjustments during the historical 15-minute.
                "
          ::= { hwCmtsCmHist15MinEntry 12 }

    hwCmtsCmHist15MSeriousPowerAdjust OBJECT-TYPE
          SYNTAX  Counter32
          MAX-ACCESS  read-only
          STATUS  current
          DESCRIPTION
                "
                Indicates the number of severe CM transmit power adjustments during the historical 15-minute.
                "
          ::= { hwCmtsCmHist15MinEntry 13 }

    hwCmtsCmHist15MCrc OBJECT-TYPE
          SYNTAX  Counter64
          MAX-ACCESS  read-only
          STATUS  current
          DESCRIPTION
                "
                Indicates the number of CRC failures during the historical 15-minute.
                0 represents invalid value.
                "
          ::= { hwCmtsCmHist15MinEntry 14 }


    -- Table hwCmtsCmHist1DayTable
    hwCmtsCmHist1DayTable OBJECT-TYPE
          SYNTAX     SEQUENCE OF HwCmtsCmHist1DayEntry
          MAX-ACCESS not-accessible
          STATUS     current
          DESCRIPTION
                "
                Indicates the historical 24-hour performance statistics.
                The indexes of this table are hwCmtsCmHist1DayId and hwCmtsCmHist1DayInterval.
                "
          ::= { hwCmtsAccessObject 19 }

    hwCmtsCmHist1DayEntry OBJECT-TYPE
          SYNTAX     HwCmtsCmHist1DayEntry
          MAX-ACCESS not-accessible
          STATUS     current
          DESCRIPTION
                "
                Indicates the historical 24-hour performance statistics.
                The indexes of this entry are hwCmtsCmHist1DayId and hwCmtsCmHist1DayInterval.
                 "
          INDEX       { hwCmtsCmHist1DayId, hwCmtsCmHist1DayInterval }
          ::= { hwCmtsCmHist1DayTable 1 }

    HwCmtsCmHist1DayEntry ::=
          SEQUENCE {
                    hwCmtsCmHist1DayId                    Integer32,
                    hwCmtsCmHist1DayInterval              Integer32,
                    hwCmtsCmHist1DayStartTime             OCTET STRING,
                    hwCmtsCmHist1DayElapsedTime           Integer32,
                    hwCmtsCmHist1DayValidityFlag          Integer32,
                    hwCmtsCmHist1DaySuccessReg            Counter32,
                    hwCmtsCmHist1DayFailReg               Counter32,
                    hwCmtsCmHist1DayRepeatReg             Counter32,
                    hwCmtsCmHist1DaySuccessPeriodRng      Counter32,
                    hwCmtsCmHist1DayPeriodRngLoss         Counter32,
                    hwCmtsCmHist1DaySeriousPeriodRngLoss  Counter32,
                    hwCmtsCmHist1DayPowerAdjust           Counter32,
                    hwCmtsCmHist1DaySeriousPowerAdjust    Counter32,
                    hwCmtsCmHist1DayCrc                   Counter64
                   }



    hwCmtsCmHist1DayId OBJECT-TYPE
          SYNTAX  Integer32
          MAX-ACCESS   not-accessible
          STATUS  current
          DESCRIPTION
                "
                Indicates a CM index.
                "
          ::= { hwCmtsCmHist1DayEntry 1 }

    hwCmtsCmHist1DayInterval OBJECT-TYPE
          SYNTAX  Integer32 (1..30)
          MAX-ACCESS   not-accessible
          STATUS  current
          DESCRIPTION
                "
                The previous 24 hours are considered as the first range.
                The greater the value, the earlier the time.
                "
          ::= { hwCmtsCmHist1DayEntry 2 }

    hwCmtsCmHist1DayStartTime OBJECT-TYPE
          SYNTAX  OCTET STRING
          MAX-ACCESS  read-only
          STATUS  current
          DESCRIPTION
                "
                Indicates the start time of a statistical period.
                "
          ::= { hwCmtsCmHist1DayEntry 3 }

    hwCmtsCmHist1DayElapsedTime OBJECT-TYPE
          SYNTAX  Integer32
          UNITS   "s"
          MAX-ACCESS  read-only
          STATUS  current
          DESCRIPTION
                "
                Indicates the elapsed time in a statistical period.
                "
          ::= { hwCmtsCmHist1DayEntry 4 }

    hwCmtsCmHist1DayValidityFlag OBJECT-TYPE
          SYNTAX  Integer32 (1..2)
          MAX-ACCESS  read-only
          STATUS  current
          DESCRIPTION
                "
                Indicates the flag for statistical information.
                Options:
                1-Yes
                2-No
                "
          ::= { hwCmtsCmHist1DayEntry 5 }





    hwCmtsCmHist1DaySuccessReg OBJECT-TYPE
          SYNTAX  Counter32
          MAX-ACCESS  read-only
          STATUS  current
          DESCRIPTION
                "
                Indicates the number of registration requests initiated by a CM during the historical 24-hour.
                "
          ::= { hwCmtsCmHist1DayEntry 6 }

    hwCmtsCmHist1DayFailReg OBJECT-TYPE
          SYNTAX  Counter32
          MAX-ACCESS  read-only
          STATUS  current
          DESCRIPTION
                "
                Indicates the number of CM registration failures during the historical 24-hour.
                "
          ::= { hwCmtsCmHist1DayEntry 7 }

    hwCmtsCmHist1DayRepeatReg OBJECT-TYPE
          SYNTAX  Counter32
          MAX-ACCESS  read-only
          STATUS  current
          DESCRIPTION
                "
                Indicates the number of repeated registrations during the historical 24-hour.
                "
          ::= { hwCmtsCmHist1DayEntry 8 }

    hwCmtsCmHist1DaySuccessPeriodRng OBJECT-TYPE
          SYNTAX  Counter32
          MAX-ACCESS  read-only
          STATUS  current
          DESCRIPTION
                "
                Indicates the number of periodic ranging requests initiated by a CM during the historical 24-hour.
                "
          ::= { hwCmtsCmHist1DayEntry 9 }

    hwCmtsCmHist1DayPeriodRngLoss OBJECT-TYPE
          SYNTAX  Counter32
          MAX-ACCESS  read-only
          STATUS  current
          DESCRIPTION
                "
                Indicates the number of lost periodic ranging requests initiated by a CM during the historical 24-hour.
                "
          ::= { hwCmtsCmHist1DayEntry 10 }

    hwCmtsCmHist1DaySeriousPeriodRngLoss OBJECT-TYPE
          SYNTAX  Counter32
          MAX-ACCESS  read-only
          STATUS  current
          DESCRIPTION
                "
                Indicates the number of consecutive periodic ranging request failures during the historical 24-hour.
                "
          ::= { hwCmtsCmHist1DayEntry 11 }

    hwCmtsCmHist1DayPowerAdjust OBJECT-TYPE
          SYNTAX  Counter32
          MAX-ACCESS  read-only
          STATUS  current
          DESCRIPTION
                "
                Indicates the number of CM transmit power adjustments during the historical 24-hour.
                "
          ::= { hwCmtsCmHist1DayEntry 12 }

    hwCmtsCmHist1DaySeriousPowerAdjust OBJECT-TYPE
          SYNTAX  Counter32
          MAX-ACCESS  read-only
          STATUS  current
          DESCRIPTION
                "
                Indicates the number of severe CM transmit power adjustments during the historical 24-hour.
                "
          ::= { hwCmtsCmHist1DayEntry 13 }

    hwCmtsCmHist1DayCrc OBJECT-TYPE
          SYNTAX  Counter64
          MAX-ACCESS  read-only
          STATUS  current
          DESCRIPTION
                "
                Indicates the number of CRC failures during the historical 24-hour.
                0 represents invalid value.
                "
          ::= { hwCmtsCmHist1DayEntry 14 }



  hwCmtsCmStatThresholdTable OBJECT IDENTIFIER ::= { hwCmtsAccessObject  20}
    -- Table hwCmtsCmStatThresholdTable

    hwCmtsCmStatThresholdRepeatReg OBJECT-TYPE
          SYNTAX  Integer32 (60..86400)
          UNITS   "s"
          MAX-ACCESS  read-write
          STATUS  current
          DESCRIPTION
                "
                Indicates the repeated registration interval.
                Default value: 180.
                "
          ::= { hwCmtsCmStatThresholdTable 1 }

    hwCmtsCmStatThresholdSeriousPeriodRngLoss OBJECT-TYPE
          SYNTAX  Integer32 (1..12)
          MAX-ACCESS  read-write
          STATUS  current
          DESCRIPTION
                "
                Indicates the severe loss threshold for periodic ranging requests.
                Default value: 6.
                "
          ::= { hwCmtsCmStatThresholdTable 2 }

    hwCmtsCmStatThresholdSeriousPowerAdjust OBJECT-TYPE
          SYNTAX  Integer32 (1..10)
          UNITS   "dB"
          MAX-ACCESS  read-write
          STATUS  current
          DESCRIPTION
                "
                Indicates the severe power adjustment threshold.
                Default value: 2.
                "
          ::= { hwCmtsCmStatThresholdTable 3 }


    -- Table hwDocsIfCmtsIPToCmTable
    hwDocsIfCmtsIPToCmTable OBJECT-TYPE
          SYNTAX     SEQUENCE OF HwDocsIfCmtsIPToCmEntry
          MAX-ACCESS not-accessible
          STATUS     current
          DESCRIPTION
                "
                Indicates the CM index queried by the IP address of a CM.
                The index of this table is hwDocsIfCmtsCmIPAddr.
                "
          ::= { hwCmtsAccessObject 21 }

    hwDocsIfCmtsIPToCmEntry OBJECT-TYPE
          SYNTAX     HwDocsIfCmtsIPToCmEntry
          MAX-ACCESS not-accessible
          STATUS     current
          DESCRIPTION
                "
                Indicates the CM index queried by the IP address of a CM.
                The index of this entry is hwDocsIfCmtsCmIPAddr.
                 "
          INDEX       { hwDocsIfCmtsCmIPAddr }
          ::= { hwDocsIfCmtsIPToCmTable 1 }

    HwDocsIfCmtsIPToCmEntry ::=
          SEQUENCE {
                    hwDocsIfCmtsCmIPAddr       IpAddress,
                    hwDocsIfCmtsCmPtr          Integer32
                   }

    hwDocsIfCmtsCmIPAddr OBJECT-TYPE
          SYNTAX  IpAddress
          MAX-ACCESS   not-accessible
          STATUS  current
          DESCRIPTION
                "
                Indicates the IP address of the CM.
                "
          ::= { hwDocsIfCmtsIPToCmEntry 1 }

    hwDocsIfCmtsCmPtr OBJECT-TYPE
          SYNTAX  Integer32
          MAX-ACCESS   read-only
          STATUS  current
          DESCRIPTION
                "
                Indicates the CM index.
                "
          ::= { hwDocsIfCmtsIPToCmEntry 2 }


    -- Table hwCmtsMtaInfoTable
    hwCmtsMtaInfoTable OBJECT-TYPE
          SYNTAX     SEQUENCE OF HwCmtsMtaInfoEntry
          MAX-ACCESS not-accessible
          STATUS     current
          DESCRIPTION
                "
                Indicates the basic information about the media terminal adapter (MTA).
                The index of this table is hwCmtsMtaInfoCmId.
                "
          ::= { hwCmtsAccessObject 22 }

    hwCmtsMtaInfoEntry OBJECT-TYPE
          SYNTAX     HwCmtsMtaInfoEntry
          MAX-ACCESS not-accessible
          STATUS     current
          DESCRIPTION
                "
                Indicates the basic information about the media terminal adapter (MTA).
                The index of this entry is hwCmtsMtaInfoCmId.
                "
          INDEX       { hwCmtsMtaInfoCmId }
          ::= { hwCmtsMtaInfoTable 1 }

    HwCmtsMtaInfoEntry ::=
          SEQUENCE {
                    hwCmtsMtaInfoCmId       Integer32,
                    hwCmtsMtaMacAddress     MacAddress,
                    hwCmtsMtaIPAddress      IpAddress,
                    hwCmtsMtaPktcVersion    Integer32
                   }

    hwCmtsMtaInfoCmId OBJECT-TYPE
          SYNTAX  Integer32
          MAX-ACCESS  not-accessible
          STATUS  current
          DESCRIPTION
                "
                Indicates a CM index.
                "
          ::= { hwCmtsMtaInfoEntry 1 }

    hwCmtsMtaMacAddress OBJECT-TYPE
          SYNTAX   MacAddress
          MAX-ACCESS  read-only
          STATUS  current
          DESCRIPTION
                "
                Indicates the MAC address of the MTA.
                "
          ::= { hwCmtsMtaInfoEntry 2 }

    hwCmtsMtaIPAddress OBJECT-TYPE
          SYNTAX  IpAddress
          MAX-ACCESS  read-only
          STATUS  current
          DESCRIPTION
                "
                Indicates the IP address of the MTA.
                "
          ::= { hwCmtsMtaInfoEntry 3 }

    hwCmtsMtaPktcVersion OBJECT-TYPE
          SYNTAX  Integer32  (-1|1..3)
          MAX-ACCESS  read-only
          STATUS  current
          DESCRIPTION
                "
                Indicates the version of PacketCable.
                Options:
                1-packetcable1.0
                2-packetcable1.5
                3-packetcable2.0
                -1 represent invalid version of PacketCable.
                "
          ::= { hwCmtsMtaInfoEntry 4 }


    -- Table hwDocsIfUpstreamChannelStatusTable

    hwDocsIfUpstreamChannelStatusTable OBJECT-TYPE
          SYNTAX     SEQUENCE OF HwDocsIfUpstreamChannelStatusEntry
          MAX-ACCESS not-accessible
          STATUS     current
          DESCRIPTION
               "Indicates the current status of a CMTS upstream channel.
               The index of this table is ifIndex."
          ::= { hwCmtsAccessObject 23 }

    hwDocsIfUpstreamChannelStatusEntry OBJECT-TYPE
          SYNTAX     HwDocsIfUpstreamChannelStatusEntry
          MAX-ACCESS not-accessible
          STATUS     current
          DESCRIPTION
               "Indicates the current status of a CMTS upstream channel.
               The index of this entry is ifIndex."
          INDEX       { ifIndex }
          ::= { hwDocsIfUpstreamChannelStatusTable 1 }

    HwDocsIfUpstreamChannelStatusEntry ::=
          SEQUENCE {
                    hwDocsIfUpstreamChannelStatusFrequency           Integer32,
                    hwDocsIfUpstreamChannelStatusWidth               Integer32,
                    hwDocsIfUpstreamChannelStatusModulationProfile   Unsigned32,
                    hwDocsIfUpstreamChannelStatusRxPower             Integer32,
                    hwDocsIfUpstreamChannelStatusPowerAdjustThreshold Unsigned32,
                    hwDocsIfUpstreamChannelStatusPowerAdjustContinue  Unsigned32,
                    hwDocsIfUpstreamChannelStatusPowerMaxAdjust       Unsigned32
                  }

    hwDocsIfUpstreamChannelStatusFrequency OBJECT-TYPE
          SYNTAX     Integer32  (0..1000000000)
          UNITS   "Hz"
          MAX-ACCESS read-only
          STATUS     current
          DESCRIPTION
               "The current used center frequency of this upstream interface.
                This object returns 0 if the frequency is undefined or unknown.
                Range: 5000000-85000000 for AnnexA
                       5000000-85000000 for AnnexB
                "
          ::= { hwDocsIfUpstreamChannelStatusEntry 1 }

    hwDocsIfUpstreamChannelStatusWidth OBJECT-TYPE
          SYNTAX     Integer32  (0..64000000)
          UNITS   "Hz"
          MAX-ACCESS read-only
          STATUS     current
          DESCRIPTION
               "The current used Channel Width of this upstream interface.
               This object returns 0 if the Width is undefined or unknown.
               now support 1600000, 3200000, 6400000, other is reserved
               Default: 3200000
               "
          ::= { hwDocsIfUpstreamChannelStatusEntry 2 }


    hwDocsIfUpstreamChannelStatusModulationProfile OBJECT-TYPE
          SYNTAX     Unsigned32  (0..128)
          MAX-ACCESS read-only
          STATUS     current
          DESCRIPTION
               "The current used Modulation Profile of this upstream interface.
                This object returns 0 if the Modulation Profile is undefined or unknown."
          ::= { hwDocsIfUpstreamChannelStatusEntry 3 }

    hwDocsIfUpstreamChannelStatusRxPower OBJECT-TYPE
          SYNTAX     Integer32
          UNITS     "0.1dBmV"
          MAX-ACCESS read-only
          STATUS     current
          DESCRIPTION
               "This object indicates the receive power of the current upstream channel. 
                If -2147483647 is returned, the receive power is undefined or cannot be identified.
                Value range: -2147483647|-130..230
               "
          ::= { hwDocsIfUpstreamChannelStatusEntry 4 }

    hwDocsIfUpstreamChannelStatusPowerAdjustThreshold OBJECT-TYPE
          SYNTAX     Unsigned32
          UNITS     "dB"
          MAX-ACCESS read-only
          STATUS     current
          DESCRIPTION
               "This object indicates transmit power adjustment threshold.
                2147483647(0x7FFFFFFF) represents invalid value.
               "
          ::= { hwDocsIfUpstreamChannelStatusEntry 5 }

    hwDocsIfUpstreamChannelStatusPowerAdjustContinue OBJECT-TYPE
          SYNTAX     Unsigned32
          UNITS     "dB"
          MAX-ACCESS read-only
          STATUS     current
          DESCRIPTION
               "This object indicates ranging continue status threshold.
                2147483647(0x7FFFFFFF) represents invalid value.
               "
          ::= { hwDocsIfUpstreamChannelStatusEntry 6 }

    hwDocsIfUpstreamChannelStatusPowerMaxAdjust OBJECT-TYPE
          SYNTAX     Unsigned32
          UNITS     "dB"
          MAX-ACCESS read-only
          STATUS     current
          DESCRIPTION
               "This object indicates maximum power adjustment.
                2147483647(0x7FFFFFFF) represents invalid value.
               "
          ::= { hwDocsIfUpstreamChannelStatusEntry 7 }

   -- Table hwCmtsDownChannelTable
    hwCmtsDownChannelTable OBJECT-TYPE
          SYNTAX     SEQUENCE OF HwCmtsDownChannelEntry
          MAX-ACCESS not-accessible
          STATUS     current
          DESCRIPTION
               "Indicates the signal quality of a CMTS downstream channel.
               The index of this table is ifIndex."
          ::= { hwCmtsAccessObject 24 }

    hwCmtsDownChannelEntry OBJECT-TYPE
          SYNTAX     HwCmtsDownChannelEntry
          MAX-ACCESS not-accessible
          STATUS     current
          DESCRIPTION
               "Indicates the signal quality of a CMTS downstream channel.
               The index of this entry is ifIndex."
          INDEX       { ifIndex }
          ::= { hwCmtsDownChannelTable 1 }

    HwCmtsDownChannelEntry ::=
          SEQUENCE {
                    hwCmtsDownChannelMaxDataRate           Integer32,
                    hwCmtsDownChannelRealTimeDataRate      Integer32,
                    hwCmtsDownChannel20CmDataRateSum       Unsigned32,
                    hwCmtsDownChannel30CmDataRateSum       Unsigned32,
                    hwCmtsDownChannelSymbolRate            Integer32,
                    hwCmtsDownChannelNotActiveReason        INTEGER,
                    hwCmtsDownChannel20CmUtilization       Counter32,
                    hwCmtsDownChannel30CmUtilization       Counter32,
                    hwCmtsDownChannelRealTimeTxPower       Integer32,
                    hwCmtsDownChannelConfigTxPower         Integer32,
                    hwCmtsDownChannelOperation             INTEGER,
                    hwCmtsDownChannel31CmDataRateSum       Unsigned32, 
                    hwCmtsDownChannel31CmUtilization       Counter32
                   }    

    hwCmtsDownChannelMaxDataRate OBJECT-TYPE
          SYNTAX     Integer32
          UNITS     "kbps"
          MAX-ACCESS read-only
          STATUS     current
          DESCRIPTION
               "The max data rate.
                -1 represents invalid value."
          ::= { hwCmtsDownChannelEntry 1 }

    hwCmtsDownChannelRealTimeDataRate OBJECT-TYPE
          SYNTAX     Integer32
          UNITS     "kbps"
          MAX-ACCESS read-only
          STATUS     current
          DESCRIPTION
               "The real time data rate.
                -1 represents invalid value."
          ::= { hwCmtsDownChannelEntry 2 }

    hwCmtsDownChannel20CmDataRateSum OBJECT-TYPE
          SYNTAX     Unsigned32
          UNITS     "kbps"
          MAX-ACCESS read-only
          STATUS     current
          DESCRIPTION
               "Rate sum of all DOCSIS 2.0 cable modem on the channel.
                0 represents invalid value."
          ::= { hwCmtsDownChannelEntry 3 }

    hwCmtsDownChannel30CmDataRateSum OBJECT-TYPE
          SYNTAX     Unsigned32
          UNITS     "kbps"
          MAX-ACCESS read-only
          STATUS     current
          DESCRIPTION
               "Rate sum of all DOCSIS 3.0 cable modem on the channel.
                0 represents invalid value."
          ::= { hwCmtsDownChannelEntry 4 }
          
    hwCmtsDownChannelSymbolRate OBJECT-TYPE
          SYNTAX     Integer32
          UNITS     "0.001Msym/s"
          MAX-ACCESS read-only
          STATUS     current
          DESCRIPTION
               "Indicates the current symbol rate of a CMTS downstream channel.
                The default value is 6952."
          ::= { hwCmtsDownChannelEntry 5 }
          
       hwCmtsDownChannelNotActiveReason OBJECT-TYPE
          SYNTAX     INTEGER
              {
              other(1),
              noLicense(2),
              channelModeErr(3),
              exceedMaxChannelNum(4),
              exceedMaxFreq(5),
              exceedMaxFreqSpan(6),
              eqamSymbolRateConflict(7),
              exceedMaxFreqGroup(9),
              exceedDocsisDsNum(13),
              exceedDsEqamNum(14),
              exceedDocsisAndVodEqamDsNum(16), 
              notSupportChannelAnnex(20),
              freqProfMismatch(21),
              channelIdOccupiedByOther(22),
              overlapfreqwidth(23),
              invalid(-1)
              }
          MAX-ACCESS read-only
          STATUS     current
          DESCRIPTION
               "The reason of downstream channel not active.
                Options:
                1.other(1)                          - Other reason                   
                2.noLicense(2)                      - No license                 
                3.channelModeErr(3)                 - Channel mode error            
                4.exceedMaxChannelNum(4)            - Channel ID exceeds actual capability      
                5.exceedMaxFreq(5)                  - The channel frequency exceeds actual capability             
                6.exceedMaxFreqSpan(6)              - Exceed maximum frequency span         
                7.eqamSymbolRateConflict(7)         - The number of EQAM symbol-rate exceeds the actual capability        
                8.exceedMaxFreqGroup(9)             - Exceed maximum frequency group number 
                9.exceedDocsisDsNum(13)             - The number of DOCSIS downstream channel exceeds real capability 
                10.exceedDsEqamNum(14)              - The number of EQAM downstream channel exceeds real capability 
                11.exceedDocsisAndVodEqamDsNum(16)  - The total number of DOCSIS and EQAM VOD downstream channels exceeds the actual capability 
                12.notSupportChannelAnnex(20)       - Not support channel Annex
                13.freqProfMismatch(21)             - The frequency and the frequency profile configured for the port do not match     
                14.channelIdOccupiedByOther(22)     - The channel ID is occupied by another channel
                15.overlapfreqwidth(23)             - The difference of frequency between two downstream channels is incorrect. It must be at least 8 MHz in AnnexA mode and 6 MHz in AnnexB mode      
                16.invalid(-1)                      - Indicates the downstream channel is active                  
               "  
          ::= { hwCmtsDownChannelEntry 6 }

    hwCmtsDownChannel20CmUtilization OBJECT-TYPE
          SYNTAX     Counter32
          UNITS     "%"
          MAX-ACCESS read-only
          STATUS     current
          DESCRIPTION
               "
               Traffic ratio of DOCSIS 2.0 on the downstream channel. 
               DOCSIS 2.0 traffic ratio on the downstream channel = All DOCSIS 2.0 service traffic on the downstream channel/Capacity of the downstream channel.
               0 represents invalid value.
               "
          ::= { hwCmtsDownChannelEntry 7 }          

    hwCmtsDownChannel30CmUtilization OBJECT-TYPE
          SYNTAX     Counter32
          UNITS     "%"
          MAX-ACCESS read-only
          STATUS     current
          DESCRIPTION
               "
               Traffic ratio of DOCSIS 3.0 on the downstream channel. 
               DOCSIS 3.0 traffic ratio on the downstream channel = All DOCSIS 3.0 service traffic on the downstream channel/Capacity of the downstream channel.
               0 represents invalid value.
               "
          ::= { hwCmtsDownChannelEntry 8 }  
            
    hwCmtsDownChannelRealTimeTxPower OBJECT-TYPE
          SYNTAX     Integer32
          UNITS      "0.1dBmV"
          MAX-ACCESS read-only
          STATUS     current
          DESCRIPTION
               "At the CMTS, the real time transmit power. 
               If the interface is down, this object returns the configured value (CMTS).
               If -2147483647 is returned, the transmit power is undefined or cannot be identified.
               The default value is 450."
          ::= { hwCmtsDownChannelEntry 9 }
     
    hwCmtsDownChannelConfigTxPower OBJECT-TYPE
        SYNTAX   Integer32
        UNITS      "0.1dBmV"
        MAX-ACCESS  read-only
        STATUS      current
        DESCRIPTION
             "At the CMTS, the configured transmit power. This object returns the configured value (CMTS).
              The invalid value is -2147483647. If -2147483647 is returned, the transmit power is undefined or cannot be identified. 
              The default value is 450."
         ::= { hwCmtsDownChannelEntry 10 }  
             
    hwCmtsDownChannelOperation OBJECT-TYPE
        SYNTAX   INTEGER
            {
                clearStat(1),
                invalidValue(-1)
            }
        MAX-ACCESS  read-write
        STATUS      current
        DESCRIPTION
             "clear statistics of the downstream channel on cable port.
             Options:
             1. clearStat(1)         - clear down channel statistics. 
             2. invalidValue(-1)     - invalid value.
             "
         ::= { hwCmtsDownChannelEntry 11 }           
         
    hwCmtsDownChannel31CmDataRateSum OBJECT-TYPE
          SYNTAX     Unsigned32
          UNITS     "kbps"
          MAX-ACCESS read-only
          STATUS     current
          DESCRIPTION
               "Rate sum of all DOCSIS 3.1 cable modem on the downstream channel.
                0 represents invalid value."
          ::= { hwCmtsDownChannelEntry 12 } 
          
    hwCmtsDownChannel31CmUtilization OBJECT-TYPE
          SYNTAX     Counter32
          UNITS     "%"
          MAX-ACCESS read-only
          STATUS     current
          DESCRIPTION
               "
               Traffic ratio of DOCSIS 3.1 on the downstream channel. 
               DOCSIS 3.1 traffic ratio on the downstream channel = All DOCSIS 3.1 service traffic on the downstream channel/Capacity of the downstream channel.
               0 represents invalid value.
               "
          ::= { hwCmtsDownChannelEntry 13 }  



  -- Table hwCmtsCmNumSummaryTable
    hwCmtsCmNumSummaryTable OBJECT-TYPE
          SYNTAX     SEQUENCE OF HwCmtsCmNumSummaryEntry
          MAX-ACCESS not-accessible
          STATUS     current
          DESCRIPTION
               "Indicates the number of cable modem by one port.
               The index of this table is hwCmtsCmNumSummaryIfIndex."
          ::= { hwCmtsAccessObject 25 }

    hwCmtsCmNumSummaryEntry OBJECT-TYPE
          SYNTAX     HwCmtsCmNumSummaryEntry
          MAX-ACCESS not-accessible
          STATUS     current
          DESCRIPTION
               "Indicates the number of cable modem by one port.
                The index of this entry is hwCmtsCmNumSummaryIfIndex."
          INDEX       { hwCmtsCmNumSummaryIfIndex }
          ::= { hwCmtsCmNumSummaryTable 1 }

    HwCmtsCmNumSummaryEntry ::=
          SEQUENCE {
                    hwCmtsCmNumSummaryIfIndex                Integer32,
                    hwCmtsCmNumSummaryPortIfIndex            Integer32,
                    hwCmtsCmNumSummaryIfType                 INTEGER,
                    hwCmtsCmNumSummaryTotalCmNum             Unsigned32,
                    hwCmtsCmNumSummaryOnlineCmNum            Unsigned32,
                    hwCmtsCmNumSummaryUnOnlineCmNum          Unsigned32,
                    hwCmtsCmNumSummaryOfflineCmNum           Unsigned32,
                    hwCmtsCmNumSummaryWidebandCmNum          Unsigned32,
                    hwCmtsCmNumSummaryRangingCompleteCmNum   Unsigned32,
                    hwCmtsCmNumSummaryStartDhcpV4CmNum       Unsigned32,
                    hwCmtsCmNumSummaryDhcpOfferCmNum         Unsigned32,
                    hwCmtsCmNumSummaryDhcpv4CompleteCmNum    Unsigned32,
                    hwCmtsCmNumSummaryDhcpV4RequestCmNum     Unsigned32,
                    hwCmtsCmNumSummaryStartDhcpV6CmNum       Unsigned32,
                    hwCmtsCmNumSummaryDhcpv6AdvertiseCmNum   Unsigned32,
                    hwCmtsCmNumSummaryDhcpV6RequestCmNum     Unsigned32,
                    hwCmtsCmNumSummaryDhcpV6CompleteCmNum    Unsigned32,
                    hwCmtsCmNumSummaryStartTftpCmNum         Unsigned32,
                    hwCmtsCmNumSummaryTftpCompleteCmNum      Unsigned32,
                    hwCmtsCmNumSummaryEaeCmNum               Unsigned32,
                    hwCmtsCmNumSummaryIfName                 OCTET STRING,
                    hwCmtsCmNumSummaryInitCmNum              Unsigned32,
                    hwCmtsCmNumSummaryRejectCmNum            Unsigned32
                   }
                   
    hwCmtsCmNumSummaryIfIndex OBJECT-TYPE
          SYNTAX  Integer32
          MAX-ACCESS  not-accessible
          STATUS  current
          DESCRIPTION
                "Indicates the index of CM summary information table.
                The ifIndex have three types 
                1. docsis port ifIndex
                2. upstream channel ifIndex, include channel type, docsis port index and channel index, if channel index is 0, indicates query cm that use multichannel
                3. downstream channel ifIndex, include channel type, docsis port index and channel index, if channel index is 0, indicates query cm that use multichannel"
          ::= { hwCmtsCmNumSummaryEntry 1 }

    hwCmtsCmNumSummaryPortIfIndex OBJECT-TYPE
          SYNTAX     Integer32
          MAX-ACCESS read-only
          STATUS     current
          DESCRIPTION
               "Indicates the docsis port IfIndex"
          ::= { hwCmtsCmNumSummaryEntry 2 }

    hwCmtsCmNumSummaryIfType OBJECT-TYPE
          SYNTAX  INTEGER{uschannel(59),dschannel(60),docsisport(62)}
          MAX-ACCESS read-only
          STATUS     current
          DESCRIPTION
                "Indicates the query type.
                Options:
                1. uschannel(59) -Indicates the type is upstream channel 
                2. dschannel(60) -Indicates the type is downstream channel 
                3. docsisport(62)-Indicates the type is docsis port 
                "
          ::= { hwCmtsCmNumSummaryEntry 3 }

    hwCmtsCmNumSummaryTotalCmNum OBJECT-TYPE
          SYNTAX     Unsigned32
          MAX-ACCESS read-only
          STATUS     current
          DESCRIPTION
               "The number of CMs."
          ::= { hwCmtsCmNumSummaryEntry 4 }

    hwCmtsCmNumSummaryOnlineCmNum OBJECT-TYPE
          SYNTAX     Unsigned32
          MAX-ACCESS read-only
          STATUS     current
          DESCRIPTION
               "The number of registered CMs."
          ::= { hwCmtsCmNumSummaryEntry 5 }

    hwCmtsCmNumSummaryUnOnlineCmNum OBJECT-TYPE
          SYNTAX     Unsigned32
          MAX-ACCESS read-only
          STATUS     current
          DESCRIPTION
               "The number of unregistered CMs."
          ::= { hwCmtsCmNumSummaryEntry 6 }

    hwCmtsCmNumSummaryOfflineCmNum OBJECT-TYPE
          SYNTAX     Unsigned32
          MAX-ACCESS read-only
          STATUS     current
          DESCRIPTION
               "The number of CMs in status of offline."
          ::= { hwCmtsCmNumSummaryEntry 7 }

    hwCmtsCmNumSummaryWidebandCmNum OBJECT-TYPE
          SYNTAX     Unsigned32
          MAX-ACCESS read-only
          STATUS     current
          DESCRIPTION
               "The number of widband CMs."
          ::= { hwCmtsCmNumSummaryEntry 8 }

    hwCmtsCmNumSummaryRangingCompleteCmNum OBJECT-TYPE
          SYNTAX     Unsigned32
          MAX-ACCESS read-only
          STATUS     current
          DESCRIPTION
               "The number of ranging complete CMs."
          ::= { hwCmtsCmNumSummaryEntry 9 }

    hwCmtsCmNumSummaryStartDhcpV4CmNum OBJECT-TYPE
          SYNTAX     Unsigned32
          MAX-ACCESS read-only
          STATUS     current
          DESCRIPTION
               "The number of CMs in status of start DHCP V4."
          ::= { hwCmtsCmNumSummaryEntry 10 }

    hwCmtsCmNumSummaryDhcpOfferCmNum OBJECT-TYPE
          SYNTAX     Unsigned32
          MAX-ACCESS read-only
          STATUS     current
          DESCRIPTION
               "The number of CMs in status of DHCP offer."
          ::= { hwCmtsCmNumSummaryEntry 11 }

    hwCmtsCmNumSummaryDhcpv4CompleteCmNum OBJECT-TYPE
          SYNTAX     Unsigned32
          MAX-ACCESS read-only
          STATUS     current
          DESCRIPTION
               "The number of CMs in status of DHCP complete."
          ::= { hwCmtsCmNumSummaryEntry 12 }

    hwCmtsCmNumSummaryDhcpV4RequestCmNum OBJECT-TYPE
          SYNTAX     Unsigned32
          MAX-ACCESS read-only
          STATUS     current
          DESCRIPTION
               "The number of CMs in status of DHCP request."
          ::= { hwCmtsCmNumSummaryEntry 13 }
          
    hwCmtsCmNumSummaryStartDhcpV6CmNum OBJECT-TYPE
          SYNTAX     Unsigned32
          MAX-ACCESS read-only
          STATUS     current
          DESCRIPTION
               "The number of CMs in status of start DHCPV6."
          ::= { hwCmtsCmNumSummaryEntry 14 }
          
    hwCmtsCmNumSummaryDhcpv6AdvertiseCmNum OBJECT-TYPE
          SYNTAX     Unsigned32
          MAX-ACCESS read-only
          STATUS     current
          DESCRIPTION
               "The number of CMs in status of DHCPV6 advertise."
          ::= { hwCmtsCmNumSummaryEntry 15 }
          
    hwCmtsCmNumSummaryDhcpV6RequestCmNum OBJECT-TYPE
          SYNTAX     Unsigned32
          MAX-ACCESS read-only
          STATUS     current
          DESCRIPTION
               "The number of CMs in status of DHCPV6 request."
          ::= { hwCmtsCmNumSummaryEntry 16 }
          
    hwCmtsCmNumSummaryDhcpV6CompleteCmNum OBJECT-TYPE
          SYNTAX     Unsigned32
          MAX-ACCESS read-only
          STATUS     current
          DESCRIPTION
               "The number of CMs in status of DHCPV6 complete."
          ::= { hwCmtsCmNumSummaryEntry 17 }
    hwCmtsCmNumSummaryStartTftpCmNum OBJECT-TYPE
          SYNTAX     Unsigned32
          MAX-ACCESS read-only
          STATUS     current
          DESCRIPTION
               "The number of CMs in status of start TFTP."
          ::= { hwCmtsCmNumSummaryEntry 18 }
    hwCmtsCmNumSummaryTftpCompleteCmNum OBJECT-TYPE
          SYNTAX     Unsigned32
          MAX-ACCESS read-only
          STATUS     current
          DESCRIPTION
               "The number of CMs in status of TFTP complete."
          ::= { hwCmtsCmNumSummaryEntry 19 }
          
    hwCmtsCmNumSummaryEaeCmNum OBJECT-TYPE
          SYNTAX     Unsigned32
          MAX-ACCESS read-only
          STATUS     current
          DESCRIPTION
               "The number of CMs in status of startEAE."
          ::= { hwCmtsCmNumSummaryEntry 20 }  
      
    hwCmtsCmNumSummaryIfName OBJECT-TYPE
        SYNTAX     OCTET STRING(SIZE(0..255))
        MAX-ACCESS read-only
          STATUS     current
        DESCRIPTION
          "
          The textual name of hwCmtsCmNumSummaryIfIndex.
          Return a zero-length OCTET STRING to indicate that the name is not achieved.
          "
        ::= { hwCmtsCmNumSummaryEntry 21 }
        
    hwCmtsCmNumSummaryInitCmNum OBJECT-TYPE
          SYNTAX     Unsigned32
          MAX-ACCESS read-only
          STATUS     current
          DESCRIPTION
               "The number of CMs in the initialize state.
               The CM is determined as in the initialize state if it is in one of the following states:
               1. the CM OFDM initialization ranging message is received.
               2. the CM initialization ranging message is received.
               3. the CM initialization ranging is complete.
               "
          ::= { hwCmtsCmNumSummaryEntry 22 }
          
    hwCmtsCmNumSummaryRejectCmNum OBJECT-TYPE
          SYNTAX     Unsigned32
          MAX-ACCESS read-only
          STATUS     current
          DESCRIPTION
               "The number of CMs in the reject state.
               The CM is determined as in the reject state if it is in one of the following states:
               1. the MIC verification fails.
               2. the BPI authentication fails.
               3. the authentication reject due to other reasons.
               "
          ::= { hwCmtsCmNumSummaryEntry 23 }

    --Table hwCmtsSysCfgTable  begin
       hwCmtsSysCfgTable OBJECT IDENTIFIER ::= {hwCmtsAccessObject 26}
     hwCmtsSysCfgUnstableConnCmNumThreshold OBJECT-TYPE
          SYNTAX  Unsigned32(1..1024)
          MAX-ACCESS  read-write
          STATUS  current
          DESCRIPTION
                "
                Threshold for the number of cable modems with unstable connection.
                Range: 1..1024
                Default: 128
                "
          ::= { hwCmtsSysCfgTable 1 }

     hwCmtsSysCfgMassOfflineCmMonitorPeriod OBJECT-TYPE
          SYNTAX  Unsigned32(1..1440)
          UNITS   "minute"
          MAX-ACCESS  read-write
          STATUS  current
          DESCRIPTION
                "
                Period for monitoring the number of offline cable modems.
                Range: 1..1440
                Default: 5
                "
          ::= { hwCmtsSysCfgTable 2 }

      hwCmtsSysCfgOfflineCmNumThreshold OBJECT-TYPE
          SYNTAX  Unsigned32(1..1024)
          MAX-ACCESS  read-write
          STATUS  current
          DESCRIPTION
                "
                Threshold for the number of offline cable modem.
                Range: 1..1024
                Default: 128
                "
          ::= { hwCmtsSysCfgTable 3 }
          
      hwCmtsSysCfgEQAMUtilizationAlarmThreshold OBJECT-TYPE
          SYNTAX  Integer32(70..100)
          UNITS   "%"
          MAX-ACCESS  read-write
          STATUS  current
          DESCRIPTION
                "
                Threshold for the EQAM channel utilization alarm.
                Range: 70..100
                Default: 100
                "
          ::= { hwCmtsSysCfgTable 4 }
               
      hwCmtsSysSnrDegradeThreshold OBJECT-TYPE
          SYNTAX  Integer32(5..35)
          UNITS   "dB"
          MAX-ACCESS  read-write
          STATUS  current
          DESCRIPTION
                "
                Threshold for the upstream SNR degrade alarm.
                Range: 5..35
                Default: 15
                "
          ::= { hwCmtsSysCfgTable 5 }

      hwCmtsSysSnrRestoreThreshold OBJECT-TYPE
          SYNTAX  Integer32(5..35)
          UNITS   "dB"
          MAX-ACCESS  read-write
          STATUS  current
          DESCRIPTION
                "
                Threshold for the upstream SNR restore alarm.
                Range: 5..35
                Default: 25
                "
          ::= { hwCmtsSysCfgTable 6 } 
                
      hwCmtsSysCfgBandwidthUtilizationInterval OBJECT-TYPE
          SYNTAX      Integer32 (60..86400)
          UNITS       "seconds"
          MAX-ACCESS  read-write
          STATUS  current
          DESCRIPTION
                "The time interval in seconds over which the channel
             utilization is calculated.  All upstream/downstream
             channels use this node to configure."
          ::= { hwCmtsSysCfgTable 7 }

                                 

      --Table   hwCmtsSysCfgTable  end

   -- Table hwDocsIf3CmtsCmCpeStatTable begin
    hwDocsIf3CmtsCmCpeStatTable OBJECT-TYPE
          SYNTAX     SEQUENCE OF HwDocsIf3CmtsCmCpeStatEntry
          MAX-ACCESS not-accessible
          STATUS     current
          DESCRIPTION
               "Indicates the statistics of each type CPE. 
                The index of this table is ifIndex."
          ::= { hwCmtsAccessObject 27 }

    hwDocsIf3CmtsCmCpeStatEntry OBJECT-TYPE
          SYNTAX     HwDocsIf3CmtsCmCpeStatEntry
          MAX-ACCESS not-accessible
          STATUS     current
          DESCRIPTION
               "Indicates the statistics of each type CPE. 
                The index of this entry is ifIndex."
          INDEX       { ifIndex }
          ::= { hwDocsIf3CmtsCmCpeStatTable 1 }

    HwDocsIf3CmtsCmCpeStatEntry ::=
          SEQUENCE {
                    hwDocsIf3CmtsCmCpeStatMTANum              Integer32,
                    hwDocsIf3CmtsCmCpeStatSTBNum              Integer32,
                    hwDocsIf3CmtsCmCpeStatHostNum             Integer32,
                    hwDocsIf3CmtsCmCpeStatRouterNum           Integer32,
                    hwDocsIf3CmtsCmCpeStatUnclassifiedNum     Integer32
                   }

    hwDocsIf3CmtsCmCpeStatMTANum OBJECT-TYPE
          SYNTAX     Integer32
          MAX-ACCESS read-only
          STATUS     current
          DESCRIPTION
               "This object indicates the number of MTA type CPEs."
          ::= { hwDocsIf3CmtsCmCpeStatEntry 1 }

    hwDocsIf3CmtsCmCpeStatSTBNum OBJECT-TYPE
          SYNTAX     Integer32
          MAX-ACCESS read-only
          STATUS     current
          DESCRIPTION
               "This object indicates the number of STB type CPEs."
          ::= { hwDocsIf3CmtsCmCpeStatEntry 2 }

    hwDocsIf3CmtsCmCpeStatHostNum OBJECT-TYPE
          SYNTAX     Integer32
          MAX-ACCESS read-only
          STATUS     current
          DESCRIPTION
               "This object indicates the number of host type CPEs."
          ::= { hwDocsIf3CmtsCmCpeStatEntry 3 }

    hwDocsIf3CmtsCmCpeStatRouterNum OBJECT-TYPE
          SYNTAX     Integer32
          MAX-ACCESS read-only
          STATUS     current
          DESCRIPTION
               "This object indicates the number of router type CPEs."
          ::= { hwDocsIf3CmtsCmCpeStatEntry 4 }

    hwDocsIf3CmtsCmCpeStatUnclassifiedNum OBJECT-TYPE
          SYNTAX     Integer32
          MAX-ACCESS read-only
          STATUS     current
          DESCRIPTION
               "This object indicates the number of unclassified CPEs."
          ::= { hwDocsIf3CmtsCmCpeStatEntry 5 }
          
   -- Table hwDocsIf3CmtsCmCpeStatTable end
   
   -- Table hwDocsIfDownstreamChannelTable begin
          
    hwDocsIfDownstreamChannelTable OBJECT-TYPE
        SYNTAX      SEQUENCE OF HwDocsIfDownstreamChannelEntry
        MAX-ACCESS  not-accessible
        STATUS      current
        DESCRIPTION
            "This table describes the attributes of downstream
             channels (frequency bands).
             The index of this table is ifIndex."
        REFERENCE
            "Data-Over-Cable Service Interface Specifications: Radio
             Frequency Interface Specification SP-RFIv2.0-I10-051209,
             Tables 6-16, and 6-17. "
          ::= { hwCmtsAccessObject 28 }

   hwDocsIfDownstreamChannelEntry OBJECT-TYPE
        SYNTAX      HwDocsIfDownstreamChannelEntry
        MAX-ACCESS  not-accessible
        STATUS      current
        DESCRIPTION
            "This table describes the attributes of downstream
             channels (frequency bands).
             The index of this entry is ifIndex."
        INDEX { ifIndex }
        ::= { hwDocsIfDownstreamChannelTable 1 }

   HwDocsIfDownstreamChannelEntry ::= SEQUENCE {
            hwDocsIfDownChannelModulation       INTEGER,
            hwDocsIfDownstreamChannelMode       INTEGER,
            hwDocsIfDownstreamChannelSymbolRate INTEGER,
            hwDocsIfDownstreamChannelAnnex      INTEGER
        }
        
   hwDocsIfDownChannelModulation OBJECT-TYPE
        SYNTAX      INTEGER {
            unknown(1),
            other(2),
            qam64(3),
            qam256(4),
            qam1024(5)
        }
        MAX-ACCESS  read-write
        STATUS      current
        DESCRIPTION
            "The modulation type associated with this downstream
             channel.  If the interface is down, this object either
             returns the configured value (CMTS), the most current
             value (CM), or the value of unknown(1).  See the
             associated conformance object for write conditions and
             limitations.  See the reference for specifics on the
             modulation profiles implied by qam64 qam256 and qam1024.
             Default value: qam256(4)
             Options:
             1. unknown(1) - unknown
             2. other(2)   - Indicates the other modulation type
             3. qam64(3)   - QAM64
             4. qam256(4)  - QAM256
             5. qam1024(5) - QAM1024"
        REFERENCE
            "Data-Over-Cable Service Interface Specifications: Radio
             Frequency Interface Specification SP-RFIv2.0-I10-051209,
             Table 6-17."
        DEFVAL       { qam256 }
        ::= { hwDocsIfDownstreamChannelEntry 1 }
        
   hwDocsIfDownstreamChannelMode OBJECT-TYPE
        SYNTAX      INTEGER {
            docsis(1),
            eqam(2)
        }
        MAX-ACCESS  read-write
        STATUS      current
        DESCRIPTION
            "The downstream channel mode
             Options:
             1. docsis(1)  - Data-Over-Cable service interface specifications
             2. eqam(2)    - Edge Quadrature Amplitude Modulation"
        DEFVAL       { docsis }
        ::= { hwDocsIfDownstreamChannelEntry 2 }        
   
   hwDocsIfDownstreamChannelSymbolRate OBJECT-TYPE
        SYNTAX      INTEGER {
            symbolRate6875(1),
            symbolRate6900(2),
            symbolRate6952(3)
        }
        UNITS       "Msym/s"
        MAX-ACCESS  read-write
        STATUS      current
        DESCRIPTION
            "Indicates the symbol rate of a CMTS downstream channel, 
             The channel symbol rate takes effect only for the EQAM channel mode complying with AnnexA.
             The symbol rate value must be 6.952 when the modulation value is 1024 QAM
             Options:
             1. symbolRate6875(1)  - the downstream channel symbol rate is 6.875
             2. symbolRate6900(2)  - the downstream channel symbol rate is 6.900
             2. symbolRate6952(3)  - the downstream channel symbol rate is 6.952"
        DEFVAL       { symbolRate6952 }
        ::= { hwDocsIfDownstreamChannelEntry 3 }   
        
   hwDocsIfDownstreamChannelAnnex OBJECT-TYPE
     SYNTAX      INTEGER {
         unknown(1),
         other(2),
         annexA(3),
         annexB(4),
         annexC(5),
         default(6)
        }
     MAX-ACCESS  read-write
     STATUS      current
     DESCRIPTION
         "This attribute defines the ITU-J-83 Annex being used 
          for this MAC Domain.  The value of this attribute 
          indicates the conformance of the implementation to 
          important regional cable standards.  
          Options:
          1. unknown(1)   - Unknown
          2. other(2)     - Other
          3. annexA(3)    - Annex A from ITU-J83 is used
          4. annexB(4)    - Annex B from ITU-J83 is used
          5. annexC(5)    - Annex C from ITU-J83 is used
          6. default(6)   - The attribute is default, the annex mode configured on port takes effect"
      DEFVAL { default }
        ::= { hwDocsIfDownstreamChannelEntry 4} 
   -- Table hwDocsIfDownstreamChannelTable end
        
   -- Table hwDocsIf3MdCfgTable begin
   
    hwDocsIf3MdCfgTable OBJECT-TYPE
        SYNTAX      SEQUENCE OF HwDocsIf3MdCfgEntry
        MAX-ACCESS  not-accessible
        STATUS      current
        DESCRIPTION
            "This table describes the attributes of RF port.
             The index of this table is ifIndex."
          ::= { hwCmtsAccessObject 29 }

   hwDocsIf3MdCfgEntry OBJECT-TYPE
        SYNTAX      HwDocsIf3MdCfgEntry
        MAX-ACCESS  not-accessible
        STATUS      current
        DESCRIPTION
            "This table describes the attributes of RF port.
             The index of this entry is ifIndex."
        INDEX { ifIndex }
        ::= { hwDocsIf3MdCfgTable 1 }

   HwDocsIf3MdCfgEntry ::= SEQUENCE {
            hwdocsIf3MdCfgUsPreEqEnable       INTEGER,
            hwDocsIf3MdCfgUsSgMode            INTEGER,
            hwdocsIf3MdCfgMapLeadTime         Integer32,
            hwdocsIf3MdCfgMinMapTime          Integer32,
            hwDocsIf3MdCfgOperation           INTEGER,
            hwDocsIf3SidClusterNumber         Unsigned32,
            hwDocsIf3SidClusterMaxRequest     Unsigned32,
            hwDocsIf3SidClusterMaxTime        Unsigned32,
            hwDocsIf3SidClusterMaxTotalByte   Unsigned32,
            hwDocsIf3SidClusterMaxOutstandingByte   Unsigned32,
            hwDocsIf3PeriodicRngInterval      Unsigned32     
        }
        
   hwdocsIf3MdCfgUsPreEqEnable OBJECT-TYPE
        SYNTAX      INTEGER {
                             true(1),
                             false(2)
                            }
        MAX-ACCESS  read-write
        STATUS      current
        DESCRIPTION
                "This object is used to enable or disable pre-equalization
                on the upstream channel represented by this table instance.
                Options:
                1. true(1) - enable the pre-equalization
                2. false(2) - disable the pre-equalization
                Default value: true(1)
                "
        ::= { hwDocsIf3MdCfgEntry 1 }
        
    hwDocsIf3MdCfgUsSgMode OBJECT-TYPE
        SYNTAX      INTEGER {
                             single(1),
                             multiple(2)
                            }
        MAX-ACCESS  read-write
        STATUS      current
        DESCRIPTION
                "This object is used to configure the service group work mode of upstream channels on a cable port.
                 Options:
                   1. single(1)   - set MAC domain upstream channels to work in single service group mode.
                   2. multiple(2) - set MAC domain upstream channels to work in multiple service group mode.
                 Default value: single(1)
                "
        ::= { hwDocsIf3MdCfgEntry 2 }
        
    hwdocsIf3MdCfgMapLeadTime OBJECT-TYPE
        SYNTAX      Integer32 (-1000..2000)
        UNITS   "us"
        MAX-ACCESS  read-write
        STATUS      current
        DESCRIPTION
                "This object is used to configure the lead time for map messages on a cable port.
                 Note: a smaller parameter value may cause some CMs to drop packets or go offline.
                 Default value: 0, 0 indicates that the lead time for map messages remains unchanged. 
                 A positive number indicates to add the number to the lead time, and a negative number 
                 indicates to delete the number from the lead time.
                "
        ::= { hwDocsIf3MdCfgEntry 3 }
        
    hwdocsIf3MdCfgMinMapTime OBJECT-TYPE
        SYNTAX      Integer32 (1000..5000)
        UNITS   "us"
        MAX-ACCESS  read-write
        STATUS      current
        DESCRIPTION
                "This object is used to configure the minimum interval time for map messages on a cable port.
                 Note: a smaller parameter value may cause some CMs to drop packets or go offline.
                 Default value: 2500.
                "
        ::= { hwDocsIf3MdCfgEntry 4 }
                                
    hwDocsIf3MdCfgOperation OBJECT-TYPE
        SYNTAX      INTEGER {
                             clearCablePortStat(1),
                             clearAllCmStat(2),
                             clearAllUsChanStat(3),
                             clearAllDsChanStat(4),    
                             clearAllCmConnectivity(5),
                             clearAllUsChanPerfStat(6),
                             clearAllCmPerfStat(7),  
                             clearAllEqamChanStat(8), 
                             invalidValue(-1)
                           }
        MAX-ACCESS  read-write
        STATUS      current
        DESCRIPTION
                "This object is used to clear the statistics of a cable port or a CM.
                 Options: 
                   1.clearCablePortStat(1)       - clears the cable port statistics.
                   2.clearAllCmStat(2)           - clears the statistics of all the CMs under the cable port,
                                                   which is not supported currently.
                   3.clearAllUsChanStat(3)       - clears the statistics of all the upstream channels on the cable port, 
                                                   including the maximum and minimum values of the upstream channel SNR.
                   4.clearAllDsChanStat(4)       - clears the statistics of all the downstream channels on the cable port.
                   5.clearAllCmConnectivity(5)   - clears the connection statistics of all CMs under the cable port.
                   6.clearAllUsChanPerfStat(6)   - clears the statistics of all the upstream channels on the cable port.  
                   7.clearAllCmPerfStat(7)       - clears the performance statistics of all CMs under the cable port,
                                                   which is not supported currently.
                   8.clearAllQamChanStat(8)      - clears the performance statistics of all EQAM channels on the cable port.
                   9.invalidValue(-1)            - Invalid value."
        ::= { hwDocsIf3MdCfgEntry 5 }  
        
     hwDocsIf3SidClusterNumber OBJECT-TYPE
        SYNTAX      Unsigned32 (1..2)
        MAX-ACCESS  read-write
        STATUS      current
        DESCRIPTION
                "This object is used to configure the number of SID cluster. 
                The configuration takes effect after the CM goes online again.
                Default: 1
                "
        ::= { hwDocsIf3MdCfgEntry 6 }

    hwDocsIf3SidClusterMaxRequest OBJECT-TYPE
        SYNTAX      Unsigned32 (0..255)
        MAX-ACCESS  read-write
        STATUS      current
        DESCRIPTION
                "This object is used to configure the maximum number of requests that can be sent by the CM using the SID cluster. 
                0 indicates no limit.
                The configuration takes effect after the CM goes online again.
                Default: 128
                "
        ::= { hwDocsIf3MdCfgEntry 7 }

    hwDocsIf3SidClusterMaxTime OBJECT-TYPE
        SYNTAX      Unsigned32 (0..65535)
        UNITS       "ms"
        MAX-ACCESS  read-write
        STATUS      current
        DESCRIPTION
                "This object is used to configure the maximum time during which requests are sent by the CM using the SID cluster. 
                The time starts from the time at which the first request is sent by the CM using the SID cluster and ends at the time at which the last request is sent. 
                0 indicates no limit.
                The configuration takes effect after the CM goes online again. 
                Default: 5000
                "
        ::= { hwDocsIf3MdCfgEntry 8 }

    hwDocsIf3SidClusterMaxTotalByte OBJECT-TYPE
        SYNTAX      Unsigned32 (0..4294967295)
        UNITS       "bytes"
        MAX-ACCESS  read-write
        STATUS      current
        DESCRIPTION
                "This object is used to configure the maximum number of bytes that can be requested through the CM using the SID cluster, including the number of request bytes 
                that have been sent by the CM, and the total number of bytes with bandwidth unassigned and bytes with bandwidth assigned. 
                0 indicates no limit.
                The configuration takes effect after the CM goes online again. 
                Default: 500000
                "
        ::= { hwDocsIf3MdCfgEntry 9 }

    hwDocsIf3SidClusterMaxOutstandingByte OBJECT-TYPE
        SYNTAX      Unsigned32 (0..4294967295)
        UNITS       "bytes"
        MAX-ACCESS  read-write
        STATUS      current
        DESCRIPTION
                "This object is used to configure the maximum number of bytes that can continue to be requested through the CM using the SID cluster.
                0 indicates no limit.
                The configuration takes effect after the CM goes online again. 
                Default: 1000000
                "
        ::= { hwDocsIf3MdCfgEntry 10 } 

    hwDocsIf3PeriodicRngInterval OBJECT-TYPE
        SYNTAX      Unsigned32 (15000..25000)
        UNITS       "ms"
        MAX-ACCESS  read-write
        STATUS      current
        DESCRIPTION
                "This object is used to set the interval at which the periodic ranging grant is assigned for an online CM.
                Every online CM initiates a ranging request after receiving the periodic ranging grant.
                Default: 15000
                "
        ::= { hwDocsIf3MdCfgEntry 11 } 
   -- Table hwDocsIf3MdCfgTable end

   -- Table hwCmtsUsFftDataTable start
    hwCmtsUsFftDataTable OBJECT-TYPE
          SYNTAX     SEQUENCE OF HwCmtsUsFftDataEntry
          MAX-ACCESS not-accessible
          STATUS     current
          DESCRIPTION
               "Indicates the upstream channel FFT data.
               The indexes of this table are ifIndex and hwCmtsUsFftDataId.
               "
          ::= { hwCmtsAccessObject 30 }

    hwCmtsUsFftDataEntry OBJECT-TYPE
          SYNTAX     HwCmtsUsFftDataEntry
          MAX-ACCESS not-accessible
          STATUS     current
          DESCRIPTION
               "Indicates the upstream channel FFT data.
               The indexes of this entry are ifIndex and hwCmtsUsFftDataId.
               "
          INDEX       { ifIndex, hwCmtsUsFftDataId }
          ::= { hwCmtsUsFftDataTable 1 }

    HwCmtsUsFftDataEntry ::=
          SEQUENCE {
                    hwCmtsUsFftDataId       Integer32,
                    hwCmtsUsFftDataNum      Integer32,
                    hwCmtsUsFftDataContent  OCTET STRING
                   }

    hwCmtsUsFftDataId OBJECT-TYPE
          SYNTAX  Integer32 (0..7)
          MAX-ACCESS  not-accessible
          STATUS  current
          DESCRIPTION
                "Indicates the FFT data identity."
          ::= { hwCmtsUsFftDataEntry 1 }

    hwCmtsUsFftDataNum OBJECT-TYPE
          SYNTAX      Integer32
          MAX-ACCESS  read-only
          STATUS  current
          DESCRIPTION
                "Indicates the number of FFT data objects."
          ::= { hwCmtsUsFftDataEntry 2 }

    hwCmtsUsFftDataContent OBJECT-TYPE
          SYNTAX      OCTET STRING(SIZE (0..4096))
          MAX-ACCESS  read-only
          STATUS  current
          DESCRIPTION
                "Indicates the FFT data contents.
                The data content consists of frequency (four bytes in the unit of Hz) and magnitude (four bytes in the unit of 0.01 dBmV)."
          ::= { hwCmtsUsFftDataEntry 3 }
          
   -- Table hwCmtsUsFftDataTable end 
   
   -- Table hwCmtsRemoteQueryControlTable begin
    hwCmtsRemoteQueryControlTable OBJECT IDENTIFIER ::= { hwCmtsAccessObject 31 }

    hwCmtsRemoteQueryControlPort OBJECT-TYPE
          SYNTAX  Integer32
          MAX-ACCESS  read-write
          STATUS  current
          DESCRIPTION
                "Indicates the fixed port to remote query, the value is ifindex,
                 -1 indicates to query all frames.
                "
          ::= { hwCmtsRemoteQueryControlTable 1 }

    hwCmtsRemoteQueryControlTimeLength OBJECT-TYPE
          SYNTAX  Integer32 (-1..1440)
          UNITS   "minute"
          MAX-ACCESS  read-write
          STATUS  current
          DESCRIPTION
                "Indicates the auto stop time for query fixed port, 0 means not to stop automatically.
                If hwCmtsRemoteQueryControlPort is -1, this parameter is invalid.
                Default: 30
                "
          ::= { hwCmtsRemoteQueryControlTable 2 }
          
    hwCmtsRemoteQueryControlRemainedTimeLength OBJECT-TYPE
          SYNTAX  Integer32 (-1..86400)
          UNITS   "second"
          MAX-ACCESS  read-only
          STATUS  current
          DESCRIPTION
                "Indicates the remained time from now to the auto stop time. 
                If hwCmtsRemoteQueryControlPort is -1, or if the hwCmtsRemoteQueryControlTimeLength is 0, this parameter is invalid.
                "
          ::= { hwCmtsRemoteQueryControlTable 3 }
          
  -- Table hwCmtsRemoteQueryControlTable end
  
   -- Table hwDocsIfCmtsIPv6ToCmTable begin
    hwDocsIfCmtsIPv6ToCmTable OBJECT-TYPE
          SYNTAX     SEQUENCE OF HwDocsIfCmtsIPv6ToCmEntry
          MAX-ACCESS not-accessible
          STATUS     current
          DESCRIPTION
                "
                Indicates the CM index queried by the IPv6 address of a CM.
                The index of this table is hwDocsIfCmtsIPv6CmIPAddr.
                "
          ::= { hwCmtsAccessObject 32 }

    hwDocsIfCmtsIPv6ToCmEntry OBJECT-TYPE
          SYNTAX     HwDocsIfCmtsIPv6ToCmEntry
          MAX-ACCESS not-accessible
          STATUS     current
          DESCRIPTION
                "
                Indicates the CM index queried by the IPv6 address of a CM.
                The index of this entry is hwDocsIfCmtsIPv6CmIPAddr.
                 "
          INDEX       { hwDocsIfCmtsIPv6CmIPAddr }
          ::= { hwDocsIfCmtsIPv6ToCmTable 1 }

    HwDocsIfCmtsIPv6ToCmEntry ::=
          SEQUENCE {
                    hwDocsIfCmtsIPv6CmIPAddr       InetAddressIPv6,
                    hwDocsIfCmtsIPv6CmPtr          Integer32
                   }

    hwDocsIfCmtsIPv6CmIPAddr OBJECT-TYPE
          SYNTAX  InetAddressIPv6
          MAX-ACCESS   not-accessible
          STATUS  current
          DESCRIPTION
                "
                Indicates the IPv6 address of the CM.
                "
          ::= { hwDocsIfCmtsIPv6ToCmEntry 1 }

    hwDocsIfCmtsIPv6CmPtr OBJECT-TYPE
          SYNTAX  Integer32
          MAX-ACCESS   read-only
          STATUS  current
          DESCRIPTION
                "
                Indicates the CM index.
                "
          ::= { hwDocsIfCmtsIPv6ToCmEntry 2 }
          
   -- Table hwDocsIfCmtsIPv6ToCmTable end     
   
   -- Table hwCmtsAdmissionCtrBandwidthReservationTable begin
   
    hwCmtsAdmissionCtrBandwidthReservationTable OBJECT-TYPE
          SYNTAX     SEQUENCE OF HwCmtsAdmissionCtrBandwidthReservationEntry
          MAX-ACCESS not-accessible
          STATUS     current
          DESCRIPTION
               "This table describes the information of current reservation bandwidth.
                The index of this table is docsIf3CmtsCmRegStatusId.
               "
          ::= { hwCmtsAccessObject 33 }

    hwCmtsAdmissionCtrBandwidthReservationEntry OBJECT-TYPE
          SYNTAX     HwCmtsAdmissionCtrBandwidthReservationEntry
          MAX-ACCESS not-accessible
          STATUS     current
          DESCRIPTION
               "This table describes the information of current reservation bandwidth.
                The index of this entry is docsIf3CmtsCmRegStatusId.
               "
          INDEX       { docsIf3CmtsCmRegStatusId}
          ::= { hwCmtsAdmissionCtrBandwidthReservationTable 1 }

    HwCmtsAdmissionCtrBandwidthReservationEntry ::=
          SEQUENCE {
                    hwCmtsAdmissionCtrSFIDList                  OCTET STRING,
                    hwCmtsAdmissionCtrServiceFlowTypeList       OCTET STRING,
                    hwCmtsAdmissionCtrrBandwidthReservList      OCTET STRING
                   }

    hwCmtsAdmissionCtrSFIDList OBJECT-TYPE
          SYNTAX  OCTET STRING(SIZE (0..64))
          MAX-ACCESS  read-only
          STATUS  current
          DESCRIPTION
                "This object indicates the list of the service flow ID.
                 It can contain as most as 16 service flow IDs.
                 Every 4 octets represent a service flow ID."
          ::= { hwCmtsAdmissionCtrBandwidthReservationEntry 1 }

    hwCmtsAdmissionCtrServiceFlowTypeList OBJECT-TYPE
          SYNTAX  OCTET STRING(SIZE (0..16))
          MAX-ACCESS  read-only
          STATUS  current
          DESCRIPTION
                "This object indicates the list of the service flow type.
                It can contain as most as 16 service flow types.
                Each octet represents a service flow type."
          ::= { hwCmtsAdmissionCtrBandwidthReservationEntry 2 }

    hwCmtsAdmissionCtrrBandwidthReservList OBJECT-TYPE
          SYNTAX  OCTET STRING(SIZE (0..64))
          UNITS   "bps"
          MAX-ACCESS  read-only
          STATUS  current
          DESCRIPTION
                "This object indicates the list of current reservation bandwidth.
                It can contain as most as 16 reservation bandwidthes.
                Every 4 octets represent a reservation bandwidth."
          ::= { hwCmtsAdmissionCtrBandwidthReservationEntry 3 }
                          
    -- Table hwCmtsAdmissionCtrBandwidthReservationTable end        
  
  -- Table hwCmtsCapabilityConfigTable
    hwCmtsCapabilityConfigTable OBJECT-TYPE
          SYNTAX     SEQUENCE OF HwCmtsCapabilityConfigEntry
          MAX-ACCESS not-accessible
          STATUS     current
          DESCRIPTION
               "Indicates the configuration of cable capability on one cable port.
               The index of this table is ifIndex."
          ::= { hwCmtsAccessObject 34 }

    hwCmtsCapabilityConfigEntry OBJECT-TYPE
          SYNTAX     HwCmtsCapabilityConfigEntry
          MAX-ACCESS not-accessible
          STATUS     current
          DESCRIPTION
               "Indicates the configuration of cable capability on one cable port.
                The index of this entry is ifIndex."
          INDEX       { ifIndex }
          ::= { hwCmtsCapabilityConfigTable 1 }

    HwCmtsCapabilityConfigEntry ::=
          SEQUENCE {
                    hwCmtsCapabilityUpstreamChannelNum       Unsigned32,
                    hwCmtsCapabilityDownstreamChannelNum     Unsigned32,
                    hwCmtsCapabilityEqamChannelNum           Unsigned32
                   }
                   
    hwCmtsCapabilityUpstreamChannelNum OBJECT-TYPE
          SYNTAX  Unsigned32 (2..16)
          MAX-ACCESS  read-write
          STATUS  current
          DESCRIPTION
                "
                Indicates the configuration of upstream channel number of a cable port.
                "
          ::= { hwCmtsCapabilityConfigEntry 1 }
          
    hwCmtsCapabilityDownstreamChannelNum OBJECT-TYPE
          SYNTAX  Unsigned32 (16..32)
          MAX-ACCESS  read-write
          STATUS  current
          DESCRIPTION
                "
                Indicates the configuration of downstream channel number of a cable port.
                "
          ::= { hwCmtsCapabilityConfigEntry 2 }

    hwCmtsCapabilityEqamChannelNum OBJECT-TYPE
          SYNTAX  Unsigned32 (0..254)
          MAX-ACCESS  read-write
          STATUS  current
          DESCRIPTION
                "Indicates the configuration of EQAM channel number of a cable port."
          ::= { hwCmtsCapabilityConfigEntry 3 }

    -- Table hwCmtsCapabilityConfigTable end

    -- Table hwCmtsCapabilityStatusTable
    hwCmtsCapabilityStatusTable OBJECT-TYPE
          SYNTAX     SEQUENCE OF HwCmtsCapabilityStatusEntry
          MAX-ACCESS not-accessible
          STATUS     current
          DESCRIPTION
               "Indicates the status of cable capability on one cable port.
               The index of this table is ifIndex."
          ::= { hwCmtsAccessObject 35 }

    hwCmtsCapabilityStatusEntry OBJECT-TYPE
          SYNTAX     HwCmtsCapabilityStatusEntry
          MAX-ACCESS not-accessible
          STATUS     current
          DESCRIPTION
               "Indicates the status of cable capability on one cable port.
                The index of this entry is ifIndex."
          INDEX       { ifIndex }
          ::= { hwCmtsCapabilityStatusTable 1 }

    HwCmtsCapabilityStatusEntry ::=
          SEQUENCE {
                    hwCmtsCapabilityRealUpstreamChannelNum           Unsigned32,
                    hwCmtsCapabilityRealDownstreamChannelNum         Unsigned32,
                    hwCmtsCapabilityRealUpstreamMaxFrequency         Unsigned32,
                    hwCmtsCapabilityRealDownstreamMaxFrequency       Unsigned32,
                    hwCmtsCapabilityRealDownstreamMaxFrequencySpan   Unsigned32,
                    hwCmtsCapabilityScdma                            INTEGER,
                    hwCmtsCapabilityRealDownstreamMaxFrequencyGroupNum          Unsigned32,
                    hwCmtsCapabilityRealDownstreamFrequencyGroupCenterDivisor   Unsigned32,
                    hwCmtsCapabilityRealMdUsSgNum                    Unsigned32,
                    hwCmtsCapabilityRealRfIpReturnSupport            INTEGER,
                    hwCmtsCapabilityRealEqamDownstreamChannelNum   Unsigned32,
                    hwCmtsCapabilityUpstreamCenterFreqSpan65MHz       INTEGER,
                    hwCmtsCapabilityChannelAnnex                      INTEGER,
                    hwCmtsCapabilityPNMSpecturmMaxFrequency           INTEGER,
                    hwCmtsCapabilityPNMSpecturmResolution             INTEGER,
                    hwCmtsCapabilityPNMSpecturm                INTEGER,
                    hwCmtsCapabilityRealD31UpstreamMaxFrequency       Unsigned32,
                    hwCmtsCapabilityRealD31DownstreamMaxFrequency     Unsigned32
                   }
                   
    hwCmtsCapabilityRealUpstreamChannelNum OBJECT-TYPE
          SYNTAX  Unsigned32
          MAX-ACCESS  read-only
          STATUS  current
          DESCRIPTION
                "
                Indicates the real upstream channel number of a cable port.
                4294967295(0xFFFFFFFF) represents invalid value.
                "
          ::= { hwCmtsCapabilityStatusEntry 1 }
          
    hwCmtsCapabilityRealDownstreamChannelNum OBJECT-TYPE
          SYNTAX  Unsigned32
          MAX-ACCESS  read-only
          STATUS  current
          DESCRIPTION
                "
                Indicates the real downstream channel number of a cable port.
                4294967295(0xFFFFFFFF) represents invalid value.
                "
          ::= { hwCmtsCapabilityStatusEntry 2 }
          
    hwCmtsCapabilityRealUpstreamMaxFrequency OBJECT-TYPE
          SYNTAX  Unsigned32
          MAX-ACCESS  read-only
          STATUS  current
          DESCRIPTION
                "
                Indicates the maximum frequency of D3.0 upstream channel of a cable port.
                4294967295(0xFFFFFFFF) represents invalid value.
                "
          ::= { hwCmtsCapabilityStatusEntry 3 }
          
    hwCmtsCapabilityRealDownstreamMaxFrequency OBJECT-TYPE
          SYNTAX  Unsigned32
          MAX-ACCESS  read-only
          STATUS  current
          DESCRIPTION
                "
                Indicates the maximum frequency of D3.0 downstream channel of a cable port.
                4294967295(0xFFFFFFFF) represents invalid value.
                "
          ::= { hwCmtsCapabilityStatusEntry 4 }
          
    hwCmtsCapabilityRealDownstreamMaxFrequencySpan OBJECT-TYPE
          SYNTAX  Unsigned32
          MAX-ACCESS  read-only
          STATUS  current
          DESCRIPTION
                "
                Indicates the maximum frequency span of downstream channel of a cable port.
                4294967295(0xFFFFFFFF) represents invalid value.
                "
          ::= { hwCmtsCapabilityStatusEntry 5 }

    hwCmtsCapabilityScdma OBJECT-TYPE
          SYNTAX INTEGER
          {
              notSupport(1),
              support(2),
              invalidValue(-1)
          }
          MAX-ACCESS  read-only
          STATUS  current
          DESCRIPTION
               "
               Support scdma channel type capability.
               Options:
               1. notSupport(1)     - not support
               2. support(2)        - support
               3. invalidValue(-1)  - Invalid value
               "
          ::= { hwCmtsCapabilityStatusEntry 6 }

    hwCmtsCapabilityRealDownstreamMaxFrequencyGroupNum OBJECT-TYPE
          SYNTAX  Unsigned32
          MAX-ACCESS  read-only
          STATUS  current
          DESCRIPTION
                "
                Indicates the maximum frequency group number of downstream channel of a cable port.
                4294967295(0xFFFFFFFF) represents invalid value.
                "
          ::= { hwCmtsCapabilityStatusEntry 7 }
          
    hwCmtsCapabilityRealDownstreamFrequencyGroupCenterDivisor OBJECT-TYPE
          SYNTAX  Unsigned32
          UNITS   "Hz"
          MAX-ACCESS  read-only
          STATUS  current
          DESCRIPTION
                "
                Indicates the center frequency divisor of downstream channel of a cable port.
                4294967295(0xFFFFFFFF) represents invalid value.
                "
          ::= { hwCmtsCapabilityStatusEntry 8 }   
          
    hwCmtsCapabilityRealMdUsSgNum OBJECT-TYPE
          SYNTAX  Unsigned32
          MAX-ACCESS  read-only
          STATUS  current
          DESCRIPTION
                "
                Indicates the number of MAC domain upstream service groups of a cable port.
                4294967295(0xFFFFFFFF) represents invalid value.
                "
          ::= { hwCmtsCapabilityStatusEntry 9 }
          
    hwCmtsCapabilityRealRfIpReturnSupport OBJECT-TYPE
          SYNTAX INTEGER
          {
              notSupport(1),
              support(2),
              invalidValue(-1)
          }
          MAX-ACCESS  read-only
          STATUS  current
          DESCRIPTION
               "
               Support ip return capability.
               Options:
               1. notSupport(1)     - not support
               2. support(2)        - support
               3. invalidValue(-1)  - Invalid value
               "
          ::= { hwCmtsCapabilityStatusEntry 10 }
          
    hwCmtsCapabilityRealEqamDownstreamChannelNum OBJECT-TYPE
          SYNTAX  Unsigned32
          MAX-ACCESS  read-only
          STATUS  current
          DESCRIPTION
                "
                Indicates the real EQAM downstream channel number of a cable port.
                4294967295(0xFFFFFFFF) represents invalid value.
                "
          ::= { hwCmtsCapabilityStatusEntry 11 }

        hwCmtsCapabilityUpstreamCenterFreqSpan65MHz OBJECT-TYPE
          SYNTAX INTEGER
          {
              notSupport(1),
              support(2),
              invalidValue(-1)
          }
          MAX-ACCESS  read-only
          STATUS  current
          DESCRIPTION
               "
               The upstream channel center frequency spans 65 MHz.
               Options:
               1. notSupport(1)     - not support
               2. support(2)        - support
               3. invalidValue(-1)  - Invalid value
               "
          ::= { hwCmtsCapabilityStatusEntry 12 }                  
                     
    hwCmtsCapabilityChannelAnnex OBJECT-TYPE
          SYNTAX INTEGER
          {   notSupport(1),
              support(2),
              invalidValue(-1)
          }
          MAX-ACCESS  read-only
          STATUS  current
          DESCRIPTION
               "Support channel Annex capability.
               Options:
               1. notSupport(1)     - not support
               2. support(2)        - support
               3. invalidValue(-1)  - Invalid value
               "
          ::= { hwCmtsCapabilityStatusEntry 13 }          
                     
    hwCmtsCapabilityPNMSpecturmMaxFrequency OBJECT-TYPE
          SYNTAX INTEGER
          {   hz102M(1),
              hz204M(2),
              invalidValue(-1)
          }
          MAX-ACCESS  read-only
          STATUS  current
          DESCRIPTION
               "PNM spectrum support max frequency.
               Options:
               1. hz102M(1)     - 102MHz
               2. hz204M(2)        - 204MHz
               3. invalidValue(-1)  - Invalid value
               "
          ::= { hwCmtsCapabilityStatusEntry 14 }   
                                      
    hwCmtsCapabilityPNMSpecturmResolution OBJECT-TYPE
          SYNTAX INTEGER
          {   hz50K(1),
              hz60K(2),
              invalidValue(-1)
          }
          MAX-ACCESS  read-only
          STATUS  current
          DESCRIPTION
               "PNM spectrum support resolution.
               Options:
               1. hz50K(1)     - 50KHz
               2. hz60K(2)        - 60KHz
               3. invalidValue(-1)  - Invalid value
               "
          ::= { hwCmtsCapabilityStatusEntry 15 }

    hwCmtsCapabilityPNMSpecturm OBJECT-TYPE
          SYNTAX INTEGER
          {   notSupport(1),
              support(2),
              invalidValue(-1)
          }
          MAX-ACCESS  read-only
          STATUS  current
          DESCRIPTION
               "Support PNM Specturm capability.
               Options:
               1. notSupport(1)     - not support
               2. support(2)        - support
               3. invalidValue(-1)  - Invalid value
               "
          ::= { hwCmtsCapabilityStatusEntry 16 }
          
   hwCmtsCapabilityRealD31UpstreamMaxFrequency OBJECT-TYPE
          SYNTAX  Unsigned32
          MAX-ACCESS  read-only
          STATUS  current
          DESCRIPTION
                "
                Indicates the D3.1 upstream upper band edge maximum frequency  of a cable port.
                4294967295(0xFFFFFFFF) represents invalid value.
                "
          ::= { hwCmtsCapabilityStatusEntry 17 }
          
    hwCmtsCapabilityRealD31DownstreamMaxFrequency OBJECT-TYPE
          SYNTAX  Unsigned32
          MAX-ACCESS  read-only
          STATUS  current
          DESCRIPTION
                "
                Indicates the D3.1 downstream upper band edge maximum frequency of a cable port.
                4294967295(0xFFFFFFFF) represents invalid value.
                "
          ::= { hwCmtsCapabilityStatusEntry 18 }
                    
    -- Table hwCmtsCapabilityStatusTable end 
    
    -- Table hwCmtsLoadBalanceExcludeCmTable begin
   
    hwCmtsLoadBalanceExcludeCmTable OBJECT-TYPE
          SYNTAX     SEQUENCE OF HwCmtsLoadBalanceExcludeCmEntry
          MAX-ACCESS not-accessible
          STATUS     current
          DESCRIPTION
               "Indicates the information of CM group excluded from load balancing.
                The indexes of this table are ifIndex and hwCmtsLoadBalanceExcludeCmGroupId.
               "
          ::= { hwCmtsAccessObject 36 }

    hwCmtsLoadBalanceExcludeCmEntry OBJECT-TYPE
          SYNTAX     HwCmtsLoadBalanceExcludeCmEntry
          MAX-ACCESS not-accessible
          STATUS     current
          DESCRIPTION
               "Indicates the information of CM group excluded from load balancing.
                The indexes of this entry are ifIndex and hwCmtsLoadBalanceExcludeCmGroupId.
               "
          INDEX       { ifIndex, hwCmtsLoadBalanceExcludeCmGroupId }
          ::= { hwCmtsLoadBalanceExcludeCmTable 1 }

    HwCmtsLoadBalanceExcludeCmEntry ::=
          SEQUENCE {
                    hwCmtsLoadBalanceExcludeCmGroupId           Unsigned32,
                    hwCmtsLoadBalanceExcludeCmMacAddr           MacAddress,
                    hwCmtsLoadBalanceExcludeCmMacAddrMask       MacAddress,
                    hwCmtsLoadBalanceExcludeCmRowStatus         RowStatus
                   }

    hwCmtsLoadBalanceExcludeCmGroupId OBJECT-TYPE
          SYNTAX  Unsigned32 (1..64)
          MAX-ACCESS  not-accessible
          STATUS  current
          DESCRIPTION
                "Indicates the CM group ID excluded from load balancing."
          ::= { hwCmtsLoadBalanceExcludeCmEntry 1 }

    hwCmtsLoadBalanceExcludeCmMacAddr OBJECT-TYPE
          SYNTAX  MacAddress
          MAX-ACCESS  read-write
          STATUS  current
          DESCRIPTION
                "Indicates the MAC address of the CM or CPE excluded from load balancing."  
                     
          DEFVAL { '000000000000'H }
          ::= { hwCmtsLoadBalanceExcludeCmEntry 2 }
          
    hwCmtsLoadBalanceExcludeCmMacAddrMask OBJECT-TYPE
          SYNTAX  MacAddress
          MAX-ACCESS  read-write
          STATUS  current
          DESCRIPTION
                "Indicates the MAC address mask of the CM or CPE excluded from load balancing.
                This attribute corresponds to a  bit mask acting as
        a wild card to associate a cable modem MAC addresses
        to a CM group ID excluded from load balancing. The cable modem 
        matching criteria is performed by bit-Anded
        the cable modem MAC address with the MacAddrMAsk
        attribute and being compared with the bit-ANDed
        of attributes MacdAddr and MacAddrMask.
        
        A cable modem MAC address look up is performed first with
        instances containing this attribute value not null,
        if several entries match, the largest consecutive
        bit match from MSB to LSB is used." 
               
        DEFVAL { 'FFFFFFFFFFFF'H }
          ::= { hwCmtsLoadBalanceExcludeCmEntry 3 }
          
    hwCmtsLoadBalanceExcludeCmRowStatus OBJECT-TYPE
          SYNTAX     RowStatus
          MAX-ACCESS read-create
          STATUS     current
          DESCRIPTION
                "Indicates the row status to create or 
                 delete a CM group excluded from load balancing."
          ::= { hwCmtsLoadBalanceExcludeCmEntry 4 }
                         
    -- Table hwCmtsLoadBalanceExcludeCmTable end 

    -- Table hwDocsIfRFOutTable begin
   
    hwDocsIfRFOutTable OBJECT-TYPE
          SYNTAX     SEQUENCE OF HwDocsIfRFOutEntry
          MAX-ACCESS not-accessible
          STATUS     current
          DESCRIPTION
               "This table describes the RF output branch status.
                The indexes of this table are hwFrameIndex and hwDocsIfRFOutId.
               "
          ::= { hwCmtsAccessObject 37 }

    hwDocsIfRFOutEntry OBJECT-TYPE
          SYNTAX     HwDocsIfRFOutEntry
          MAX-ACCESS not-accessible
          STATUS     current
          DESCRIPTION
               "This table describes the RF output branch status.
                The indexes of this entry are hwFrameIndex and hwDocsIfRFOutId.
               "
          INDEX       { hwFrameIndex, hwDocsIfRFOutId }
          ::= { hwDocsIfRFOutTable 1 }

    HwDocsIfRFOutEntry ::=
          SEQUENCE {
                    hwDocsIfRFOutId               Integer32,
                    hwDocsIfRFOutUsAdminStatus    INTEGER,
                    hwDocsIfRFOutUsOperStatus     INTEGER,
                    hwDocsIfRFOutCfgAttenuationValue INTEGER,
                    hwDocsIfRFOutOperAttenuationValue INTEGER
                   }

    hwDocsIfRFOutId OBJECT-TYPE
          SYNTAX  Integer32 (0..3)
          MAX-ACCESS  not-accessible
          STATUS  current
          DESCRIPTION
                "Indicates the RF output branch index."
          ::= { hwDocsIfRFOutEntry 1 }

    hwDocsIfRFOutUsAdminStatus OBJECT-TYPE
          SYNTAX  INTEGER {enable(1),disable(2),attenuation(3)}
          MAX-ACCESS  read-write
          STATUS  current
          DESCRIPTION
                "Indicates the upstream RF output branch admin status.
                Options:
                1. enable(1)      -Indicates the status is enable
                2. disable(2)     -Indicates the status is disable
                3. attenuation(3) -Indicates the status is attenuation(obsolete)
                "
          DEFVAL  { enable }
          ::= { hwDocsIfRFOutEntry 2 }

    hwDocsIfRFOutUsOperStatus OBJECT-TYPE
          SYNTAX  INTEGER {enable(1),disable(2),attenuation(3),invalidValue(-1)}
          MAX-ACCESS  read-only
          STATUS  current
          DESCRIPTION
               "Indicates the upstream RF output branch operating status.
                Options:
                1. enable(1)      -Indicates the status is enable
                2. disable(2)     -Indicates the status is disable
                3. attenuation(3) -Indicates the status is attenuation(obsolete)
                4. invalidValue(-1) -Invalid value
                "
          ::= { hwDocsIfRFOutEntry 3 }
          
    hwDocsIfRFOutCfgAttenuationValue OBJECT-TYPE 
          SYNTAX  INTEGER {decrement4db(1),decrement6db(2),decrement8db(3),decrement10db(4),invalidValue(-1)} 
          UNITS   "dB" 
          MAX-ACCESS  read-write 
          STATUS obsolete
          DESCRIPTION 
           "Indicates the upstream RF output attenuation power. 
               Options: 
               1. decrement4db(1)      -Indicates the attenuation value is 4db. 
               2. decrement6db(2)      -Indicates the attenuation value is 6db 
               3. decrement8db(3)      -Indicates the attenuation value is 8db 
               4. decrement10db(4)     -Indicates the attenuation value is 10db 
               5. invalidValue(-1)      -Invalid value 
               Default value: 2 
               " 
         ::= { hwDocsIfRFOutEntry 4 } 
                  
    hwDocsIfRFOutOperAttenuationValue OBJECT-TYPE 
         SYNTAX  INTEGER {decrement4db(1),decrement6db(2),decrement8db(3),decrement10db(4),invalidValue(-1)} 
         UNITS   "dB" 
         MAX-ACCESS  read-only 
         STATUS obsolete
         DESCRIPTION 
              "Indicates the upstream RF output operating attenuation power. 
               Options: 
               1. decrement4db(1)      -Indicates the attenuation value is 4db. 
               2. decrement6db(2)      -Indicates the attenuation value is 6db 
               3. decrement8db(3)      -Indicates the attenuation value is 8db 
               4. decrement10db(4)     -Indicates the attenuation value is 10db 
               5. invalidValue(-1)      -Invalid value 
               " 
         ::= { hwDocsIfRFOutEntry 5 }                          

                         
    -- Table hwDocsIfRFOutTable end 

    -- Table hwCmtsCmUsChannelCurrTable
    hwCmtsCmUsChannelCurrTable OBJECT-TYPE
          SYNTAX     SEQUENCE OF HwCmtsCmUsChannelCurrEntry
          MAX-ACCESS not-accessible
          STATUS     current
          DESCRIPTION
                "
                Indicates the current performance statistics of the upstream channel
                which the cable modem location.
                The indexes of this table are hwCmtsCmCurrId and hwCmtsCmUsChannelCurrId.
                "
          ::= { hwCmtsAccessObject 38 }

    hwCmtsCmUsChannelCurrEntry OBJECT-TYPE
          SYNTAX     HwCmtsCmUsChannelCurrEntry
          MAX-ACCESS not-accessible
          STATUS     current
          DESCRIPTION
                "
                Indicates the current performance statistics of the upstream channel
                which the cable modem location.
                The indexes of this entry are hwCmtsCmCurrId and hwCmtsCmUsChannelCurrId.
                "
          INDEX       { hwCmtsCmCurrId, hwCmtsCmUsChannelCurrId }
          ::= { hwCmtsCmUsChannelCurrTable 1 }

    HwCmtsCmUsChannelCurrEntry ::=
          SEQUENCE {
                    hwCmtsCmUsChannelCurrId                      Integer32,
                    hwCmtsCmUsChannelCurr15MStartTime            OCTET STRING,
                    hwCmtsCmUsChannelCurr15MElapsedTime          Integer32,
                    hwCmtsCmUsChannelCurr15MValidityFlag         Integer32,
                    hwCmtsCmUsChannelCurr15MSuccessPeriodRng     Counter32,
                    hwCmtsCmUsChannelCurr15MPeriodRngLoss        Counter32,
                    hwCmtsCmUsChannelCurr15MSeriousPeriodRngLoss Counter32,
                    hwCmtsCmUsChannelCurr15MPowerAdjust          Counter32,
                    hwCmtsCmUsChannelCurr15MSeriousPowerAdjust   Counter32,
                    hwCmtsCmUsChannelCurr1DayStartTime           OCTET STRING,
                    hwCmtsCmUsChannelCurr1DayElapsedTime         Integer32,
                    hwCmtsCmUsChannelCurr1DayValidityFlag        Integer32,
                    hwCmtsCmUsChannelCurr1DaySuccessPeriodRng            Counter32,
                    hwCmtsCmUsChannelCurr1DayPeriodRngLoss               Counter32,
                    hwCmtsCmUsChannelCurr1DaySeriousPeriodRngLoss        Counter32,
                    hwCmtsCmUsChannelCurr1DayPowerAdjust                 Counter32,
                    hwCmtsCmUsChannelCurr1DaySeriousPowerAdjust          Counter32,
                    hwCmtsCmUsChannelCurrEverBeforeStartTime             OCTET STRING,
                    hwCmtsCmUsChannelCurrEverBeforeElapsedTime           Integer32,
                    hwCmtsCmUsChannelCurrEverBeforeValidityFlag          Integer32,
                    hwCmtsCmUsChannelCurrEverBeforeSuccessPeriodRng      Counter32,
                    hwCmtsCmUsChannelCurrEverBeforePeriodRngLoss         Counter32,
                    hwCmtsCmUsChannelCurrEverBeforeSeriousPeriodRngLoss  Counter32,
                    hwCmtsCmUsChannelCurrEverBeforePowerAdjust           Counter32,
                    hwCmtsCmUsChannelCurrEverBeforeSeriousPowerAdjust    Counter32,
                    hwCmtsCmUsChannelCurrEverBeforeLastSeriousPeriodRngLossTime   DateAndTime,
                    hwCmtsCmUsChannelCurrEverBeforeFirstSeriousPeriodRngLossTime  DateAndTime,
                    hwCmtsCmUsChannelCurrEverBeforeLastSeriousPowerAdjustTime     DateAndTime,
                    hwCmtsCmUsChannelCurrEverBeforeFirstSeriousPowerAdjustTime    DateAndTime
                   }

    hwCmtsCmUsChannelCurrId OBJECT-TYPE
          SYNTAX  Integer32
          MAX-ACCESS   not-accessible
          STATUS  current
          DESCRIPTION
                "
                The upstream channel ID.
                "
          ::= { hwCmtsCmUsChannelCurrEntry 1 }

    hwCmtsCmUsChannelCurr15MStartTime OBJECT-TYPE
          SYNTAX  OCTET STRING
          MAX-ACCESS  read-only
          STATUS  current
          DESCRIPTION
                "
                Indicates the start time of the current 15-minute statistical period.
                "
          ::= { hwCmtsCmUsChannelCurrEntry 2 }


    hwCmtsCmUsChannelCurr15MElapsedTime OBJECT-TYPE
          SYNTAX  Integer32
          UNITS   "s"
          MAX-ACCESS  read-only
          STATUS  current
          DESCRIPTION
                "
                Indicates the elapsed time in the current 15-minute statistical period.
                -1 represents invalid value.
                "
          ::= { hwCmtsCmUsChannelCurrEntry 3 }

    hwCmtsCmUsChannelCurr15MValidityFlag OBJECT-TYPE
          SYNTAX  Integer32 (1..2)
          MAX-ACCESS  read-only
          STATUS  current
          DESCRIPTION
                "
                Indicates the flag for statistical information.
                Options:
                1-Yes
                2-No
                "
          ::= { hwCmtsCmUsChannelCurrEntry 4 }

    hwCmtsCmUsChannelCurr15MSuccessPeriodRng OBJECT-TYPE
          SYNTAX  Counter32
          MAX-ACCESS  read-only
          STATUS  current
          DESCRIPTION
                "
                Indicates the number of successful periodic ranging requests during the current 15-minute.
                4294967295 represents invalid value.
                "
          ::= { hwCmtsCmUsChannelCurrEntry 5 }

    hwCmtsCmUsChannelCurr15MPeriodRngLoss OBJECT-TYPE
          SYNTAX  Counter32
          MAX-ACCESS  read-only
          STATUS  current
          DESCRIPTION
                "
                Indicates the number of lost periodic ranging requests during the current 15-minute.
                4294967295 represents invalid value.
                "
          ::= { hwCmtsCmUsChannelCurrEntry 6 }

    hwCmtsCmUsChannelCurr15MSeriousPeriodRngLoss OBJECT-TYPE
          SYNTAX  Counter32
          MAX-ACCESS  read-only
          STATUS  current
          DESCRIPTION
                "
                Indicates the number of consecutive periodic ranging request failures during the current 15-minute.
                4294967295 represents invalid value.
                "
          ::= { hwCmtsCmUsChannelCurrEntry 7 }

    hwCmtsCmUsChannelCurr15MPowerAdjust OBJECT-TYPE
          SYNTAX  Counter32
          MAX-ACCESS  read-only
          STATUS  current
          DESCRIPTION
                "
                Indicates the number of transmit power adjustments during the current 15-minute.
                4294967295 represents invalid value.
                "
          ::= { hwCmtsCmUsChannelCurrEntry 8 }

    hwCmtsCmUsChannelCurr15MSeriousPowerAdjust OBJECT-TYPE
          SYNTAX  Counter32
          MAX-ACCESS  read-only
          STATUS  current
          DESCRIPTION
                "
                Indicates the number of severe transmit power adjustments during the current 15-minute.
                4294967295 represents invalid value.
                "
          ::= { hwCmtsCmUsChannelCurrEntry 9 }

    hwCmtsCmUsChannelCurr1DayStartTime OBJECT-TYPE
          SYNTAX  OCTET STRING
          MAX-ACCESS  read-only
          STATUS  current
          DESCRIPTION
                "
                Indicates the start time of the current 24-hour statistical period.
                "
          ::= { hwCmtsCmUsChannelCurrEntry 10 }


    hwCmtsCmUsChannelCurr1DayElapsedTime OBJECT-TYPE
          SYNTAX  Integer32
          UNITS   "s"
          MAX-ACCESS  read-only
          STATUS  current
          DESCRIPTION
                "
                Indicates the elapsed time in the current 24-hour statistical period.
                -1 represents invalid value.
                "
          ::= { hwCmtsCmUsChannelCurrEntry 11 }

    hwCmtsCmUsChannelCurr1DayValidityFlag OBJECT-TYPE
          SYNTAX  Integer32 (1..2)
          MAX-ACCESS  read-only
          STATUS  current
          DESCRIPTION
                "
                Indicates the flag for statistical information.
                Options:
                1-Yes
                2-No
                "
          ::= { hwCmtsCmUsChannelCurrEntry 12 }

    hwCmtsCmUsChannelCurr1DaySuccessPeriodRng OBJECT-TYPE
          SYNTAX  Counter32
          MAX-ACCESS  read-only
          STATUS  current
          DESCRIPTION
                "
                Indicates the number of successful periodic ranging requests during the current 24-hour.
                4294967295 represents invalid value.
                "
          ::= { hwCmtsCmUsChannelCurrEntry 13 }

    hwCmtsCmUsChannelCurr1DayPeriodRngLoss OBJECT-TYPE
          SYNTAX  Counter32
          MAX-ACCESS  read-only
          STATUS  current
          DESCRIPTION
                "
                Indicates the number of lost periodic ranging requests during the current 24-hour.
                4294967295 represents invalid value.
                "
          ::= { hwCmtsCmUsChannelCurrEntry 14 }

    hwCmtsCmUsChannelCurr1DaySeriousPeriodRngLoss OBJECT-TYPE
          SYNTAX  Counter32
          MAX-ACCESS  read-only
          STATUS  current
          DESCRIPTION
                "
                Indicates the number of consecutive periodic ranging request failures during the current 24-hour.
                4294967295 represents invalid value.
                "
          ::= { hwCmtsCmUsChannelCurrEntry 15 }

    hwCmtsCmUsChannelCurr1DayPowerAdjust OBJECT-TYPE
          SYNTAX  Counter32
          MAX-ACCESS  read-only
          STATUS  current
          DESCRIPTION
                "
                Indicates the number of transmit power adjustments during the current 24-hour.
                4294967295 represents invalid value.
                "
          ::= { hwCmtsCmUsChannelCurrEntry 16 }

    hwCmtsCmUsChannelCurr1DaySeriousPowerAdjust OBJECT-TYPE
          SYNTAX  Counter32
          MAX-ACCESS  read-only
          STATUS  current
          DESCRIPTION
                "
                Indicates the number of severe transmit power adjustments during the current 24-hour.
                4294967295 represents invalid value.
                "
          ::= { hwCmtsCmUsChannelCurrEntry 17 }

    hwCmtsCmUsChannelCurrEverBeforeStartTime OBJECT-TYPE
          SYNTAX  OCTET STRING
          MAX-ACCESS  read-only
          STATUS  current
          DESCRIPTION
                "
                Indicates the start time of the statistical period.
                "
          ::= { hwCmtsCmUsChannelCurrEntry 18 }


    hwCmtsCmUsChannelCurrEverBeforeElapsedTime OBJECT-TYPE
          SYNTAX  Integer32
          UNITS   "s"
          MAX-ACCESS  read-only
          STATUS  current
          DESCRIPTION
                "
                Indicates the elapsed time in the statistical period.
                -1 represents invalid value.
                "
          ::= { hwCmtsCmUsChannelCurrEntry 19 }

    hwCmtsCmUsChannelCurrEverBeforeValidityFlag OBJECT-TYPE
          SYNTAX  Integer32 (1..2)
          MAX-ACCESS  read-only
          STATUS  current
          DESCRIPTION
                "
                Indicates the flag for statistical information.
                Options:
                1-Yes
                2-No
                "
          ::= { hwCmtsCmUsChannelCurrEntry 20 }

    hwCmtsCmUsChannelCurrEverBeforeSuccessPeriodRng OBJECT-TYPE
          SYNTAX  Counter32
          MAX-ACCESS  read-only
          STATUS  current
          DESCRIPTION
                "
                Indicates the number of previous successful periodic ranging requests.
                4294967295 represents invalid value.
                "
          ::= { hwCmtsCmUsChannelCurrEntry 21 }

    hwCmtsCmUsChannelCurrEverBeforePeriodRngLoss OBJECT-TYPE
          SYNTAX  Counter32
          MAX-ACCESS  read-only
          STATUS  current
          DESCRIPTION
                "
                Indicates the number of previous loss of periodic ranging requests.
                4294967295 represents invalid value.
                "
          ::= { hwCmtsCmUsChannelCurrEntry 22 }

    hwCmtsCmUsChannelCurrEverBeforeSeriousPeriodRngLoss OBJECT-TYPE
          SYNTAX  Counter32
          MAX-ACCESS  read-only
          STATUS  current
          DESCRIPTION
                "
                Indicates the number of previous loss of the consecutive periodic ranging requests.
                4294967295 represents invalid value.
                "
          ::= { hwCmtsCmUsChannelCurrEntry 23 }

    hwCmtsCmUsChannelCurrEverBeforePowerAdjust OBJECT-TYPE
          SYNTAX  Counter32
          MAX-ACCESS  read-only
          STATUS  current
          DESCRIPTION
                "
                Indicates the number of previous transmit power adjustments.
                4294967295 represents invalid value.
                "
          ::= { hwCmtsCmUsChannelCurrEntry 24 }

    hwCmtsCmUsChannelCurrEverBeforeSeriousPowerAdjust OBJECT-TYPE
          SYNTAX  Counter32
          MAX-ACCESS  read-only
          STATUS  current
          DESCRIPTION
                " 
                Indicates the number of previous severe power adjustments.
                4294967295 represents invalid value.
                "
          ::= { hwCmtsCmUsChannelCurrEntry 25 }     
          
    hwCmtsCmUsChannelCurrEverBeforeLastSeriousPeriodRngLossTime OBJECT-TYPE
      SYNTAX  DateAndTime
      MAX-ACCESS  read-only
      STATUS  current
      DESCRIPTION
            " 
            Indicates the time of the latest loss of the severe periodic ranging request.
            "
      ::= { hwCmtsCmUsChannelCurrEntry 26 }
      
    hwCmtsCmUsChannelCurrEverBeforeFirstSeriousPeriodRngLossTime OBJECT-TYPE
      SYNTAX  DateAndTime
      MAX-ACCESS  read-only
      STATUS  current
      DESCRIPTION
            " 
             Indicates the time of the first loss of the severe periodic ranging request.
            "
      ::= { hwCmtsCmUsChannelCurrEntry 27 }
      
    hwCmtsCmUsChannelCurrEverBeforeLastSeriousPowerAdjustTime OBJECT-TYPE
     SYNTAX  DateAndTime
     MAX-ACCESS  read-only
     STATUS  current
     DESCRIPTION
           "
           Indicates the time of the latest severe power adjustment.
           "
     ::= { hwCmtsCmUsChannelCurrEntry 28 }
     
    hwCmtsCmUsChannelCurrEverBeforeFirstSeriousPowerAdjustTime OBJECT-TYPE
     SYNTAX  DateAndTime
     MAX-ACCESS  read-only
    STATUS  current
     DESCRIPTION
           " 
           Indicates the time of the first severe power adjustment.
           "
     ::= { hwCmtsCmUsChannelCurrEntry 29 }                  

    --Table hwCmtsCableModemVendorTable
    
    hwCmtsCableModemVendorTable OBJECT-TYPE
        SYNTAX     SEQUENCE OF HwCmtsCableModemVendorEntry
        MAX-ACCESS not-accessible
        STATUS     current
        DESCRIPTION
            "
            Indicates the mapping between the OUI and vendor name of a cable modem.
            The index of this table is hwCmtsCableModemOUI.
            "
        ::= { hwCmtsAccessObject 41 }
        
    hwCmtsCableModemVendorEntry OBJECT-TYPE
        SYNTAX     HwCmtsCableModemVendorEntry
        MAX-ACCESS not-accessible
        STATUS     current
        DESCRIPTION
           "
           Indicates the mapping between the OUI and vendor name of a cable modem.
           The index of this entry is hwCmtsCableModemOUI.
           "
       INDEX       { hwCmtsCableModemOUI }
       ::= { hwCmtsCableModemVendorTable 1 }

   HwCmtsCableModemVendorEntry ::=
       SEQUENCE {
           hwCmtsCableModemOUI     OCTET STRING,
           hwCmtsCableModemUserDefinedVendorName  OCTET STRING,
           hwCmtsCableModemVendorRowStatus RowStatus
       }
       
   hwCmtsCableModemOUI OBJECT-TYPE
       SYNTAX OCTET STRING (SIZE (3))
       MAX-ACCESS not-accessible 
       STATUS current
       DESCRIPTION
           "Indicates the OUI.
           "
       ::= { hwCmtsCableModemVendorEntry 1 } 
       
    hwCmtsCableModemUserDefinedVendorName OBJECT-TYPE                                               
       SYNTAX OCTET STRING(SIZE (1..16))
       MAX-ACCESS read-write
       STATUS current                                                          
       DESCRIPTION                                                             
           "Indicates the user-defined vendor name of an OUI.
           "                                                                   
       ::= { hwCmtsCableModemVendorEntry 2 }            
       
    hwCmtsCableModemVendorRowStatus OBJECT-TYPE
          SYNTAX RowStatus
          MAX-ACCESS read-create
          STATUS current
          DESCRIPTION
              "RowStatus.
               1. active(1)          -the status of the row is active
               2. createAndGo(4)     -the status of the row is createAndGo
               3. destroy(6)         -the status of the row is destroy
               Active(1) is state, the value may be read or written.
               CreateAndGo(4), and destroy(6) are actions, these values may be written, but are never read.
              "
       ::= { hwCmtsCableModemVendorEntry 3 }                                                                          
        
    --Table hwCmtsCableModemVendorTable end
    
    -- Table hwCmtsCableModemVendorStatisticTable
    hwCmtsCableModemVendorStatisticTable OBJECT-TYPE
          SYNTAX     SEQUENCE OF HwCmtsCableModemVendorStatisticEntry
          MAX-ACCESS not-accessible
          STATUS     current
          DESCRIPTION
               "Indicates the numbers of cable modem by one RF port and OUI list.
               The index of this table is ifIndex."
          ::= { hwCmtsAccessObject 42 }

    hwCmtsCableModemVendorStatisticEntry OBJECT-TYPE
          SYNTAX     HwCmtsCableModemVendorStatisticEntry
          MAX-ACCESS not-accessible
          STATUS     current
          DESCRIPTION
               "Indicates the numbers of cable modem by one RF port and OUI list.
                The index of this entry is ifIndex."
          INDEX       { ifIndex }
          ::= { hwCmtsCableModemVendorStatisticTable 1 }

    HwCmtsCableModemVendorStatisticEntry ::=
          SEQUENCE {
                    hwCmtsCableModemOUIList       OCTET STRING,
                    hwCmtsCableModemOnline        OCTET STRING,
                    hwCmtsCableModemOffline       OCTET STRING,
                    hwCmtsCableModemUnregistered  OCTET STRING
                   }

   hwCmtsCableModemOUIList OBJECT-TYPE
       SYNTAX OCTET STRING (SIZE (0..1536))
       MAX-ACCESS read-only 
       STATUS current
       DESCRIPTION
           "This node indicates the OUI list. The OUI list records the OUI of the CMs one by one.
            Each record takes 3 bytes. It can contain as most as 512 OUI.
           "
       ::= { hwCmtsCableModemVendorStatisticEntry 1 } 
       
    hwCmtsCableModemOnline OBJECT-TYPE
          SYNTAX     OCTET STRING  (SIZE (0..1024))
          MAX-ACCESS read-only
          STATUS     current
          DESCRIPTION
               "This node indicates the list of the number of CMs in status of online. The number 
                list records the numbers of the CMs in status of online one by one according to 
                the OUI list. Each record takes 2 bytes. It can contain as most as 512 numbers.
               "
          ::= { hwCmtsCableModemVendorStatisticEntry 2 }

    hwCmtsCableModemOffline OBJECT-TYPE
          SYNTAX     OCTET STRING  (SIZE (0..1024))
          MAX-ACCESS read-only
          STATUS     current
          DESCRIPTION
               "This node indicates the list of the number of CM in status of offline. The number 
                list records the number of the CMs in status of offline one by one according to 
                the OUI list. Each record takes 2 bytes. It can contain as most as 512 numbers.
               "
          ::= { hwCmtsCableModemVendorStatisticEntry 3 }

    hwCmtsCableModemUnregistered OBJECT-TYPE
          SYNTAX     OCTET STRING  (SIZE (0..1024))
          MAX-ACCESS read-only
          STATUS     current
          DESCRIPTION
               "This node indicates the list of the number of CM in status of unregistered. The number 
                list records the number of the CMs in status of unregistered one by one according to 
                the OUI list. Each record takes 2 bytes. It can contain as most as 512 numbers.
               "
          ::= { hwCmtsCableModemVendorStatisticEntry 4 }
            
    -- Table hwCmtsCableModemVendorStatisticTable end 
    
    --Table hwCmtsServiceTypeTable begin
        
    hwCmtsServiceTypeTable OBJECT-TYPE
        SYNTAX     SEQUENCE OF HwCmtsServiceTypeEntry
        MAX-ACCESS not-accessible
        STATUS     current
        DESCRIPTION
            "Indicates the mapping from service type identifier to downstream frequency.
             The index of this table is hwCmtsServiceTypeID.
            "
        ::= { hwCmtsAccessObject 43 }

    hwCmtsServiceTypeEntry OBJECT-TYPE
        SYNTAX     HwCmtsServiceTypeEntry
        MAX-ACCESS not-accessible
        STATUS     current
        DESCRIPTION
            "Indicates the mapping from service type identifier to downstream frequency.
             The index of this entry is hwCmtsServiceTypeID.
            "
        INDEX       { IMPLIED hwCmtsServiceTypeID }
        ::= { hwCmtsServiceTypeTable 1 }

    HwCmtsServiceTypeEntry ::=
        SEQUENCE {
                 hwCmtsServiceTypeID 
                 OCTET STRING,
                 hwCmtsServiceTypeDsFrequency 
                 Integer32,
                 hwCmtsServiceTypeRowStatus 
                 RowStatus
        }
        
    hwCmtsServiceTypeID OBJECT-TYPE
            SYNTAX OCTET STRING (SIZE (1..16))
            MAX-ACCESS not-accessible
            STATUS current
            DESCRIPTION
                "Indicates the service type identifier.                          
                "
         ::= { hwCmtsServiceTypeEntry 1 }
        
     hwCmtsServiceTypeDsFrequency OBJECT-TYPE
            SYNTAX Integer32 (10000..1002000000)
            UNITS   "Hz"
            MAX-ACCESS read-create
            STATUS current
            DESCRIPTION
                "The center frequency of the downstream channel.
                 Range: 10000-1002000000           
                "
         ::= { hwCmtsServiceTypeEntry 2 }    
       
    hwCmtsServiceTypeRowStatus OBJECT-TYPE
            SYNTAX RowStatus
            MAX-ACCESS read-create
            STATUS current
            DESCRIPTION
                "RowStatus.
                 1. active(1)      -indicates the query operation.
                 2. createAndGo(4) -indicates adding a mapping from service type identifier to downstream frequency.
                 3. destroy(6)     -indicates deleting a mapping from service type identifier to downstream frequency.
                 Default: active(1)
                "
         ::= { hwCmtsServiceTypeEntry 3 }
        
    --Table hwCmtsServiceTypeTable end    
    
    --Table hwDocsIf3CmtsCmThresholdTable begin
        
    hwDocsIf3CmtsCmThresholdTable OBJECT-TYPE
        SYNTAX     SEQUENCE OF HwDocsIf3CmtsCmThresholdEntry
        MAX-ACCESS not-accessible
        STATUS     current
        DESCRIPTION
            "Indicates the threshold for controlling the CM under CMTS.
             The index of this table is ifindex.
            "
        ::= { hwCmtsAccessObject 44 }

    hwDocsIf3CmtsCmThresholdEntry OBJECT-TYPE
        SYNTAX     HwDocsIf3CmtsCmThresholdEntry
        MAX-ACCESS not-accessible
        STATUS     current
        DESCRIPTION
            "Indicates the threshold for controlling the CM under CMTS.
             The index of this entry is ifindex.
            "
        INDEX       { ifIndex }
        ::= { hwDocsIf3CmtsCmThresholdTable 1 }

    HwDocsIf3CmtsCmThresholdEntry ::=
        SEQUENCE {
                   hwDocsIf3CmtsCmAccessNumUpperThreshold Integer32,
                   hwDocsIf3CmtsCmAccessNumLowerThreshold Integer32
                 }
        
    hwDocsIf3CmtsCmAccessNumUpperThreshold OBJECT-TYPE
            SYNTAX Integer32 (-1|1..1024)
            MAX-ACCESS read-write
            STATUS current
            DESCRIPTION
                "The upper threshold of CMs that can be connected.
                 -1 represents invalid value."
         ::= { hwDocsIf3CmtsCmThresholdEntry 1 }    
         
   hwDocsIf3CmtsCmAccessNumLowerThreshold OBJECT-TYPE
            SYNTAX Integer32 (-1|1..1024)
            MAX-ACCESS read-write
            STATUS current
            DESCRIPTION
                "The lower threshold of CMs that can be connected.
                 -1 represents invalid value."
                
         ::= { hwDocsIf3CmtsCmThresholdEntry 2 }    
        
    --Table hwDocsIf3CmtsCmThresholdTable end    
    
    --Table hwCmtsCmConnectivityTable begin
        
    hwCmtsCmConnectivityTable OBJECT-TYPE
        SYNTAX     SEQUENCE OF HwCmtsCmConnectivityEntry
        MAX-ACCESS not-accessible
        STATUS     current
        DESCRIPTION
            "
            Indicates the cable modem connectivity.
            The index of this table is docsIf3CmtsCmRegStatusId.
            "
        ::= { hwCmtsAccessObject 45 }        
        
    hwCmtsCmConnectivityEntry OBJECT-TYPE
        SYNTAX     HwCmtsCmConnectivityEntry
        MAX-ACCESS not-accessible
        STATUS     current
        DESCRIPTION
           "
           Indicates the cable modem connectivity.
           The index of this entry is docsIf3CmtsCmRegStatusId.
           "
       INDEX  { docsIf3CmtsCmRegStatusId }
       ::= { hwCmtsCmConnectivityTable 1 }

   HwCmtsCmConnectivityEntry ::=
       SEQUENCE {
           hwCmtsCmConnFirstOnlineTime
             DateAndTime,
           hwCmtsCmConnOnlineRatio
             Integer32,
           hwCmtsCmConnOnlineTimes
             Integer32,
           hwCmtsCmConnMinOnlineTime 
             Integer32,
           hwCmtsCmConnAvgOnlineTime
             Integer32,
           hwCmtsCmConnMaxOnlineTime
             Integer32,
            hwCmtsCmConnMinOfflineTime 
             Integer32,
            hwCmtsCmConnAvgOfflineTime
             Integer32,
            hwCmtsCmConnMaxOfflineTime
             Integer32,
            hwCmtsCmConnOperation
             INTEGER
                 }
       
    hwCmtsCmConnFirstOnlineTime OBJECT-TYPE
          SYNTAX  DateAndTime
          MAX-ACCESS  read-only
          STATUS  current
          DESCRIPTION
                " 
                Indicates the first online time of a cable modem. 
                It indicates the first online time of a cable modem 
                whose connection statistics are cleared if a clearance operation has been performed.
                "
          ::= { hwCmtsCmConnectivityEntry 1 }      
       
    hwCmtsCmConnOnlineRatio OBJECT-TYPE
          SYNTAX  Integer32
          UNITS   "0.01%"
          MAX-ACCESS  read-only
          STATUS  current
          DESCRIPTION
                " 
                Indicates the percentage of time the cable modem has been online.
                -1 represents invalid value.
                "
          ::= { hwCmtsCmConnectivityEntry 2 }          
       
    hwCmtsCmConnOnlineTimes OBJECT-TYPE
          SYNTAX  Integer32
          MAX-ACCESS  read-only
          STATUS  current
          DESCRIPTION
                " 
                Indicates the number of times the cable modem online.
                -1 represents invalid value.
                "
          ::= { hwCmtsCmConnectivityEntry 3 }
          
    hwCmtsCmConnMinOnlineTime OBJECT-TYPE
          SYNTAX  Integer32
          UNITS   "s"
          MAX-ACCESS  read-only
          STATUS  current
          DESCRIPTION
                " 
                Indicates the mininum of time the cable modem has benn online.
                -1 represents invalid value.
                "
          ::= { hwCmtsCmConnectivityEntry 4 }          
          
    hwCmtsCmConnAvgOnlineTime OBJECT-TYPE
          SYNTAX  Integer32
          UNITS   "s"
          MAX-ACCESS  read-only
          STATUS  current
          DESCRIPTION
                " 
                Indicates the average of time the cable modem has benn online.
                -1 represents invalid value.
                "
          ::= { hwCmtsCmConnectivityEntry 5 } 
          
    hwCmtsCmConnMaxOnlineTime OBJECT-TYPE
          SYNTAX  Integer32
          UNITS   "s"
          MAX-ACCESS  read-only
          STATUS  current
          DESCRIPTION
                " 
                Indicates the maxinum of time the cable modem has benn online.
                -1 represents invalid value.
                "
          ::= { hwCmtsCmConnectivityEntry 6 } 
          
    hwCmtsCmConnMinOfflineTime  OBJECT-TYPE
          SYNTAX  Integer32
          UNITS   "s"
          MAX-ACCESS  read-only
          STATUS  current
          DESCRIPTION
                " 
                Indicates the mininum of time the cable modem has benn offline.
                -1 represents invalid value.
                "
          ::= { hwCmtsCmConnectivityEntry 7 } 
          
    hwCmtsCmConnAvgOfflineTime OBJECT-TYPE
          SYNTAX  Integer32
          UNITS   "s"
          MAX-ACCESS  read-only
          STATUS  current
          DESCRIPTION
                " 
                Indicates the average of time the cable modem has benn offline.
                -1 represents invalid value.
                "
          ::= { hwCmtsCmConnectivityEntry 8 }          
                   
    hwCmtsCmConnMaxOfflineTime OBJECT-TYPE
          SYNTAX  Integer32
          UNITS   "s"
          MAX-ACCESS  read-only
          STATUS  current
          DESCRIPTION
                " 
                Indicates the maxinum of time the cable modem has benn offline.
                -1 represents invalid value.
                "
          ::= { hwCmtsCmConnectivityEntry 9 } 
          
    hwCmtsCmConnOperation OBJECT-TYPE
          SYNTAX  INTEGER 
              {
                clear(1),
                invalidValue(-1)
              }
          MAX-ACCESS  read-write
          STATUS  current
          DESCRIPTION
                "This object is used to clear the cable modem connectivity. 
                Options:
                1. clear(1)           - clear the cable modem connectivity.
                2. invalidValue(-1)   - invalid value.
                "
          ::= { hwCmtsCmConnectivityEntry 10 } 
                                                                                          
    --Table hwCmtsCmConnectivityTable end   
    
    --Table hwCmtsAdmissionCtrMaxReservedBandwidthTable begin
        
    hwCmtsAdmissionCtrMaxReservedBandwidthTable OBJECT-TYPE
        SYNTAX     SEQUENCE OF HwCmtsAdmissionCtrMaxReservedBandwidthEntry
        MAX-ACCESS not-accessible
        STATUS     current
        DESCRIPTION
            "Indicates the max reserved bandwidth configuration.
             The index of this table is ifIndex.
            "
        ::= { hwCmtsAccessObject 46 }

    hwCmtsAdmissionCtrMaxReservedBandwidthEntry OBJECT-TYPE
        SYNTAX     HwCmtsAdmissionCtrMaxReservedBandwidthEntry
        MAX-ACCESS not-accessible
        STATUS     current
        DESCRIPTION
            "Indicates the max reserved bandwidth configuration.
             The index of this entry is ifIndex.
            "
        INDEX       { ifIndex }
        ::= { hwCmtsAdmissionCtrMaxReservedBandwidthTable 1 }

    HwCmtsAdmissionCtrMaxReservedBandwidthEntry ::=
        SEQUENCE {
                   hwCmtsAdmissionCtrUsMaxReservedBandwidth          Unsigned32,
                   hwCmtsAdmissionCtrDsMaxReservedBandwidth          Unsigned32
                  }                         
         
   hwCmtsAdmissionCtrUsMaxReservedBandwidth OBJECT-TYPE
            SYNTAX Unsigned32 (0..30720 | 4294967295)
            UNITS   "kbps"
            MAX-ACCESS read-write
            STATUS current
            DESCRIPTION
                "The upstream max reserved bandwidth.
                 4294967295 represents invalid value and
                 to delete the configuration."
                
         ::= { hwCmtsAdmissionCtrMaxReservedBandwidthEntry 1 } 
         
   hwCmtsAdmissionCtrDsMaxReservedBandwidth OBJECT-TYPE
            SYNTAX Unsigned32 (0..42884 | 4294967295)
            UNITS   "kbps"
            MAX-ACCESS read-write
            STATUS current
            DESCRIPTION
                "The downstream max reserved bandwidth.
                 4294967295 represents invalid value and
                 to delete the configuration."
                
         ::= { hwCmtsAdmissionCtrMaxReservedBandwidthEntry 2 }     
        
   --Table hwCmtsAdmissionCtrMaxReservedBandwidthTable end  
    --Table hwDocsLoadbal3RestrictCmCfgTable begin
    
    hwDocsLoadbal3RestrictCmCfgTable OBJECT-TYPE
        SYNTAX     SEQUENCE OF HwDocsLoadbal3RestrictCmCfgEntry
        MAX-ACCESS not-accessible
        STATUS     current
        DESCRIPTION
            "Indicates the CMs information that added to restricted load balancing group. 
             The index of this table is docsLoadbal3RestrictCmCfgId.
            "
        ::= { hwCmtsAccessObject 47 }

    hwDocsLoadbal3RestrictCmCfgEntry OBJECT-TYPE
        SYNTAX     HwDocsLoadbal3RestrictCmCfgEntry
        MAX-ACCESS not-accessible
        STATUS     current
        DESCRIPTION
            "Indicates the CMs information that added to restricted load balancing group.
             The index of this entry is docsLoadbal3RestrictCmCfgId.
            "
        INDEX       { docsLoadbal3RestrictCmCfgId }
        ::= { hwDocsLoadbal3RestrictCmCfgTable 1 }

    HwDocsLoadbal3RestrictCmCfgEntry ::=
        SEQUENCE {
                   hwDocsLoadbal3RestrictCmCfgMethod      BITS,
                   hwDocsLoadbal3RestrictCmCfgMacAddr     MacAddress,
                   hwDocsLoadbal3RestrictCmCfgMacAddrMask MacAddress,
                   hwDocsLoadbal3RestrictCmCfgGrpId       Unsigned32,
                   hwDocsLoadbal3RestrictCmCfgMacVer      INTEGER,
                   hwDocsLoadbal3RestrictCmCfgStatus         RowStatus,
                   hwDocsLoadbal3RestrictCmCfgServiceTypeID  OCTET STRING
                 }
 
    hwDocsLoadbal3RestrictCmCfgMethod OBJECT-TYPE
          SYNTAX  BITS 
          {
            macRange(0),
            docsisVersion(1),
            serviceType(2)
          }
          MAX-ACCESS  read-write
          STATUS  current
          DESCRIPTION
                "Indicates the method of adding CM to restricted load balancing group.
                 Options:
                  1. macRange(0) - Add CM to restricted load balancing group by CM MAC with MAC mask
                  2. docsisVersion(1) - Add CM to restricted load balancing group by CM docsis version 
                  3. serviceType(2) - Add CM to restricted load balancing group by CM service type ID
                  Default value: macRange(0)
                "
          ::= { hwDocsLoadbal3RestrictCmCfgEntry 1 }
          
    hwDocsLoadbal3RestrictCmCfgMacAddr OBJECT-TYPE
            SYNTAX MacAddress
            MAX-ACCESS read-write
            STATUS current
            DESCRIPTION
                "Indicates the MAC address of the CM that added to the restricted load balancing group."
            DEFVAL { '000000000000'H }
         ::= { hwDocsLoadbal3RestrictCmCfgEntry 2 }    

    hwDocsLoadbal3RestrictCmCfgMacAddrMask OBJECT-TYPE
            SYNTAX MacAddress
            MAX-ACCESS read-write
            STATUS current
            DESCRIPTION
                "Indicates the MAC address mask of the CM that added to the restricted load balancing group.
                 This attribute corresponds to a  bit mask acting as
               a wild card to associate a cable modem MAC addresses
             to a Restricted Load Balancing Group ID referenced by
             a restricted group Id or a Service Type ID.
           The cable modem matching criteria is performed by bit-Anded
           the cable modem MAC address with the MacAddrMAsk
           attribute and being compared with the bit-Anded
           of attributes MacdAddr and MacAddrMask.
  
           A cable modem MAC address look up is performed first with
           instances containing this attribute value not null,
           if several entries match, the largest consecutive
           bit match from MSB to LSB is used.
                "
             DEFVAL { 'FFFFFFFFFFFF'H }
         ::= { hwDocsLoadbal3RestrictCmCfgEntry 3 }    
     
    hwDocsLoadbal3RestrictCmCfgGrpId OBJECT-TYPE
            SYNTAX Unsigned32
            MAX-ACCESS read-write
            STATUS current
            DESCRIPTION
                "Indicates the restricted load balancing group identifier.
                 The value zero indicates that the instance is matched only against the ServiceTypeId value."
         ::= { hwDocsLoadbal3RestrictCmCfgEntry 4 }    
         
    hwDocsLoadbal3RestrictCmCfgMacVer OBJECT-TYPE
            SYNTAX INTEGER
            {
                doc20(2),
                doc30(3),
                doc31(4),
                invalidValue(-1) 
            }

            MAX-ACCESS read-write
            STATUS current
            DESCRIPTION
                "Indicates the restricted load balancing group identifier.
                Options:
                  1. doc20(2)  - Indicates CM version is docsis 2.0 
                  2. doc30(3)  - Indicates CM version is docsis 3.0
                  3. doc31(4)  - Indicates CM version is docsis 3.1
                  4. invalidValue(-1) - Indicates invalid value,can not use this value when create action
                "
         ::= { hwDocsLoadbal3RestrictCmCfgEntry 5 }    

    hwDocsLoadbal3RestrictCmCfgStatus OBJECT-TYPE
            SYNTAX RowStatus
            MAX-ACCESS read-create
            STATUS current
            DESCRIPTION
                "Indicates the row status to create or delete a restricted load balancing CM group."
         ::= { hwDocsLoadbal3RestrictCmCfgEntry 6 }    
 
    hwDocsLoadbal3RestrictCmCfgServiceTypeID OBJECT-TYPE
            SYNTAX OCTET STRING(SIZE (0..16))
            MAX-ACCESS read-write
            STATUS current
            DESCRIPTION
                "Indicates the service type ID of the CM that added to the restricted load balancing group."
         ::= { hwDocsLoadbal3RestrictCmCfgEntry 7 }  
         
    --Table hwDocsLoadbal3RestrictCmCfgTable end
    
    --Table hwCmtsCmFrequencyTable begin
    hwCmtsCmFrequencyTable OBJECT-TYPE
        SYNTAX     SEQUENCE OF HwCmtsCmFrequencyEntry
        MAX-ACCESS not-accessible
        STATUS     current
        DESCRIPTION
            "
            This table describes the attributes cm channels.
            The index of this table is ifIndex and hwCmtsCmFrequencyMacAddress.
            "
        ::= { hwCmtsAccessObject 48 }
        
    hwCmtsCmFrequencyEntry OBJECT-TYPE
        SYNTAX     HwCmtsCmFrequencyEntry
        MAX-ACCESS not-accessible
        STATUS     current
        DESCRIPTION
           "
            This table describes the attributes cm channels.
           The index of this entry is ifIndex and hwCmtsCmFrequencyMacAddress.
           "
       INDEX       {ifIndex, hwCmtsCmFrequencyMacAddress }
       ::= { hwCmtsCmFrequencyTable 1 }

   HwCmtsCmFrequencyEntry ::=
       SEQUENCE {
           hwCmtsCmFrequencyMacAddress       MacAddress,
           hwCmtsCmFrequencyDsChannelID      Integer32,
           hwCmtsCmFrequencyUsChannelID      Integer32,
           hwCmtsCmFrequencyRowStatus        RowStatus
       }
       
   hwCmtsCmFrequencyMacAddress OBJECT-TYPE
       SYNTAX MacAddress
       MAX-ACCESS not-accessible 
       STATUS current
       DESCRIPTION
           "
           Indicates the MAC address of CM.
           "
       ::= { hwCmtsCmFrequencyEntry 1 } 
       
    hwCmtsCmFrequencyDsChannelID OBJECT-TYPE                                               
       SYNTAX  Integer32 (-1 | 1..104)
       MAX-ACCESS  read-write
       STATUS  current
       DESCRIPTION
       "
       The CMTS identification of the downstream channel.
       If the downstream channel ID is unknown, this object returns a value of -1.
       "                                                                  
       ::= { hwCmtsCmFrequencyEntry 2 }            
       
    hwCmtsCmFrequencyUsChannelID OBJECT-TYPE                                                            
       SYNTAX Integer32 (-1 | 1..20)                                         
       MAX-ACCESS read-write                                                             
       STATUS current                                                                        
       DESCRIPTION                                                                           
       "
       The CMTS identification of the upstream channel.
       If the upstream channel ID is unknown, this object returns a value of -1.
       "                                                                                 
       ::= { hwCmtsCmFrequencyEntry 3 } 
                              
    hwCmtsCmFrequencyRowStatus OBJECT-TYPE
          SYNTAX RowStatus
          MAX-ACCESS read-create
          STATUS current
          DESCRIPTION
              "RowStatus.
               1. active(1)          -the status of the row is active
               2. createAndGo(4)     -the status of the row is createAndGo
               3. destroy(6)         -the status of the row is destroy
               Active(1) is state, the value may be read or written.
               CreateAndGo(4), and destroy(6) are actions, these values may be written, but are never read.
              "
       ::= { hwCmtsCmFrequencyEntry 4 }                                                                          
        
    --Table hwCmtsCmFrequencyTable end
    
        
    -- Table hwCmtsCmNumStatisticsTable
    hwCmtsCmNumStatisticsTable OBJECT-TYPE
          SYNTAX     SEQUENCE OF HwCmtsCmNumStatisticsEntry
          MAX-ACCESS not-accessible
          STATUS     current
          DESCRIPTION
               "Indicates the number of cable modem by one port.
               The index of this table is hwCmtsCmNumStatisticsIfIndex."
          ::= { hwCmtsAccessObject 49 }

    hwCmtsCmNumStatisticsEntry OBJECT-TYPE
          SYNTAX     HwCmtsCmNumStatisticsEntry
          MAX-ACCESS not-accessible
          STATUS     current
          DESCRIPTION
               "Indicates the number of cable modem by one port.
                The index of this entry is hwCmtsCmNumStatisticsIfIndex."
          INDEX       { hwCmtsCmNumStatisticsIfIndex }
          ::= { hwCmtsCmNumStatisticsTable 1 }

    HwCmtsCmNumStatisticsEntry ::=
          SEQUENCE {
                    hwCmtsCmNumStatisticsIfIndex                Integer32,
                    hwCmtsCmNumStatisticsPortIfIndex            Integer32,
                    hwCmtsCmNumStatisticsIfType                 INTEGER,
                    hwCmtsCmNumStatisticsTotalCmNum             Unsigned32,
                    hwCmtsCmNumStatisticsRegCmNum               Unsigned32,
                    hwCmtsCmNumStatisticsWidebandCmNum          Unsigned32
                   }
                   
    hwCmtsCmNumStatisticsIfIndex OBJECT-TYPE
          SYNTAX  Integer32
          MAX-ACCESS  not-accessible
          STATUS  current
          DESCRIPTION
                "Indicates the index of CM number statistics table.
                The ifIndex have two types 
                1. upstream channel ifIndex, include channel type, docsis port index and channel index
                2. downstream channel ifIndex, include channel type, docsis port index and channel index"
          ::= { hwCmtsCmNumStatisticsEntry 1 }

    hwCmtsCmNumStatisticsPortIfIndex OBJECT-TYPE
          SYNTAX     Integer32
          MAX-ACCESS read-only
          STATUS     current
          DESCRIPTION
               "Indicates the docsis port IfIndex"
          ::= { hwCmtsCmNumStatisticsEntry 2 }

   hwCmtsCmNumStatisticsIfType OBJECT-TYPE
          SYNTAX  INTEGER{uschannel(59),dschannel(60)}
          MAX-ACCESS read-only
          STATUS     current
          DESCRIPTION
                "Indicates the query type.
                Options:
                1. uschannel(59) -Indicates the type is upstream channel 
                2. dschannel(60) -Indicates the type is downstream channel 
                "
          ::= { hwCmtsCmNumStatisticsEntry 3 }

    hwCmtsCmNumStatisticsTotalCmNum OBJECT-TYPE
          SYNTAX     Unsigned32
          MAX-ACCESS read-only
          STATUS     current
          DESCRIPTION
               "The number of CM."
          ::= { hwCmtsCmNumStatisticsEntry 4 }

    hwCmtsCmNumStatisticsRegCmNum OBJECT-TYPE
          SYNTAX     Unsigned32
          MAX-ACCESS read-only
          STATUS     current
          DESCRIPTION
               "The number of registered CM."
          ::= { hwCmtsCmNumStatisticsEntry 5 }

    hwCmtsCmNumStatisticsWidebandCmNum OBJECT-TYPE
          SYNTAX     Unsigned32
          MAX-ACCESS read-only
          STATUS     current
          DESCRIPTION
               "The number of widband CM."
          ::= { hwCmtsCmNumStatisticsEntry 6 }
          
     -- Table hwCmtsCmIndexListTable
    hwCmtsCmIndexListTable OBJECT-TYPE
          SYNTAX     SEQUENCE OF HwCmtsCmIndexListEntry
          MAX-ACCESS not-accessible
          STATUS     current
          DESCRIPTION
               "Indicates the index list of cable modem by one port.
               The indexes of this table are hwCmtsCmIndexListIfIndex and hwCmtsCmIndexListSecondIndex."
          ::= { hwCmtsAccessObject 50 }

    hwCmtsCmIndexListEntry OBJECT-TYPE
          SYNTAX     HwCmtsCmIndexListEntry
          MAX-ACCESS not-accessible
          STATUS     current
          DESCRIPTION
               "Indicates the index list of cable modem by one port.
                The indexes of this entry are hwCmtsCmIndexListIfIndex and hwCmtsCmIndexListSecondIndex."
          INDEX       { hwCmtsCmIndexListIfIndex, hwCmtsCmIndexListSecondIndex }
          ::= { hwCmtsCmIndexListTable 1 }

    HwCmtsCmIndexListEntry ::=
          SEQUENCE {
                    hwCmtsCmIndexListIfIndex                Integer32,
                    hwCmtsCmIndexListSecondIndex            INTEGER,
                    hwCmtsCmIndexList                       OCTET STRING                    
                   }
                   
    hwCmtsCmIndexListIfIndex OBJECT-TYPE
          SYNTAX  Integer32
          MAX-ACCESS  not-accessible
          STATUS  current
          DESCRIPTION
                "Indicates the index of CM index list table.
                The ifIndex have three types 
                1. docsis port ifIndex
                2. upstream channel ifIndex, include channel type, docsis port index and channel index
                3. downstream channel ifIndex, include channel type, docsis port index and channel index"
          ::= { hwCmtsCmIndexListEntry 1 }

    hwCmtsCmIndexListSecondIndex OBJECT-TYPE
          SYNTAX  INTEGER{all(1),online(2),offline(3)}
          MAX-ACCESS not-accessible
          STATUS     current
          DESCRIPTION
                "Indicates the second Index of CM Index List Table.
                Options:
                1. all(1)- Indicates return all the CM Index
                2. online(2)- Indicates return the CM Index of the online CMs
                3. offline(3)- Indicates return the CM Index of the offline CMs"
          ::= { hwCmtsCmIndexListEntry 2 }  
          
    hwCmtsCmIndexList OBJECT-TYPE
          SYNTAX     OCTET STRING
          MAX-ACCESS read-only
          STATUS     current
          DESCRIPTION
               "Indicates the index list of the cable modem."
          ::= { hwCmtsCmIndexListEntry 3 }      
    
    hwDocsIfCmtsUpChnlMslotCounterTable OBJECT-TYPE
           SYNTAX     SEQUENCE OF HwDocsIfCmtsUpChnlMslotCounterEntry
           MAX-ACCESS not-accessible
           STATUS     current
           DESCRIPTION
               "Indicates the mini-slot counter table of a CMTS upstream channel.
               The indexes of this table are ifIndex and hwDocsIfCmtsUpChnlMslotIntervalUsageCode."
           ::= { hwCmtsAccessObject 51 }

    hwDocsIfCmtsUpChnlMslotCounterEntry OBJECT-TYPE
           SYNTAX     HwDocsIfCmtsUpChnlMslotCounterEntry
           MAX-ACCESS not-accessible
           STATUS     current
           DESCRIPTION
               "Indicates the mini-slot counter table of a CMTS upstream channel.
                 The indexes of this entry are ifIndex and hwDocsIfCmtsUpChnlMslotIntervalUsageCode.
               "
           INDEX       { ifIndex, hwDocsIfCmtsUpChnlMslotIntervalUsageCode }
        ::= { hwDocsIfCmtsUpChnlMslotCounterTable 1 }


    HwDocsIfCmtsUpChnlMslotCounterEntry ::=
          SEQUENCE {
                    hwDocsIfCmtsUpChnlMslotIntervalUsageCode         INTEGER,
                    hwDocsIfCmtsUpChnlUcastGrantedMslots             Counter64
                  }

    hwDocsIfCmtsUpChnlMslotIntervalUsageCode OBJECT-TYPE
        SYNTAX       INTEGER {
            request(1),
            initialRanging(3),
            periodicRanging(4),
            shortData(5),
            longData(6),         
            advPhyShortData(9),
            advPhyLongData(10),
            ugs(11),
            data(12),
            dataInitial(13)
        }
        MAX-ACCESS  not-accessible
        STATUS      current
        DESCRIPTION
            "An index into the Channel Modulation table that, when grouped with other Interval Usage Codes, fully
             instantiates all modulation sets for a given upstream channel.
            Options:
            1.request(1) - request IUC
            2.initialRanging(3) - initialRanging IUC 
            3.periodicRanging(4) -  periodicRanging IUC  
            4.shortData(5) - shortData IUC
            5.longData(6) - longData IUC
            6.advPhyShortData(9) - advPhyShortData IUC
            7.advPhyLongData(10) - advPhyLongData IUC
            8.ugs(11) - ugs IUC
            9.data(12) - data IUC
            10.dataInitial(13) - dataInitial IUC
            "
        REFERENCE
            "Data-Over-Cable Service Interface Specifications: Radio
             Frequency Interface Specification SP-RFIv2.0-I10-051209,
             Table 8-20."
        ::= { hwDocsIfCmtsUpChnlMslotCounterEntry 1 }


    hwDocsIfCmtsUpChnlUcastGrantedMslots OBJECT-TYPE
          SYNTAX  Counter64
          UNITS      "mini-slots"
          MAX-ACCESS read-only
          STATUS     current
          DESCRIPTION
                "For each IUC type, the total number of minislots granted to Unicast SIDs"
          ::= { hwDocsIfCmtsUpChnlMslotCounterEntry 2 }  
    --Table hwDocsIfCmtsUpChnlMslotCounterTable end

  --Table hwCmtsCmWhitelistTable
    hwCmtsCmWhitelistTable OBJECT-TYPE
          SYNTAX     SEQUENCE OF HwCmtsCmWhitelistEntry
          MAX-ACCESS not-accessible
          STATUS     current
          DESCRIPTION
               "This table describes the CM whitelist by one port.
               The indexes of this table are ifindex and hwCmtsCmWhitelistIndex."
          ::= { hwCmtsAccessObject 52 }

    hwCmtsCmWhitelistEntry OBJECT-TYPE
          SYNTAX     HwCmtsCmWhitelistEntry
          MAX-ACCESS not-accessible
          STATUS     current
          DESCRIPTION
               "This table describes the CM whitelist by one port.
                The indexes of this entry are ifindex and hwCmtsCmWhitelistIndex."
          INDEX       { ifIndex, hwCmtsCmWhitelistIndex }
          ::= { hwCmtsCmWhitelistTable 1 }
          
    HwCmtsCmWhitelistEntry ::=
          SEQUENCE {
                    hwCmtsCmWhitelistIndex                Unsigned32,
                    hwCmtsCmWhitelistType                 OCTET STRING,
                    hwCmtsCmWhitelistMacList              OCTET STRING,
                    hwCmtsCmWhitelistMacMaskList          OCTET STRING,
                    hwCmtsCmWhitelistRowstatus            RowStatus                 
                   } 
                   
    hwCmtsCmWhitelistIndex OBJECT-TYPE
          SYNTAX  Unsigned32 (1..512 | 4294967295)
          MAX-ACCESS  not-accessible
          STATUS  current
          DESCRIPTION
                "Indicates the index of whitelist record.
                4294967295(0xFFFFFFFF) indicates that an index will be allocated automatically for the member. 
                "
          ::= { hwCmtsCmWhitelistEntry 1 }
          
   hwCmtsCmWhitelistType OBJECT-TYPE
          SYNTAX     OCTET STRING (SIZE (1..4))
          MAX-ACCESS read-write
          STATUS     current
          DESCRIPTION
               "Indicates the index type of the CM whitelist.
               Only 0x80 0x00 0x00 0x00 is supported, 
               bit 0 is added based on the MAC address, and other bits are reserved.
               "
          ::= { hwCmtsCmWhitelistEntry 2 }        

   hwCmtsCmWhitelistMacList OBJECT-TYPE
          SYNTAX     OCTET STRING (SIZE (0..447))
          MAX-ACCESS read-write
          STATUS     current
          DESCRIPTION
               "Indicates the CM's MAC address.
               The number of MAC addresses must be the same as that of the MAC address masks. 
               Users must use a comma (0x2C) to separate the MAC addresses, 
               such as, MAC addresses : 0xB8 0x16 0x19 0xFA 0x79 0x98 0x2C 0xA4 0x7A 0xA4 0x72 0x8D 0x8D
                        MAC address masks: 0xFF 0xFF 0xFF 0xFF 0xFF 0xFF 0x2C 0xFF 0xFF 0xFF 0xFF 0xFF 0xFF."
          ::= { hwCmtsCmWhitelistEntry 3 } 
          
   hwCmtsCmWhitelistMacMaskList OBJECT-TYPE
          SYNTAX     OCTET STRING (SIZE (0..447))
          MAX-ACCESS read-write
          STATUS     current
          DESCRIPTION
               "Indicates the CM's MAC mask.
               The number of MAC address masks must be the same as that of the MAC addresses. 
               Users must use a comma (0x2C) to separate the MAC address masks, 
               such as, MAC addresses : 0xB8 0x16 0x19 0xFA 0x79 0x98 0x2C 0xA4 0x7A 0xA4 0x72 0x8D 0x8D
                        MAC address masks: 0xFF 0xFF 0xFF 0xFF 0xFF 0xFF 0x2C 0xFF 0xFF 0xFF 0xFF 0xFF 0xFF."
          ::= { hwCmtsCmWhitelistEntry 4 } 
          
   hwCmtsCmWhitelistRowstatus OBJECT-TYPE
         SYNTAX RowStatus
         MAX-ACCESS read-create
         STATUS current
         DESCRIPTION
             "RowStatus.
               1. active(1)      -indicates the query operation.
               2. createAndGo(4) -indicates creating cm whitelist.
               3. destroy(6)     -indicates deleting cm whitelist. 
              "
       ::= { hwCmtsCmWhitelistEntry  5 }                                                                          
           
    --Table hwCmtsCmWhitelistTable end
    
    --Table hwCmtsCmWhitelistModeTable
    hwCmtsCmWhitelistModeTable OBJECT-TYPE
          SYNTAX     SEQUENCE OF HwCmtsCmWhitelistModeEntry
          MAX-ACCESS not-accessible
          STATUS     current
          DESCRIPTION
               "This table describes the CM whitelist switch by one port.
               The indexes of this table are ifindex."
          ::= { hwCmtsAccessObject 53 }

    hwCmtsCmWhitelistModeEntry OBJECT-TYPE
          SYNTAX     HwCmtsCmWhitelistModeEntry
          MAX-ACCESS not-accessible
          STATUS     current
          DESCRIPTION
               "This table describes the CM whitelist switch by one port.
                The index of this entry is ifindex."
          INDEX       { ifIndex }
          ::= { hwCmtsCmWhitelistModeTable 1 }
          
    HwCmtsCmWhitelistModeEntry ::=
          SEQUENCE {
                    hwCmtsCmWhitelistMode                INTEGER
                   }
                    
    hwCmtsCmWhitelistMode  OBJECT-TYPE             
    SYNTAX  INTEGER {
                        enable(0),
                        disable(1)
                    }
          MAX-ACCESS  read-write
          STATUS  current
          DESCRIPTION
                "The switch for the cm whitelist mode.
                Options:
                1. enable(0) - enable cm whitelist mode of one port
                2. disable(1) - disable cm whitelist mode of one port
                Default: disable
                "
       ::= { hwCmtsCmWhitelistModeEntry  1 }     
    
    --Table hwCmtsCmWhitelistModeTable end

    --Table hwDocsIfCmtsCmCpeMacToCmTable begin
        
    hwDocsIfCmtsCmCpeMacToCmTable OBJECT-TYPE
        SYNTAX     SEQUENCE OF HwDocsIfCmtsCmCpeMacToCmEntry
        MAX-ACCESS not-accessible
        STATUS     current
        DESCRIPTION
            "
            Indicates the CM index queried by the MAC address of a CM or CPE.
            The index of this table is hwDocsIfCmtsCmCpeMac.
            "
        ::= { hwCmtsAccessObject 54 }

    hwDocsIfCmtsCmCpeMacToCmEntry OBJECT-TYPE
        SYNTAX     HwDocsIfCmtsCmCpeMacToCmEntry
        MAX-ACCESS not-accessible
        STATUS     current
        DESCRIPTION
            "
            Indicates the CM index queried by the MAC address of a CM or CPE.
            The index of this entry is hwDocsIfCmtsCmCpeMac.
            "
        INDEX       { hwDocsIfCmtsCmCpeMac }
        ::= { hwDocsIfCmtsCmCpeMacToCmTable 1 }

    HwDocsIfCmtsCmCpeMacToCmEntry ::=
        SEQUENCE {
                 hwDocsIfCmtsCmCpeMac MacAddress,
                 hwDocsIfCmtsCmCpeMacCmPtr Integer32
        }
        
    hwDocsIfCmtsCmCpeMac OBJECT-TYPE
            SYNTAX MacAddress
            MAX-ACCESS not-accessible
            STATUS current
            DESCRIPTION
                "Indicates the MAC address of the CM or CPE.
                "
         ::= { hwDocsIfCmtsCmCpeMacToCmEntry 1 }
         
    hwDocsIfCmtsCmCpeMacCmPtr OBJECT-TYPE
            SYNTAX Integer32
            MAX-ACCESS read-only
            STATUS current
            DESCRIPTION
                "
                Indicates the CM index.
                "
         ::= { hwDocsIfCmtsCmCpeMacToCmEntry 2 }
    
    --Table hwDocsIfCmtsCmCpeMacToCmTable end
    
    --Table hwDocsLoadbalanceStatTable begin
        
    hwDocsLoadbalanceStatTable OBJECT-TYPE
        SYNTAX     SEQUENCE OF HwDocsLoadbalanceStatEntry
        MAX-ACCESS not-accessible
        STATUS     current
        DESCRIPTION
            "
            Indicates the load balance statistics include DBC and DCC migration data on channels.
            The index of this table is ifIndex.
            "
        ::= { hwCmtsAccessObject 55  }

    hwDocsLoadbalanceStatEntry OBJECT-TYPE
        SYNTAX     HwDocsLoadbalanceStatEntry
        MAX-ACCESS not-accessible
        STATUS     current
        DESCRIPTION
            "
            Indicates the load balance statistics include DBC and DCC migration data on channels.
            The index of this entry is ifIndex.
            "
        INDEX       { ifIndex }
        ::= { hwDocsLoadbalanceStatTable 1 }

    HwDocsLoadbalanceStatEntry ::=
        SEQUENCE {
                 hwDocsLoadbalanceDccStatComplete  Counter32,
                 hwDocsLoadbalanceDccStatPending   Counter32,
                 hwDocsLoadbalanceDccStatRetries   Counter32,
                 hwDocsLoadbalanceDccStatFailure   Counter32,
                 hwDocsLoadbalanceDbcStatComplete  Counter32,
                 hwDocsLoadbalanceDbcStatPending   Counter32,
                 hwDocsLoadbalanceDbcStatRetries   Counter32,
                 hwDocsLoadbalanceDbcStatFailure   Counter32,
                 hwDocsLoadbalanceStatClear        INTEGER           
        }
        
    hwDocsLoadbalanceDccStatComplete OBJECT-TYPE
            SYNTAX Counter32
            MAX-ACCESS read-only
            STATUS current
            DESCRIPTION
                "Indicates the DCC complete statisitc of Loadbalance.  
                4294967295(0xFFFFFFFF) represents invalid value.           
                "
         ::= { hwDocsLoadbalanceStatEntry 1 }
   
    hwDocsLoadbalanceDccStatPending OBJECT-TYPE
            SYNTAX Counter32 
            MAX-ACCESS read-only
            STATUS current
            DESCRIPTION
                "Indicates the DCC pending statisitc of Loadbalance.  
                4294967295(0xFFFFFFFF) represents invalid value.           
                "
         ::= { hwDocsLoadbalanceStatEntry 2 }
     
     hwDocsLoadbalanceDccStatRetries OBJECT-TYPE
            SYNTAX Counter32 
            MAX-ACCESS read-only
            STATUS current
            DESCRIPTION
                "Indicates the DCC retries statisitc of Loadbalance.  
                4294967295(0xFFFFFFFF) represents invalid value.           
                "
         ::= { hwDocsLoadbalanceStatEntry 3 } 
         
     hwDocsLoadbalanceDccStatFailure OBJECT-TYPE
            SYNTAX Counter32 
            MAX-ACCESS read-only
            STATUS current
            DESCRIPTION
                "Indicates the DCC failure statisitc of Loadbalance. 
                4294967295(0xFFFFFFFF) represents invalid value.           
                "
         ::= { hwDocsLoadbalanceStatEntry 4 }  
                 
    hwDocsLoadbalanceDbcStatComplete OBJECT-TYPE
            SYNTAX Counter32
            MAX-ACCESS read-only
            STATUS current
            DESCRIPTION
                "Indicates the DBC complete statisitc of Loadbalance. 
                4294967295(0xFFFFFFFF) represents invalid value.           
                "
         ::= { hwDocsLoadbalanceStatEntry 5 }
   
    hwDocsLoadbalanceDbcStatPending OBJECT-TYPE
            SYNTAX Counter32 
            MAX-ACCESS read-only
            STATUS current
            DESCRIPTION
                "Indicates the DBC pending statisitc of Loadbalance.   
                4294967295(0xFFFFFFFF) represents invalid value.           
                "
         ::= { hwDocsLoadbalanceStatEntry 6 }
     
     hwDocsLoadbalanceDbcStatRetries OBJECT-TYPE
            SYNTAX Counter32
            MAX-ACCESS read-only
            STATUS current
            DESCRIPTION
                "Indicates the DBC retries statisitc of Loadbalance.
                4294967295(0xFFFFFFFF) represents invalid value.           
                "
         ::= { hwDocsLoadbalanceStatEntry 7 } 
         
     hwDocsLoadbalanceDbcStatFailure OBJECT-TYPE
            SYNTAX Counter32
            MAX-ACCESS read-only
            STATUS current
            DESCRIPTION
                "Indicates the DBC failure statisitc of Loadbalance.
                4294967295(0xFFFFFFFF) represents invalid value.           
                "
         ::= { hwDocsLoadbalanceStatEntry 8 }          

     hwDocsLoadbalanceStatClear OBJECT-TYPE
            SYNTAX INTEGER            
            {
                clear(1),
                invalidValue(-1) 
            }

            MAX-ACCESS read-create
            STATUS current
            DESCRIPTION
                "Indicates loadbalance statisitc operation mode.
                Options:
                  1. clear(1) - Indicates clearing the statistics informations of loadbalance.
                  2. invalidValue(-1) - Indicates invalid value
                "     
         ::= { hwDocsLoadbalanceStatEntry 9 }     
               
    --Table hwDocsLoadbalanceStatTable end
    
    --Table hwCmtsUsSpectrumMonitorCfgTable begin
    hwCmtsUsSpectrumMonitorCfgTable OBJECT-TYPE
        SYNTAX     SEQUENCE OF HwCmtsUsSpectrumMonitorCfgEntry
        MAX-ACCESS not-accessible
        STATUS     current
        DESCRIPTION
            "
            Indicates the upstream frequency spectrum scanning function.
            The index of this table is cable port ifIndex.
            "
        ::= { hwCmtsAccessObject 56 }

    hwCmtsUsSpectrumMonitorCfgEntry OBJECT-TYPE
        SYNTAX     HwCmtsUsSpectrumMonitorCfgEntry
        MAX-ACCESS not-accessible
        STATUS     current
        DESCRIPTION
            "
            Indicates the upstream frequency spectrum scanning function.
            The index of this entry is cable port ifIndex.
            "
        INDEX       { ifIndex }
        ::= { hwCmtsUsSpectrumMonitorCfgTable 1 }

    HwCmtsUsSpectrumMonitorCfgEntry ::=
        SEQUENCE {
                 hwCmtsUsSpectrumMonitorSwitch INTEGER,
                 hwCmtsUsSpectrumMonitorMode INTEGER,
                 hwCmtsUsSpectrumMonitorResolution INTEGER,
                 hwCmtsUsSpectrumMonitorSampleTime INTEGER,
                 hwCmtsUsSpectrumMonitorFrequencyStart Integer32,
                 hwCmtsUsSpectrumMonitorFrequencyEnd Integer32,
                 hwCmtsUsSpectrumMonitorSampleStart Integer32,
                 hwCmtsUsSpectrumMonitorUsSgId Integer32,
                 hwCmtsUsSpectrumMonitorUsChannelId Integer32,
                 hwCmtsUsSpectrumMonitorFrequencyList OCTET STRING,
                 hwCmtsUsSpectrumMonitorReportPeriod INTEGER
        }
        
    hwCmtsUsSpectrumMonitorSwitch OBJECT-TYPE
            SYNTAX  INTEGER{enable(1),disable(2)}
            MAX-ACCESS read-write
            STATUS current
            DESCRIPTION
                "Indicates the upstream frequency spectrum scanning function.
                Default:disable(2)
                Options:
                1. enable(1) - enable the upstream frequency spectrum scanning function
                2. disable(2) - disable the upstream frequency spectrum scanning function
                "
         ::= { hwCmtsUsSpectrumMonitorCfgEntry 1 }
   
    hwCmtsUsSpectrumMonitorMode OBJECT-TYPE
            SYNTAX  INTEGER{noise(1),carrier(2),all(3),freeRunning(4),invalid(-1)}
            MAX-ACCESS read-write
            STATUS current
            DESCRIPTION
                "Indicates the upstream frequency spectrum scanning mode.
                Default:noise(1)
                Options:
                1. noise(1) -Scanning noise frequency spectrum
                2. carrier(2) -Scanning carrier frequency spectrum
                3. all(3) -Scanning both noise and carrier frequency spectrum
                4. freeRunning(4) -Scanning noise or carrier frequency spectrum
                5. invalid(-1) -Invalid               
                "
         ::= { hwCmtsUsSpectrumMonitorCfgEntry 2 }
     
    hwCmtsUsSpectrumMonitorResolution OBJECT-TYPE
            SYNTAX INTEGER{hz50K(1), 
                           hz100K(2),
                           hz150K(3),
                           hz200K(4),
                           hz250K(5),
                           hz300K(6),
                           hz350K(7),
                           hz400K(8),
                           hz450K(9),
                           hz500K(10),
                           hz60K(11), 
                           hz120K(12),
                           hz180K(13),
                           hz240K(14),
                           hz360K(15),
                           hz420K(16),
                           hz480K(17),
                           hz540K(18),
                           hz600K(19),                        
                           invalid(-1)}
            MAX-ACCESS read-write
            STATUS current
            DESCRIPTION
                "Indicates the upstream frequency spectrum scanning resolution.
                 Default: hz300K(6)
                 Options:
                 1. hz50K(1)       - Sets the upstream frequency spectrum scanning resolution to 50Khz
                 2. hz100K(2)      - Sets the upstream frequency spectrum scanning resolution to 100Khz
                 3. hz150K(3)      - Sets the upstream frequency spectrum scanning resolution to  150Khz
                 4. hz200K(4)      - Sets the upstream frequency spectrum scanning resolution to 200Khz
                 5. hz250K(5)      - Sets the upstream frequency spectrum scanning resolution to 250Khz
                 6. hz300K(6)      - Sets the upstream frequency spectrum scanning resolution to 300Khz
                 7. hz350K(7)      - Sets the upstream frequency spectrum scanning resolution to 350Khz
                 8. hz400K(8)      - Sets the upstream frequency spectrum scanning resolution to 400Khz
                 9. hz450K(9)      - Sets the upstream frequency spectrum scanning resolution to 450Khz
                 10. hz500K(10)    - Sets the upstream frequency spectrum scanning resolution to 500Khz
                 11. hz60K(11)     - Sets the upstream frequency spectrum scanning resolution to 60Khz
                 12. hz120K(12)    - Sets the upstream frequency spectrum scanning resolution to 120Khz
                 13. hz180K(13)    - Sets the upstream frequency spectrum scanning resolution to  180Khz
                 14. hz240K(14)    - Sets the upstream frequency spectrum scanning resolution to 240Khz
                 15. hz360K(15)    - Sets the upstream frequency spectrum scanning resolution to 360Khz
                 16. hz420K(16)    - Sets the upstream frequency spectrum scanning resolution to 420Khz
                 17. hz480K(17)    - Sets the upstream frequency spectrum scanning resolution to 480Khz
                 18. hz540K(18)    - Sets the upstream frequency spectrum scanning resolution to 540Khz
                 19. hz600K(19)    - Sets the upstream frequency spectrum scanning resolution to 600Khz               
                 20. invalid(-1)   - Invalid value
                "
         ::= { hwCmtsUsSpectrumMonitorCfgEntry 3 }

    hwCmtsUsSpectrumMonitorSampleTime OBJECT-TYPE
            SYNTAX INTEGER{ms100(1), 
                           ms200(2),
                           ms300(3),
                           ms400(4),
                           ms500(5),
                           ms600(6),
                           ms700(7),
                           ms800(8),
                           ms900(9),
                           ms1000(10),
                           invalid(-1)}
            MAX-ACCESS read-write
            STATUS current
            DESCRIPTION
                "Indicates the upstream frequency spectrum scanning period.
                 Default: ms100(1).
                 Options:
                 1. ms100(1)    - Sets the upstream frequency spectrum scanning period to 100ms
                 2. ms200(2)    - Sets the upstream frequency spectrum scanning period to 200ms
                 3. ms300(3)    - Sets the upstream frequency spectrum scanning period to 300ms
                 4. ms400(4)    - Sets the upstream frequency spectrum scanning period to 400ms
                 5. ms500(5)    - Sets the upstream frequency spectrum scanning period to 500ms
                 6. ms600(6)    - Sets the upstream frequency spectrum scanning period to 600ms
                 7. ms700(7)    - Sets the upstream frequency spectrum scanning period to 700ms
                 8. ms800(8)    - Sets the upstream frequency spectrum scanning period to 800ms
                 9. ms900(9)    - Sets the upstream frequency spectrum scanning period to 900ms
                 10. ms1000(10) - Sets the upstream frequency spectrum scanning period to 1000ms
                 11. invalid(-1) - Getting is invalid
                "
         ::= { hwCmtsUsSpectrumMonitorCfgEntry 4 }
         
    hwCmtsUsSpectrumMonitorFrequencyStart OBJECT-TYPE
            SYNTAX      Integer32(-1|0..204000000)
            UNITS   "Hz"
            MAX-ACCESS read-write
            STATUS current
            DESCRIPTION
                "Indicates the start frequency for upstream spectrum scanning.
                -1 represent that the upstream spectrum configuration of start frequency has invalid configuration data.
                 Default: 0
                "
         ::= { hwCmtsUsSpectrumMonitorCfgEntry 5 }
 
    hwCmtsUsSpectrumMonitorFrequencyEnd OBJECT-TYPE
            SYNTAX      Integer32(-1|0..204000000)
            UNITS   "Hz"
            MAX-ACCESS read-write
            STATUS current
            DESCRIPTION
                "Indicates the end frequency for upstream spectrum scanning.
                 Requirement: The difference between the end frequency and the start frequency must be greater than the upstream frequency spectrum scanning resolution.
                 -1 represent that the upstream spectrum configuration of end frequency has invalid configuration data.
                 Default: 102000000
                "
         ::= { hwCmtsUsSpectrumMonitorCfgEntry 6 }
         
    hwCmtsUsSpectrumMonitorSampleStart OBJECT-TYPE
          SYNTAX  Integer32(-1|0..204000000)
          MAX-ACCESS  read-only
          STATUS  current
          DESCRIPTION
                "
                Indicates the start frequency for the upstream spectrum scanning.
                -1 represent that the upstream spectrum scanning mode is disable or the collected data have not been uploaded.
                "
          ::= { hwCmtsUsSpectrumMonitorCfgEntry 7 }
          
     hwCmtsUsSpectrumMonitorUsSgId OBJECT-TYPE
          SYNTAX  Integer32(1..2)
          MAX-ACCESS  read-write
          STATUS  current
          DESCRIPTION
                "
                Indicates the US-SG-ID for the upstream spectrum scanning.
                Default: 1
                "
          ::= { hwCmtsUsSpectrumMonitorCfgEntry 8 }
          
     hwCmtsUsSpectrumMonitorUsChannelId OBJECT-TYPE
          SYNTAX  Integer32(1..16)
          MAX-ACCESS  read-write
          STATUS  current
          DESCRIPTION
                "
                Indicates the upstream channel ID for the constellation scanning.
                Default: 1
                "
          ::= { hwCmtsUsSpectrumMonitorCfgEntry 9 }

    hwCmtsUsSpectrumMonitorFrequencyList OBJECT-TYPE
            SYNTAX      OCTET STRING (SIZE(0 | 1..8000))
            UNITS   "Hz"
            MAX-ACCESS read-write
            STATUS current
            DESCRIPTION
                "The frequency list for the upstream spectrum scanning.
                 It can contain as most as 50 frequencies.
                 Every 10 octets represent a frequency,
                 (,) used to indicate a separation of the different frequencies.
                "
         ::= { hwCmtsUsSpectrumMonitorCfgEntry 10 }

    hwCmtsUsSpectrumMonitorReportPeriod OBJECT-TYPE
            SYNTAX  INTEGER{ms5000(1),ms500(2),invalid(-1)}
            MAX-ACCESS read-write
            STATUS current
            DESCRIPTION
                "Indicates the upstream frequency spectrum report period mode.
                Default:ms5000(1)
                Options:
                1. ms5000(1) -Upload data in 5000ms
                2. ms500(2) -Upload data in 500ms
                3. invalid(-1) -Invalid               
                "
         ::= { hwCmtsUsSpectrumMonitorCfgEntry 11 }
    --Table hwCmtsUsSpectrumMonitorCfgTable end
    
    --Table hwCmtsUsSpectrumMonitorInfoTable begin
    hwCmtsUsSpectrumMonitorInfoTable OBJECT-TYPE
        SYNTAX     SEQUENCE OF HwCmtsUsSpectrumMonitorInfoEntry
        MAX-ACCESS not-accessible
        STATUS     current
        DESCRIPTION
            "
            Indicates obtaining upstream spectrum scanning data.
            The indexes of this table are cable port ifIndex, hwCmtsUsSpectrumMonitorDataType and hwCmtsUsSpectrumMonitorDataID.
            "
        ::= { hwCmtsAccessObject 57 }

    hwCmtsUsSpectrumMonitorInfoEntry OBJECT-TYPE
        SYNTAX     HwCmtsUsSpectrumMonitorInfoEntry
        MAX-ACCESS not-accessible
        STATUS     current
        DESCRIPTION
            "
            Indicates obtaining upstream spectrum scanning data.
            The indexes of this entry are cable port ifIndex, hwCmtsUsSpectrumMonitorDataType and hwCmtsUsSpectrumMonitorDataID.
            "
        INDEX       { ifIndex, hwCmtsUsSpectrumMonitorDataType, hwCmtsUsSpectrumMonitorDataID }
        ::= { hwCmtsUsSpectrumMonitorInfoTable 1 }

    HwCmtsUsSpectrumMonitorInfoEntry ::=
        SEQUENCE {
                 hwCmtsUsSpectrumMonitorDataType INTEGER,
                 hwCmtsUsSpectrumMonitorDataID Integer32,
                 hwCmtsUsSpectrumMonitorStartTime DateAndTime,
                 hwCmtsUsSpectrumMonitorContent OCTET STRING,
                 hwCmtsUsSpectrumMonitoReportInterval Integer32,
                 hwCmtsUsSpectrumMonitorCollectInterval Integer32
        }
    
    hwCmtsUsSpectrumMonitorDataType OBJECT-TYPE
            SYNTAX  INTEGER{noise(1),carrier(2),freeRunning(3)}
            MAX-ACCESS not-accessible
            STATUS current
            DESCRIPTION
                "Indicates the upstream spectrum scanning data type.
                Options:
                1. noise(1) -Scanning noise frequency spectrum
                2. carrier(2) -Scanning carrier frequency spectrum
                3. freeRunning(3) -Scanning noise or carrier frequency spectrum
                "
         ::= { hwCmtsUsSpectrumMonitorInfoEntry 1 }
        
    hwCmtsUsSpectrumMonitorDataID OBJECT-TYPE
            SYNTAX  Integer32(1..32)
            MAX-ACCESS not-accessible
            STATUS current
            DESCRIPTION
                "Indicates the upstream spectrum scanning data ID.
                "
         ::= { hwCmtsUsSpectrumMonitorInfoEntry 2 }
     
    hwCmtsUsSpectrumMonitorStartTime OBJECT-TYPE
            SYNTAX  DateAndTime
            MAX-ACCESS read-only
            STATUS current
            DESCRIPTION
                "Indicates the time when the upstream spectrum scanning starts.
                "
         ::= { hwCmtsUsSpectrumMonitorInfoEntry 3 }

    hwCmtsUsSpectrumMonitorContent OBJECT-TYPE
            SYNTAX  OCTET STRING(SIZE (0|1..8000))
            MAX-ACCESS read-only
            STATUS current
            DESCRIPTION
                "Indicates the upstream spectrum scanning data.
                "
         ::= { hwCmtsUsSpectrumMonitorInfoEntry 4 }
         
    hwCmtsUsSpectrumMonitoReportInterval OBJECT-TYPE
            SYNTAX      Integer32(-1|0..65535)
            MAX-ACCESS read-only
            STATUS current
            DESCRIPTION
                "Indicates the number of upstream spectrum scanning report times.
                 -1 represent that the corresponding mode of upstream spectrum is disable, or there is no reported data.
                "
         ::= { hwCmtsUsSpectrumMonitorInfoEntry 5 }
 
    hwCmtsUsSpectrumMonitorCollectInterval OBJECT-TYPE
            SYNTAX      Integer32(-1|0..4)
            MAX-ACCESS read-only
            STATUS current
            DESCRIPTION
                "Indicates the number of upstream spectrum scanning data collection reports within a period.
                 -1 represent that the corresponding mode of upstream spectrum is disable, or the period for collection report is not timeout.
                "
         ::= { hwCmtsUsSpectrumMonitorInfoEntry 6 }
     
    --Table hwCmtsUsSpectrumMonitorInfoTable end

    --Table hwCmtsUsConstellationInfoTable begin
    hwCmtsUsConstellationInfoTable OBJECT-TYPE
        SYNTAX     SEQUENCE OF HwCmtsUsConstellationInfoEntry
        MAX-ACCESS not-accessible
        STATUS     current
        DESCRIPTION
            "
            Indicates obtaining collected data about the constellation diagram.
            The indexes of this table are cable port ifIndex and hwCmtsUsConstellationDataID.
            "
        ::= { hwCmtsAccessObject 58 }

    hwCmtsUsConstellationInfoEntry OBJECT-TYPE
        SYNTAX     HwCmtsUsConstellationInfoEntry
        MAX-ACCESS not-accessible
        STATUS     current
        DESCRIPTION
            "
            Indicates obtaining collected data about the constellation diagram.
            The indexes of this entry are cable port ifIndex and hwCmtsUsConstellationDataID.
            "
        INDEX       { ifIndex, hwCmtsUsConstellationDataID }
        ::= { hwCmtsUsConstellationInfoTable 1 }

    HwCmtsUsConstellationInfoEntry ::=
        SEQUENCE {
                 hwCmtsUsConstellationDataID Integer32,
                 hwCmtsUsConstellationStartTime DateAndTime,
                 hwCmtsUsConstellationMac MacAddress,
                 hwCmtsUsConstellationPreEqualMER Integer32,
                 hwCmtsUsConstellationMER Integer32,
                 hwCmtsUsConstellationMERSample Integer32,
                 hwCmtsUsConstellationContent OCTET STRING,
                 hwCmtsUsConstellationReportInterval Integer32,
                 hwCmtsUsConstellationCollectInterval Integer32
        }
        
    hwCmtsUsConstellationDataID OBJECT-TYPE
            SYNTAX  Integer32(1..16)
            MAX-ACCESS not-accessible
            STATUS current
            DESCRIPTION
                "Indicates the constellation diagram data collection ID.
                "
         ::= { hwCmtsUsConstellationInfoEntry 1 }
   
    hwCmtsUsConstellationStartTime OBJECT-TYPE
            SYNTAX  DateAndTime
            MAX-ACCESS read-only
            STATUS current
            DESCRIPTION
                "Indicates the time when the constellation diagram data collection starts.
                "
         ::= { hwCmtsUsConstellationInfoEntry 2 }
     
    hwCmtsUsConstellationMac OBJECT-TYPE
            SYNTAX  MacAddress
            MAX-ACCESS read-only
            STATUS obsolete
            DESCRIPTION
                "Indicates the MAC address of the constellation diagram sampling.
                "
         ::= { hwCmtsUsConstellationInfoEntry 3 }

    hwCmtsUsConstellationPreEqualMER OBJECT-TYPE
            SYNTAX  Integer32(-1|1..2147483647)
            UNITS   "0.1dB"
            MAX-ACCESS read-only
            STATUS obsolete
            DESCRIPTION
                "Indicates the MER before equalization.
                 -1 represent that the corresponding mode of upstream spectrum is disable, or the period for collection report is not timeout.
                "
         ::= { hwCmtsUsConstellationInfoEntry 4 }
         
    hwCmtsUsConstellationMER OBJECT-TYPE
            SYNTAX      Integer32(-1|1..2147483647)
            UNITS   "0.1dB"
            MAX-ACCESS read-only
            STATUS obsolete
            DESCRIPTION
                "Indicates the MER after equalization.
                 -1 represent that the corresponding mode of upstream spectrum is disable, or the period for collection report is not timeout.
                "
         ::= { hwCmtsUsConstellationInfoEntry 5 }
 
    hwCmtsUsConstellationMERSample OBJECT-TYPE
            SYNTAX      Integer32(-1|1..4096)
            MAX-ACCESS read-only
            STATUS obsolete
            DESCRIPTION
                "Indicates the number of MER sampling points.
                 -1 represent that the corresponding mode of upstream spectrum is disable, or the period for collection report is not timeout.
                "
         ::= { hwCmtsUsConstellationInfoEntry 6 }

    hwCmtsUsConstellationContent OBJECT-TYPE
            SYNTAX      OCTET STRING (SIZE(0 | 1..8000))
            MAX-ACCESS read-only
            STATUS current
            DESCRIPTION
                "Indicates collected data of the constellation diagram.
                "
         ::= { hwCmtsUsConstellationInfoEntry 7 }

    hwCmtsUsConstellationReportInterval OBJECT-TYPE
            SYNTAX      Integer32(-1|0..65535)
            MAX-ACCESS read-only
            STATUS current
            DESCRIPTION
                "Indicates the number of constellation diagram report times.
                 -1 represent that the corresponding mode of upstream spectrum is disable, or there is no report data.
                "
         ::= { hwCmtsUsConstellationInfoEntry 8 }

    hwCmtsUsConstellationCollectInterval OBJECT-TYPE
            SYNTAX      Integer32(-1|0..4)
            MAX-ACCESS read-only
            STATUS current
            DESCRIPTION
                "Indicates the number of constellation diagram data collection reports within a period.
                 -1 represent that the corresponding mode of upstream spectrum is disable, or the period for collection report is not timeout.
                "
         ::= { hwCmtsUsConstellationInfoEntry 9 }
     
    --Table hwCmtsUsConstellationInfoTable end
    
    --Table hwCmtsCmPnmAttributeTable begin
    
    hwCmtsCmPnmAttributeTable OBJECT-TYPE
        SYNTAX     SEQUENCE OF HwCmtsCmPnmAttributeEntry
        MAX-ACCESS not-accessible
        STATUS     current
        DESCRIPTION
            "
            Indicates the CM PNM severity.
            The index of this table is the number of segments of the CM index list.
            "
        ::= { hwCmtsAccessObject 59  }
        
    hwCmtsCmPnmAttributeEntry OBJECT-TYPE
        SYNTAX     HwCmtsCmPnmAttributeEntry
        MAX-ACCESS not-accessible
        STATUS     current
        DESCRIPTION
            "
            Indicates the CM PNM severity.
            The index of this entry is the number of segments of the CM index list.
            "
        INDEX       { hwCmtsCmPnmGroupIndex }
        ::= { hwCmtsCmPnmAttributeTable 1 }

    HwCmtsCmPnmAttributeEntry ::=
        SEQUENCE {
                 hwCmtsCmPnmGroupIndex  Integer32,
                 hwCmtsCmPnmIndexList   OCTET STRING,
                 hwCmtsCmAttributeSeverityList   OCTET STRING          
        }
        
    hwCmtsCmPnmGroupIndex OBJECT-TYPE
            SYNTAX Integer32 (1..16|2147483647)
            MAX-ACCESS not-accessible
            STATUS current
            DESCRIPTION
                "Indicates the number of segments of the CM index list.                
                 In the set operation, index value is only 2147483647(0x7FFFFFFF).
                 In the query operation, index value is 1..16.      
                "
         ::= { hwCmtsCmPnmAttributeEntry 1 }
   
    hwCmtsCmPnmIndexList OBJECT-TYPE
          SYNTAX  OCTET STRING (SIZE (4..8192))
          MAX-ACCESS  read-write
          STATUS  current
          DESCRIPTION
                "Indicates the CM index list. 
                 One CM index consists of four bytes. For example, to enter CM index 1, enter # 0x00 0x00 0x00 0x01. 
                 To enter multiple CM indexes, enter them one by one. 
                 For example, to enter CM index 1 and CM index 5, enter # 0x00 0x00 0x00 0x01 0x00 0x00 0x00 0x05. 
                 A maximum of 2048 CM indexes can be entered. "
          ::= { hwCmtsCmPnmAttributeEntry 2 }
          
    hwCmtsCmAttributeSeverityList OBJECT-TYPE
          SYNTAX  OCTET STRING (SIZE (1..2048))
          MAX-ACCESS  read-write
          STATUS  current
          DESCRIPTION
                "Indicates the CM PNM severity list. 
                 Each byte represents a CM PNM severity. CM PNM severity IDs are in on-to-one mapping with those in hwCmtsCmPnmIndexList. 
                 For example, to configure the CM PNM severity to 1 for CM index 1 and CM PNM severity to 3 for CM index 5, enter # 0x01 0x03. 
                 A maximum of 2048 CM PNM severities can be entered.
                 The CM PNM severity can be 1: red (1), 2: yellow (2), and 3: green (3)."
          ::= { hwCmtsCmPnmAttributeEntry 3 }  
                         
    --Table hwCmtsCmPnmAttributeTable end
    
    --Table hwCmtsLoadBalanceStatusChannelTable begin
    
    hwCmtsLoadBalanceStatusChannelTable OBJECT-TYPE
        SYNTAX     SEQUENCE OF HwCmtsLoadBalanceStatusChannelEntry
        MAX-ACCESS not-accessible
        STATUS     current
        DESCRIPTION
            "
            Indicates the load balance status on channels.
            The index of this table is ifIndex.
            The ifIndex have two types 
            1. upstream channel ifIndex, include channel type, docsis port index and channel index
            2. downstream channel ifIndex, include channel type, docsis port index and channel index
            "
        ::= { hwCmtsAccessObject 60  }
        
    hwCmtsLoadBalanceStatusChannelEntry OBJECT-TYPE
        SYNTAX     HwCmtsLoadBalanceStatusChannelEntry
        MAX-ACCESS not-accessible
        STATUS     current
        DESCRIPTION
            "
            Indicates the load balance status on channels.
            The index of this entry is ifIndex.
            The ifIndex have two types 
            1. upstream channel ifIndex, include channel type, docsis port index and channel index
            2. downstream channel ifIndex, include channel type, docsis port index and channel index
            "
        INDEX       { ifIndex }
        ::= { hwCmtsLoadBalanceStatusChannelTable 1 }

    HwCmtsLoadBalanceStatusChannelEntry ::=
        SEQUENCE {
                   hwCmtsLoadBalanceStatusMinReservation   Integer32          
        }
        
    hwCmtsLoadBalanceStatusMinReservation OBJECT-TYPE
          SYNTAX  Integer32
          UNITS   "kbps"
          MAX-ACCESS  read-only
          STATUS  current
          DESCRIPTION
               "
               Indicates the sum of the minimum reserved bandwidth of channel.
               -1 represents invalid value."
          ::= { hwCmtsLoadBalanceStatusChannelEntry 1 } 
                         
    --Table hwCmtsLoadBalanceStatusChannelTable end    
    
    --Table hwDocsLoadbal3ResGrpCfgTable begin
        
    hwDocsLoadbal3ResGrpCfgTable OBJECT-TYPE
        SYNTAX     SEQUENCE OF HwDocsLoadbal3ResGrpCfgEntry
        MAX-ACCESS not-accessible
        STATUS     current
        DESCRIPTION
            "Indicates the configuration of restricted load balancing groups.
             The index of this table is docsLoadbal3ResGrpCfgId.
            "
        ::= { hwCmtsAccessObject 61 }
        
    hwDocsLoadbal3ResGrpCfgEntry OBJECT-TYPE
        SYNTAX     HwDocsLoadbal3ResGrpCfgEntry
        MAX-ACCESS not-accessible
        STATUS     current
        DESCRIPTION
            "
             Indicates the configuration of restricted load balancing groups.
             The index of this entry is docsLoadbal3ResGrpCfgId.
            "
        INDEX       { docsLoadbal3ResGrpCfgId }
        ::= { hwDocsLoadbal3ResGrpCfgTable 1 }
    HwDocsLoadbal3ResGrpCfgEntry ::=
        SEQUENCE {
                 hwDocsLoadbal3ResGrpCfgMdCmSgId Unsigned32
                 }
        
    hwDocsLoadbal3ResGrpCfgMdCmSgId OBJECT-TYPE
            SYNTAX Unsigned32(1..2)
            MAX-ACCESS read-write
            STATUS current
            DESCRIPTION
                "Indicates the MAC domain Cable Modem service group ID of Restricted Load Balancing Groups.           
                "
         ::= { hwDocsLoadbal3ResGrpCfgEntry 1 }
 
     
    --Table hwDocsLoadbal3ResGrpCfgTable end
    
    --Table hwDocsIf3CmtsMdUsSgStatTable begin
        
    hwDocsIf3CmtsMdUsSgStatTable OBJECT-TYPE
        SYNTAX     SEQUENCE OF HwDocsIf3CmtsMdUsSgStatEntry
        MAX-ACCESS not-accessible
        STATUS     current
        DESCRIPTION
            "Indicates the traffic statistics of the MAC domain upstream service group.
             The indexes of this table are ifindex and hwDocsIf3CmtsMdUsSgStatId.
            "
        ::= { hwCmtsAccessObject 62 }
    hwDocsIf3CmtsMdUsSgStatEntry OBJECT-TYPE
        SYNTAX     HwDocsIf3CmtsMdUsSgStatEntry
        MAX-ACCESS not-accessible
        STATUS     current
        DESCRIPTION
            "
             Indicates the traffic statistics of the MAC domain upstream service group.
             The indexes of this entry are ifindex and hwDocsIf3CmtsMdUsSgStatId.
            "
        INDEX       { ifIndex,
                      hwDocsIf3CmtsMdUsSgStatId }
        ::= { hwDocsIf3CmtsMdUsSgStatTable 1 }
    HwDocsIf3CmtsMdUsSgStatEntry ::=
        SEQUENCE {
                     hwDocsIf3CmtsMdUsSgStatId   Unsigned32,
                     hwDocsIf3CmtsMdUsSgStatRecvBytes  Counter64
                 }
        
    hwDocsIf3CmtsMdUsSgStatId OBJECT-TYPE
            SYNTAX Unsigned32(1..2)
            MAX-ACCESS not-accessible
            STATUS current
            DESCRIPTION
                "Indicates the MAC domain upstream service group ID.
                "
         ::= { hwDocsIf3CmtsMdUsSgStatEntry 1 }
         
         
    hwDocsIf3CmtsMdUsSgStatRecvBytes OBJECT-TYPE
            SYNTAX Counter64
            MAX-ACCESS read-only
            STATUS current
            DESCRIPTION
                "Indicates the number of bytes received by the MAC domain upstream service group.
                "
         ::= { hwDocsIf3CmtsMdUsSgStatEntry 2 }
 
    --Table hwDocsIf3CmtsMdUsSgStatTable end
    
    
    --Table hwDocsLoadbalanceClassifyStatTable begin
        
    hwDocsLoadbalanceClassifyStatTable OBJECT-TYPE
        SYNTAX     SEQUENCE OF HwDocsLoadbalanceClassifyStatEntry
        MAX-ACCESS not-accessible
        STATUS     current
        DESCRIPTION
            "Indicates the statistics of CM load balance failure list.
             The indexes of this table are ifindex and docsIf3CmtsCmRegStatusId.
            "
        ::= { hwCmtsAccessObject 63 }
        
    hwDocsLoadbalanceClassifyStatEntry OBJECT-TYPE
        SYNTAX     HwDocsLoadbalanceClassifyStatEntry
        MAX-ACCESS not-accessible
        STATUS     current
        DESCRIPTION
            "Indicates the statistics of CM load balance failure list.
             The indexes of this entry are ifindex and docsIf3CmtsCmRegStatusId.
            "
        INDEX       { ifIndex, docsIf3CmtsCmRegStatusId }
        ::= { hwDocsLoadbalanceClassifyStatTable 1 }
    HwDocsLoadbalanceClassifyStatEntry ::=
        SEQUENCE {
                     hwDocsLoadbalanceClassifyStatFailureCount              Counter32,
                     hwDocsLoadbalanceClassifyStatFailureLastTime           DateAndTime,
                     hwDocsLoadbalanceClassifyStatFailureLastReasonText     Gauge32,
                     hwDocsLoadbalanceClassifyStatFailureUsChannelListSrc   OCTET STRING,
                     hwDocsLoadbalanceClassifyStatFailureUsChannelListDst   OCTET STRING,
                     hwDocsLoadbalanceClassifyStatFailureDsChannelListSrc   OCTET STRING,
                     hwDocsLoadbalanceClassifyStatFailureDsChannelListDst   OCTET STRING,
                     hwDocsLoadbalanceClassifyStatFailureClear              INTEGER
                 }
        
    hwDocsLoadbalanceClassifyStatFailureCount OBJECT-TYPE
            SYNTAX Counter32
            MAX-ACCESS read-only
            STATUS current
            DESCRIPTION
                "Indicates the failure count of CM load balance. The maximum value is 65535.
                 If the number of load balancing failures reaches 65535, the number will not increase if another failure occurs.
                 4294967295 represents invalid value. 
                "
         ::= { hwDocsLoadbalanceClassifyStatEntry 1 }
         
         
    hwDocsLoadbalanceClassifyStatFailureLastTime OBJECT-TYPE
            SYNTAX DateAndTime
            MAX-ACCESS read-only
            STATUS current
            DESCRIPTION
                "Indicates the last failure time of CM load balancing."
         ::= { hwDocsLoadbalanceClassifyStatEntry 2 }
         
    hwDocsLoadbalanceClassifyStatFailureLastReasonText OBJECT-TYPE
            SYNTAX Gauge32(0..65535)
            MAX-ACCESS read-only
            STATUS current
            DESCRIPTION
                "Indicates the failure reason of CM load balance.
                 65535 represents invalid value.
                "
         ::= { hwDocsLoadbalanceClassifyStatEntry 3 }
         
    hwDocsLoadbalanceClassifyStatFailureUsChannelListSrc OBJECT-TYPE
            SYNTAX OCTET STRING (SIZE (2))
            MAX-ACCESS read-only
            STATUS current
            DESCRIPTION
                "Indicates the upstream source channel when CM load balance fails.
                 Each bit indicates a channel. For example, bit 1 indicates channel 1.
                 All zeros represents invalid value.
                "
         ::= { hwDocsLoadbalanceClassifyStatEntry 4 }
         
    hwDocsLoadbalanceClassifyStatFailureUsChannelListDst OBJECT-TYPE
            SYNTAX OCTET STRING (SIZE (2))
            MAX-ACCESS read-only
            STATUS current
            DESCRIPTION
                "Indicates the upstream destination channel when CM load balance fails.
                 Each bit indicates a channel. For example, bit 1 indicates channel 1.
                 All zeros represents invalid value.
                "
         ::= { hwDocsLoadbalanceClassifyStatEntry 5 }
         
    hwDocsLoadbalanceClassifyStatFailureDsChannelListSrc OBJECT-TYPE
            SYNTAX OCTET STRING (SIZE (12))
            MAX-ACCESS read-only
            STATUS current
            DESCRIPTION
                "Indicates the downstream source channel when CM load balance fails.
                 Each bit indicates a channel. For example, bit 1 indicates channel 1.
                 All zeros represents invalid value.
                "
         ::= { hwDocsLoadbalanceClassifyStatEntry 6 }
         
    hwDocsLoadbalanceClassifyStatFailureDsChannelListDst OBJECT-TYPE
            SYNTAX OCTET STRING (SIZE (12))
            MAX-ACCESS read-only
            STATUS current
            DESCRIPTION
                "Indicates the downstream destination channel when CM load balance fails.
                 Each bit indicates a channel. For example, bit 1 indicates channel 1.
                 All zeros represents invalid value.
                "
         ::= { hwDocsLoadbalanceClassifyStatEntry 7 }
         
    hwDocsLoadbalanceClassifyStatFailureClear OBJECT-TYPE
            SYNTAX INTEGER
            {
              clear(1),
              invalid(-1)
            }
            MAX-ACCESS read-create
            STATUS current
            DESCRIPTION
                "Indicates the clear of CM load balance statistics failure list.
                 The index of docsIf3CmtsCmRegStatusId is invalid when users use this node to clean load 
                 balancing failures of CMs. Users can only use this node 
                 to clear load balancing failures of CMs based on ports.
                 Options:
                 1. clear(1)    - Clear the CM load balance statistics failure list
                 2. invalid(-1) - Invalid value
                "
         ::= { hwDocsLoadbalanceClassifyStatEntry 8 }
 
    --Table hwDocsLoadbalanceClassifyStatTable end
    
    --Table hwCmtsUsInfoCollectTable begin
        
    hwCmtsUsInfoCollectTable OBJECT-TYPE
        SYNTAX     SEQUENCE OF HwCmtsUsInfoCollectEntry
        MAX-ACCESS not-accessible
        STATUS     current
        DESCRIPTION
            "Indicates the mask configuration of upstream channel information collecting.
            The index of this table is hwCmtsUsInfoCollectFileType.
            "
        ::= { hwCmtsAccessObject 64 }
    hwCmtsUsInfoCollectEntry OBJECT-TYPE
        SYNTAX     HwCmtsUsInfoCollectEntry
        MAX-ACCESS not-accessible
        STATUS     current
        DESCRIPTION
            "Indicates the mask configuration of upstream channel information collecting.
             The index of this entry is hwCmtsUsInfoCollectFileType.
            "
        INDEX       { hwCmtsUsInfoCollectFileType }
        ::= { hwCmtsUsInfoCollectTable 1 }
    HwCmtsUsInfoCollectEntry ::=
        SEQUENCE {
                     hwCmtsUsInfoCollectFileType   INTEGER,
                     hwCmtsUsInfoCollectDataItem   BITS
                 }
        
    hwCmtsUsInfoCollectFileType OBJECT-TYPE
            SYNTAX  INTEGER{spectrumFile(1),cmcPerformanceFile(2),historySpectrumFile(3)}
            MAX-ACCESS not-accessible
            STATUS current
            DESCRIPTION
                "Indicates file type of upstream channel information collecting.
                Options:
                1. spectrumFile(1) -spectrum file
                2. cmcPerformanceFile(2) -cmc performance file
                3. historySpectrumFile(3)-history spectrum file
                "
         ::= { hwCmtsUsInfoCollectEntry 1 }
         
         
    hwCmtsUsInfoCollectDataItem OBJECT-TYPE
            SYNTAX  BITS 
            {
              preConstellation(0),
              mer(1),
              burstPower(2),
              fec(3),
              equalization(4),
              impulseNoiseSymbol(5),
              realAmplitude(6),
              statAmplitude(7),
              thresholdAmplitude(8)
            }
            MAX-ACCESS read-write
            STATUS current
            DESCRIPTION
                "Indicates the mask of upstream channel information collecting.
                "
         ::= { hwCmtsUsInfoCollectEntry 2 }
 
    --Table hwCmtsUsInfoCollectTable end 
    
    --Table hwCmtsUsCmcPerformanceCfgTable begin
    hwCmtsUsCmcPerformanceCfgTable OBJECT IDENTIFIER 
         ::= { hwCmtsAccessObject  65}

    hwCmtsUsCmcPerformanceSwitch  OBJECT-TYPE  
          SYNTAX  INTEGER {enable(1),disable(2)}
          MAX-ACCESS  read-write
          STATUS  current
          DESCRIPTION
                "Indicates the switch of upstream channel cmc performance information collecting function. 
                Options:
                1. enable(1)     -Enable the upstream channel cmc performance information collecting function
                2. disable(2)    -Disable the upstream channel cmc performance information collecting function
                Default: disable(2)
                "
          ::= { hwCmtsUsCmcPerformanceCfgTable 1 }
          
    hwCmtsUsCmcPerformanceUploadTime  OBJECT-TYPE
          SYNTAX  Integer32 (120..840)
          UNITS   "seconds"
          MAX-ACCESS  read-write  
          STATUS  current  
          DESCRIPTION
                "The time for uploading files, relative time, indicates the relative time to the 15 whole minutes time.
                "
          DEFVAL  {120}
          ::= { hwCmtsUsCmcPerformanceCfgTable 2 } 

    --Table hwCmtsUsCmcPerformanceCfgTable end
    
    -- Table hwCmtsIpReturnUsChannelTable Begin
    hwCmtsIpReturnUsChannelTable OBJECT-TYPE
          SYNTAX     SEQUENCE OF HwCmtsIpReturnUsChannelEntry
          MAX-ACCESS not-accessible
          STATUS     current
          DESCRIPTION
               "This table describes the ip return attributes of upstream channels.
               The indexes of this table are ifIndex and hwCmtsIpReturnUsChannelId.
               "
          ::= { hwCmtsAccessObject 66 }

    hwCmtsIpReturnUsChannelEntry OBJECT-TYPE
          SYNTAX     HwCmtsIpReturnUsChannelEntry
          MAX-ACCESS not-accessible
          STATUS     current
          DESCRIPTION
               "This table describes the ip return attributes of upstream channels.
               The indexes of this entry are ifIndex and hwCmtsIpReturnUsChannelId.
               "
          INDEX       { ifIndex, hwCmtsIpReturnUsChannelId }
          ::= { hwCmtsIpReturnUsChannelTable 1 }

     HwCmtsIpReturnUsChannelEntry ::=
          SEQUENCE {
                    hwCmtsIpReturnUsChannelId     Integer32,
                    hwCmtsIpReturnUsChannelFrequencyConfig Integer32,
                    hwCmtsIpReturnUsChannelFreqWidthConfig INTEGER,
                    hwCmtsIpReturnUsChannelModeConfig INTEGER,
                    hwCmtsIpReturnUsChannelAdminStatus        INTEGER,
                    hwCmtsIpReturnUsChannelFrequencyStatus Integer32,
                    hwCmtsIpReturnUsChannelFreqWidthStatus      INTEGER,
                    hwCmtsIpReturnUsChannelOperStatus    INTEGER,
                    hwCmtsIpReturnUsChannelModeStatus    INTEGER,
                    hwCmtsIpReturnUsChannelRowStatus     RowStatus,
                    hwCmtsIpReturnUsModulationTechConfig INTEGER,
                    hwCmtsIpReturnUsModulationTechStatus INTEGER,
                    hwCmtsIpReturnUsBitRateConfig INTEGER,
                    hwCmtsIpReturnUsBitRateStatus INTEGER,
                    hwCmtsIpReturnUsChannelRxPowerConfig Integer32,
                    hwCmtsIpReturnUsChannelRxPowerStatus Integer32                    
                   }

    hwCmtsIpReturnUsChannelId OBJECT-TYPE
          SYNTAX     Integer32(1)
          MAX-ACCESS not-accessible
          STATUS     current
          DESCRIPTION
                "Indicates the channel id, this leaf is essential.
              DEFVAL      { 1 }"
          ::= { hwCmtsIpReturnUsChannelEntry 1 }

    hwCmtsIpReturnUsChannelFrequencyConfig OBJECT-TYPE
          SYNTAX      Integer32(-1|5000000..204000000)
          MAX-ACCESS  read-write
          STATUS  current
          DESCRIPTION
                "Indicates the channel frequency.
                -1 represent invalid value."
          ::= { hwCmtsIpReturnUsChannelEntry 2 }

    hwCmtsIpReturnUsChannelFreqWidthConfig OBJECT-TYPE
          SYNTAX     INTEGER{hz400K(1),hz500K(2),hz600K(3)}
          MAX-ACCESS read-write
          STATUS     current
          DESCRIPTION
                "
                Indicates the channel frequency bandwidth.
                Options:
                1. hz400K(1) - 400KHz     
                2. hz500K(2) - 500KHz
                3. hz600K(3) - 600KHz     
                "
              DEFVAL      { hz400K }
          ::= { hwCmtsIpReturnUsChannelEntry 3 }
    
    hwCmtsIpReturnUsChannelModeConfig OBJECT-TYPE
          SYNTAX     INTEGER{transponder(1)}
          MAX-ACCESS read-write
          STATUS     current
          DESCRIPTION
                "
                Indicates the channel mode.
                Options:
                1. transponder(1) - transponder mode
                "
              DEFVAL      { transponder }
          ::= { hwCmtsIpReturnUsChannelEntry 4 }

    hwCmtsIpReturnUsChannelAdminStatus OBJECT-TYPE
          SYNTAX     INTEGER{disable(1),enable(2)}
          MAX-ACCESS read-write
          STATUS     current
          DESCRIPTION
                "
                Indicates the administrative status of  IP return upstream channel.
                Options:
                1. disable(1) - disable IP return upstream channel
                2. enable(2) - enable IP return upstream channel
                "
              DEFVAL      { disable }
          ::= { hwCmtsIpReturnUsChannelEntry 5 }

    hwCmtsIpReturnUsChannelFrequencyStatus OBJECT-TYPE
          SYNTAX     Integer32(-1|5000000..204000000)
          MAX-ACCESS read-only
          STATUS     current
          DESCRIPTION
                "Indicates the channel frequency.
                -1 represent invalid value."
          ::= { hwCmtsIpReturnUsChannelEntry 6 }

    hwCmtsIpReturnUsChannelFreqWidthStatus OBJECT-TYPE
          SYNTAX     INTEGER{hz400K(1),hz500K(2),hz600K(3),invalid(-1)}
          MAX-ACCESS read-only
          STATUS     current
          DESCRIPTION
                "
                Indicates the channel frequency bandwidth.
                Options:
                1. hz400K(1) - 400KHz     
                2. hz500K(2) - 500KHz
                3. hz600K(3) - 600KHz      
                4. invalid(-1) - invalid value      
                "
          ::= { hwCmtsIpReturnUsChannelEntry 7 }

    hwCmtsIpReturnUsChannelOperStatus OBJECT-TYPE
          SYNTAX     INTEGER{down(1),up(2),invalid(-1)}
          MAX-ACCESS read-only
          STATUS     current
          DESCRIPTION
                "Indicates the operational status of IP return upstream channel .
                 Options:
                 1. down(1) - down status
                 2. up(2) - up status
                 3. invalid(-1) - invalid value"
          ::= { hwCmtsIpReturnUsChannelEntry 8 }

    hwCmtsIpReturnUsChannelModeStatus OBJECT-TYPE
          SYNTAX     INTEGER{transponder(1),invalid(-1)}
          MAX-ACCESS read-only
          STATUS     current
          DESCRIPTION
                "
                Indicates the channel mode.
                Options:
                1. transponder(1) - transponder mode
                2. invalid(-1) - invalid value
                "
          ::= { hwCmtsIpReturnUsChannelEntry 9 }

    hwCmtsIpReturnUsChannelRowStatus OBJECT-TYPE
          SYNTAX     RowStatus
          MAX-ACCESS read-create
          STATUS     current
          DESCRIPTION
                "Indicates the row status to create or delete a channel ip return configuration.
                Options:
                1. active(1)      -indicates modify the specific ip return configuration.
                2. createAndGo(4) -indicates creating an ip return configuration.
                3. destroy(6)     -indicates deleting the specific ip return configuration.
                "
          ::= { hwCmtsIpReturnUsChannelEntry 10 }
          
    hwCmtsIpReturnUsModulationTechConfig OBJECT-TYPE
          SYNTAX     INTEGER{fsk50KHz(1),fsk67KHz(2),fsk80KHz(3)}
          MAX-ACCESS read-write
          STATUS     current
          DESCRIPTION
                "
                Indicates the channel modulation technique.
                Options:
                1. fsk50KHz(1) - FSK,signal +/-50KHz 
                2. fsk67KHz(2) - FSK,signal +/-67KHz                     
                3. fsk80KHz(3) - FSK,signal +/-80KHz      
                "
              DEFVAL      { fsk67KHz }
          ::= { hwCmtsIpReturnUsChannelEntry 11 } 
                  
    hwCmtsIpReturnUsModulationTechStatus OBJECT-TYPE
          SYNTAX     INTEGER{fsk50KHz(1),fsk67KHz(2),fsk80KHz(3),invalid(-1)}
          MAX-ACCESS read-only
          STATUS     current
          DESCRIPTION
                "
                Indicates the channel modulation technique.
                Options:                    
                1. fsk50KHz(1) - FSK,signal +/-50KHz 
                2. fsk67KHz(2) - FSK,signal +/-67KHz                     
                3. fsk80KHz(3) - FSK,signal +/-80KHz    
                4. invalid(-1) - invalid value      
                "
          ::= { hwCmtsIpReturnUsChannelEntry 12 }   
          
    hwCmtsIpReturnUsBitRateConfig OBJECT-TYPE
          SYNTAX     INTEGER{bitRate192(1),bitRate384(2)}
          MAX-ACCESS read-write
          STATUS     current
          DESCRIPTION
                "
                Indicates the channel bit rate.
                Options:
                1. bitRate192(1) - 19.2kbps  
                2. bitRate384(2) - 38.4kbps    
                "
              DEFVAL      { bitRate384 }
          ::= { hwCmtsIpReturnUsChannelEntry 13 } 
                  
    hwCmtsIpReturnUsBitRateStatus OBJECT-TYPE
          SYNTAX     INTEGER{bitRate192(1),bitRate384(2),invalid(-1)}
          MAX-ACCESS read-only
          STATUS     current
          DESCRIPTION
                "
                Indicates the channel bit rate.
                Options:
                1. bitRate192(1) - 19.2kbps  
                2. bitRate384(2) - 38.4kbps    
                3. invalid(-1) - invalid value      
                "
          ::= { hwCmtsIpReturnUsChannelEntry 14 } 

    hwCmtsIpReturnUsChannelRxPowerConfig OBJECT-TYPE
          SYNTAX      Integer32
          UNITS       "0.1dBmV"
          MAX-ACCESS  read-write
          STATUS  current
          DESCRIPTION
                "Indicates the received power.
                Value range: -2147483647|-200..200.
                "
          DEFVAL      { 60 }
          ::= { hwCmtsIpReturnUsChannelEntry 15 }

    hwCmtsIpReturnUsChannelRxPowerStatus OBJECT-TYPE
          SYNTAX      Integer32
          UNITS       "0.1dBmV"
          MAX-ACCESS  read-only
          STATUS  current
          DESCRIPTION
                "Indicates the received power.
                Value range: -2147483647|-200..200.
                "
          ::= { hwCmtsIpReturnUsChannelEntry 16 }

  -- Table hwCmtsIpReturnUsChannelTable End
  
  -- Table hwCmtsIpReturnDsChannelTable Begin
    hwCmtsIpReturnDsChannelTable OBJECT-TYPE
          SYNTAX     SEQUENCE OF HwCmtsIpReturnDsChannelEntry
          MAX-ACCESS not-accessible
          STATUS     current
          DESCRIPTION
               "This table describes the ip return attributes of downstream channels.
               The indexes of this table are ifIndex and hwCmtsIpReturnDsChannelId.
               "
          ::= { hwCmtsAccessObject 67 }

    hwCmtsIpReturnDsChannelEntry OBJECT-TYPE
          SYNTAX     HwCmtsIpReturnDsChannelEntry
          MAX-ACCESS not-accessible
          STATUS     current
          DESCRIPTION
               "This table describes the ip return attributes of downstream channels.
               The indexes of this entry are ifIndex and hwCmtsIpReturnDsChannelId.
               "
          INDEX       { ifIndex, hwCmtsIpReturnDsChannelId }
          ::= { hwCmtsIpReturnDsChannelTable 1 }

    HwCmtsIpReturnDsChannelEntry ::=
          SEQUENCE {
                    hwCmtsIpReturnDsChannelId     Integer32,
                    hwCmtsIpReturnDsChannelFrequencyConfig Integer32,
                    hwCmtsIpReturnDsChannelFreqWidthConfig INTEGER,
                    hwCmtsIpReturnDsChannelModeConfig INTEGER,
                    hwCmtsIpReturnDsChannelAdminStatus        INTEGER,
                    hwCmtsIpReturnDsChannelFrequencyStatus Integer32,
                    hwCmtsIpReturnDsChannelFreqWidthStatus      INTEGER,
                    hwCmtsIpReturnDsChannelOperStatus    INTEGER,
                    hwCmtsIpReturnDsChannelModeStatus    INTEGER,
                    hwCmtsIpReturnDsChannelRowStatus     RowStatus,
                    hwCmtsIpReturnDsChannelTxPowerConfig Integer32,
                    hwCmtsIpReturnDsChannelTxPowerStatus Integer32,
                    hwCmtsIpReturnDsModulationTechConfig INTEGER,
                    hwCmtsIpReturnDsModulationTechStatus INTEGER,
                    hwCmtsIpReturnDsBitRateConfig INTEGER,
                    hwCmtsIpReturnDsBitRateStatus INTEGER
                   }

    hwCmtsIpReturnDsChannelId OBJECT-TYPE
          SYNTAX     Integer32(1)
          MAX-ACCESS not-accessible
          STATUS     current
          DESCRIPTION
                "Indicates the channel id.
              DEFVAL      { 1 }"
          ::= { hwCmtsIpReturnDsChannelEntry 1 }

    hwCmtsIpReturnDsChannelFrequencyConfig OBJECT-TYPE
          SYNTAX      Integer32(-1|54000000..204000000|258000000..300000000)
          MAX-ACCESS  read-write
          STATUS  current
          DESCRIPTION
                "Indicates the channel frequency.
                -1 represent invalid value."
          ::= { hwCmtsIpReturnDsChannelEntry 2 }

    hwCmtsIpReturnDsChannelFreqWidthConfig OBJECT-TYPE
          SYNTAX     INTEGER{hz400K(1),hz500K(2),hz600K(3)}
          MAX-ACCESS read-write
          STATUS     current
          DESCRIPTION
                "
                Indicates the channel frequency bandwidth.
                Options:
                1. hz400K(1) - 400KHz     
                2. hz500K(2) - 500KHz     
                3. hz600K(3) - 600KHz    
                "
              DEFVAL      { hz400K }
          ::= { hwCmtsIpReturnDsChannelEntry 3 }
    
    hwCmtsIpReturnDsChannelModeConfig OBJECT-TYPE
          SYNTAX     INTEGER{transponder(1)}
          MAX-ACCESS read-write
          STATUS     current
          DESCRIPTION
                "                
                Indicates the channel mode.
                Options:
                1. transponder(1) - transponder mode
                "
              DEFVAL      { transponder }
          ::= { hwCmtsIpReturnDsChannelEntry 4 }

    hwCmtsIpReturnDsChannelAdminStatus OBJECT-TYPE
          SYNTAX     INTEGER{disable(1),enable(2)}
          MAX-ACCESS read-write
          STATUS     current
          DESCRIPTION
                "
                Indicates the administrative status of  IP return upstream channel.
                Options:
                1. disable(1) - disable IP return upstream channel
                2. enable(2) - enable IP return upstream channel
                "
              DEFVAL      { disable }
          ::= { hwCmtsIpReturnDsChannelEntry 5 }

    hwCmtsIpReturnDsChannelFrequencyStatus OBJECT-TYPE
          SYNTAX     Integer32(-1|54000000..204000000|258000000..300000000)
          MAX-ACCESS read-only
          STATUS     current
          DESCRIPTION
                "Indicates the channel frequency.
                -1 represent invalid value."
          ::= { hwCmtsIpReturnDsChannelEntry 6 }

    hwCmtsIpReturnDsChannelFreqWidthStatus OBJECT-TYPE
          SYNTAX     INTEGER{hz400K(1),hz500K(2),hz600K(3),invalid(-1)}
          MAX-ACCESS read-only
          STATUS     current
          DESCRIPTION
                "
                Indicates the channel frequency bandwidth.
                Options:
                1. hz400K(1) - 400KHz     
                2. hz500K(2) - 500KHz     
                3. hz600K(3) - 600KHz    
                4. invalid(-1) - invalid value      
                "
          ::= { hwCmtsIpReturnDsChannelEntry 7 }

    hwCmtsIpReturnDsChannelOperStatus OBJECT-TYPE
          SYNTAX     INTEGER{down(1),up(2),invalid(-1)}
          MAX-ACCESS read-only
          STATUS     current
          DESCRIPTION
                "Indicates the operational status of IP return downstream channel .
                 Options:
                 1. down(1) - down status
                 2. up(2) - up status
                 3. invalid(-1) - invalid value"
          ::= { hwCmtsIpReturnDsChannelEntry 8 }

    hwCmtsIpReturnDsChannelModeStatus OBJECT-TYPE
          SYNTAX     INTEGER{transponder(1),invalid(-1)}
          MAX-ACCESS read-only
          STATUS     current
          DESCRIPTION
                "
                Indicates the channel mode.
                Options:
                1. transponder(1) - transponder mode
                2. invalid(-1) - invalid value
                "
          ::= { hwCmtsIpReturnDsChannelEntry 9 }

    hwCmtsIpReturnDsChannelRowStatus OBJECT-TYPE
          SYNTAX     RowStatus
          MAX-ACCESS read-create
          STATUS     current
          DESCRIPTION
                "Indicates the row status to create or delete a channel ip return configuration.
                Options:
                1. active(1)      -indicates modify the specific ip return configuration.
                2. createAndGo(4) -indicates creating an ip return configuration.
                3. destroy(6)     -indicates deleting the specific ip return configuration.
                "
          ::= { hwCmtsIpReturnDsChannelEntry 10 }
          
          
    hwCmtsIpReturnDsChannelTxPowerConfig OBJECT-TYPE
          SYNTAX      Integer32
          UNITS       "0.1dBmV"
          MAX-ACCESS  read-write
          STATUS  current
          DESCRIPTION
                "Indicates the transmit power.
                Value range: -2147483647|315..600."
              DEFVAL      { 450 }
          ::= { hwCmtsIpReturnDsChannelEntry 11 }
             
    hwCmtsIpReturnDsChannelTxPowerStatus OBJECT-TYPE
          SYNTAX      Integer32
    UNITS       "0.1dBmV"
          MAX-ACCESS  read-only
          STATUS  current
          DESCRIPTION
                "Indicates the transmit power.
                Value range: -2147483647|315..600."
          ::= { hwCmtsIpReturnDsChannelEntry 12 }
          
    hwCmtsIpReturnDsModulationTechConfig OBJECT-TYPE
          SYNTAX     INTEGER{fsk50KHz(1),fsk67KHz(2),fsk80KHz(3)}
          MAX-ACCESS read-write
          STATUS     current
          DESCRIPTION
                "
                Indicates the channel modulation technique.
                Options:
                1. fsk50KHz(1) - FSK,signal +/-50KHz
                2. fsk67KHz(2) - FSK,signal +/-67KHz                      
                3. fsk80KHz(3) - FSK,signal +/-80KHz      
                "
              DEFVAL      { fsk67KHz }
          ::= { hwCmtsIpReturnDsChannelEntry 13 } 
                  
    hwCmtsIpReturnDsModulationTechStatus OBJECT-TYPE
          SYNTAX     INTEGER{fsk50KHz(1),fsk67KHz(2),fsk80KHz(3),invalid(-1)}
          MAX-ACCESS read-only
          STATUS     current
          DESCRIPTION
                "
                Indicates the channel modulation technique.
                Options:                    
                1. fsk50KHz(1) - FSK,signal +/-50KHz
                2. fsk67KHz(2) - FSK,signal +/-67KHz                      
                3. fsk80KHz(3) - FSK,signal +/-80KHz    
                4. invalid(-1) - invalid value      
                "
          ::= { hwCmtsIpReturnDsChannelEntry 14 }   
          
    hwCmtsIpReturnDsBitRateConfig OBJECT-TYPE
          SYNTAX     INTEGER{bitRate192(1),bitRate384(2)}
          MAX-ACCESS read-write
          STATUS     current
          DESCRIPTION
                "
                Indicates the channel bit rate.
                Options:
                1. bitRate192(1) - 19.2kbps  
                2. bitRate384(2) - 38.4kbps    
                "
              DEFVAL      { bitRate384 }
          ::= { hwCmtsIpReturnDsChannelEntry 15 } 
                  
    hwCmtsIpReturnDsBitRateStatus OBJECT-TYPE
          SYNTAX     INTEGER{bitRate192(1),bitRate384(2),invalid(-1)}
          MAX-ACCESS read-only
          STATUS     current
          DESCRIPTION
                "
                Indicates the channel bit rate.
                Options:
                1. bitRate192(1) - 19.2kbps  
                2. bitRate384(2) - 38.4kbps 
                3. invalid(-1) - invalid value      
                "
          ::= { hwCmtsIpReturnDsChannelEntry 16 }   
                     
  -- Table hwCmtsIpReturnDsChannelTable End

  -- Table hwDocsIf3BondingGrpCfgTable Begin
    hwDocsIf3BondingGrpCfgTable OBJECT-TYPE
          SYNTAX     SEQUENCE OF HwDocsIf3BondingGrpCfgEntry
          MAX-ACCESS not-accessible
          STATUS     current
          DESCRIPTION
               "This table describes the configuration of bonding group.
               The indexes of this table are ifIndex, docsIf3BondingGrpCfgDir and docsIf3BondingGrpCfgCfgId.
               "
          ::= { hwCmtsAccessObject 68 }

    hwDocsIf3BondingGrpCfgEntry OBJECT-TYPE
          SYNTAX     HwDocsIf3BondingGrpCfgEntry
          MAX-ACCESS not-accessible
          STATUS     current
          DESCRIPTION
               "This table describes the configuration of bonding group.
               The indexes of this entry are ifIndex, docsIf3BondingGrpCfgDir and docsIf3BondingGrpCfgCfgId.
               "
          INDEX       { ifIndex, docsIf3BondingGrpCfgDir, docsIf3BondingGrpCfgCfgId }
          ::= { hwDocsIf3BondingGrpCfgTable 1 }

    HwDocsIf3BondingGrpCfgEntry ::=
          SEQUENCE {
                    hwDocsIf3BondingGrpCfgMdSg     Unsigned32
                   }

    hwDocsIf3BondingGrpCfgMdSg OBJECT-TYPE
          SYNTAX     Unsigned32(1..2)
          MAX-ACCESS read-write
          STATUS     current
          DESCRIPTION
                "Indicates the MAC domain service group identify code."
              DEFVAL      { 1 }
          ::= { hwDocsIf3BondingGrpCfgEntry 1 }

  -- Table hwDocsIf3BondingGrpCfgTable End

  -- Table hwCmtsRfPowerDsGroupTable Begin
    hwCmtsRfPowerDsGroupTable OBJECT-TYPE
          SYNTAX     SEQUENCE OF HwCmtsRfPowerDsGroupEntry
          MAX-ACCESS not-accessible
          STATUS     current
          DESCRIPTION
               "This table describes the configuration of downstream RF power group.
               The indexes of this table are hwFrameIndex and hwCmtsRfPowerDsConfigGroupId.
               "
          ::= { hwCmtsAccessObject 69 }

    hwCmtsRfPowerDsGroupEntry OBJECT-TYPE
          SYNTAX     HwCmtsRfPowerDsGroupEntry
          MAX-ACCESS not-accessible
          STATUS     current
          DESCRIPTION
               "This table describes the configuration of downstream RF power group.
               The indexes of this entry are hwFrameIndex and hwCmtsRfPowerDsConfigGroupId.
               "
          INDEX       { hwFrameIndex, hwCmtsRfPowerDsGroupConfigGroupId }
          ::= { hwCmtsRfPowerDsGroupTable 1 }

    HwCmtsRfPowerDsGroupEntry ::=
          SEQUENCE {
                    hwCmtsRfPowerDsGroupConfigGroupId          Integer32,
                    hwCmtsRfPowerDsGroupConfigMaxFreq          Integer32,
                    hwCmtsRfPowerDsGroupConfigMaxFreqType      INTEGER,
                    hwCmtsRfPowerDsGroupConfigRFOutPower       Integer32,
                    hwCmtsRfPowerDsGroupConfigRFOutEq          Integer32,
                    hwCmtsRfPowerDsGroupSplitterType           INTEGER,
                    hwCmtsRfPowerDsGroupConfigAtt              Integer32,
                    hwCmtsRfPowerDsGroupConfigEq               Integer32,
                    hwCmtsRfPowerDsGroupStatusAtt              Integer32,
                    hwCmtsRfPowerDsGroupStatusEq               Integer32,
                    hwCmtsRfPowerDsGroupMinAtt                 Integer32
                   }

    hwCmtsRfPowerDsGroupConfigGroupId OBJECT-TYPE
          SYNTAX     Integer32(1..4)
          MAX-ACCESS not-accessible
          STATUS     current
          DESCRIPTION
                "Indicates the downstream RF power adjustment group ID."
          ::= { hwCmtsRfPowerDsGroupEntry 1 }

    hwCmtsRfPowerDsGroupConfigMaxFreq OBJECT-TYPE
          SYNTAX     Integer32(54000000..1794000000)
          UNITS   "Hz"
          MAX-ACCESS read-write
          STATUS     current
          DESCRIPTION
                "Indicates the maximum frequency of the downstream RF transmit power.
                Default: 1218000000"
          ::= { hwCmtsRfPowerDsGroupEntry 2 }

    hwCmtsRfPowerDsGroupConfigMaxFreqType OBJECT-TYPE
           SYNTAX INTEGER{catvQam(1), 
                           docScqam(2),
                           catvCw(3)}
           MAX-ACCESS read-write
           STATUS current
           DESCRIPTION
                "Indicates the type of the maximum frequency.
                 Default: docScqam(2).
                 Options:
                 1. catvQam(1)   -CATV digital TV channel
                 2. docScqam(2)  -DOCSIS single carrier quadrature amplitude modulation channel
                 3. catvCw(3)    -CATV continuous wave channel
                "
          ::= { hwCmtsRfPowerDsGroupEntry 3 }
          
    hwCmtsRfPowerDsGroupConfigRFOutPower OBJECT-TYPE
          SYNTAX     Integer32(300..560)
          UNITS   "0.1dBmV"
          MAX-ACCESS read-write
          STATUS     current
          DESCRIPTION
                "Indicates the transmit power of the maximum frequency for the downstream RF transmit power,
                which indicates the power of the 8 MHz channel whose central frequency is the maximum frequency.
                Default: 500"
          ::= { hwCmtsRfPowerDsGroupEntry 4 }
          
    hwCmtsRfPowerDsGroupConfigRFOutEq OBJECT-TYPE
          SYNTAX     Integer32(0..220)
          UNITS   "0.1dB"
          MAX-ACCESS read-write
          STATUS     current
          DESCRIPTION
                "Indicates the equalizer value of the downstream RF transmit power.
                Default: 180"
          ::= { hwCmtsRfPowerDsGroupEntry 5 }
          
    hwCmtsRfPowerDsGroupSplitterType OBJECT-TYPE
           SYNTAX INTEGER{splitter2(1), 
                           jumper(2)}
           MAX-ACCESS read-write
           STATUS current
           DESCRIPTION
                "Indicates the type of the splitter.
                 Default: splitter2(1).
                 Options:
                 1. splitter2(1)     -The two distributors connect to two RF out ports
                 2. jumper(2)        -The jumper connector connects to only one RF out port
                "
          ::= { hwCmtsRfPowerDsGroupEntry 6 }
          
    hwCmtsRfPowerDsGroupConfigAtt OBJECT-TYPE
          SYNTAX     Integer32(0..200)
          UNITS   "0.1dB"
          MAX-ACCESS read-write
          STATUS     current
          DESCRIPTION
                "Indicates the configuration value of the downstream RF attenuation.
                The adjustment accuracy is 0.5 dB, and the configured value must be an integer multiple of 5.
                Default: 0"
          ::= { hwCmtsRfPowerDsGroupEntry 7 }
          
    hwCmtsRfPowerDsGroupConfigEq OBJECT-TYPE
          SYNTAX     Integer32(0..220)
          UNITS   "0.1dB"
          MAX-ACCESS read-write
          STATUS     current
          DESCRIPTION
                "Indicates the configuration value of the downstream RF equalizer.
                The adjustment accuracy is 0.5 dB, and the configured value must be an integer multiple of 5. 
                Default: 180"
          ::= { hwCmtsRfPowerDsGroupEntry 8 }
          
    hwCmtsRfPowerDsGroupStatusAtt OBJECT-TYPE
          SYNTAX     Integer32
          UNITS   "0.1dB"
          MAX-ACCESS read-only
          STATUS     current
          DESCRIPTION
                "Indicates the actual value of the downstream RF attenuation.
                 -1 represents invalid value."
          ::= { hwCmtsRfPowerDsGroupEntry 9 }
          
    hwCmtsRfPowerDsGroupStatusEq OBJECT-TYPE
          SYNTAX     Integer32
          UNITS   "0.1dB"
          MAX-ACCESS read-only
          STATUS     current
          DESCRIPTION
                "Indicates the actual value of the downstream RF equalizer.
                 -1 represents invalid value."
          ::= { hwCmtsRfPowerDsGroupEntry 10 }
          
    hwCmtsRfPowerDsGroupMinAtt OBJECT-TYPE
          SYNTAX     Integer32(0..200)
          UNITS   "0.1dB"
          MAX-ACCESS read-write
          STATUS     current
          DESCRIPTION
                "Indicates the minimum value of the downstream RF attenuation.
                Default: 0"
          ::= { hwCmtsRfPowerDsGroupEntry 11 }          

  -- Table hwCmtsRfPowerDsGroupTable End
  
  -- Table hwCmtsRfPowerTable Begin
    hwCmtsRfPowerTable OBJECT-TYPE
          SYNTAX     SEQUENCE OF HwCmtsRfPowerEntry
          MAX-ACCESS not-accessible
          STATUS     current
          DESCRIPTION
               "This table describes the configuration of the downstream RF transmit power.
               The index of this table is hwFrameIndex.
               "
          ::= { hwCmtsAccessObject 70 }

    hwCmtsRfPowerEntry OBJECT-TYPE
          SYNTAX     HwCmtsRfPowerEntry
          MAX-ACCESS not-accessible
          STATUS     current
          DESCRIPTION
               "This table describes the configuration of the downstream RF transmit power.
               The index of this entry is hwFrameIndex.
               "
          INDEX       { hwFrameIndex}
          ::= { hwCmtsRfPowerTable 1 }

    HwCmtsRfPowerEntry ::=
          SEQUENCE {
                    hwCmtsRfPowerDsCatvDocsisDiff     Integer32,
                    hwCmtsRfPowerDsAdjustOperation    INTEGER,
                    hwCmtsRfPowerDsAdjustMode         INTEGER,
                    hwCmtsRfPowerDsConfigCatvAtt      Integer32,
                    hwCmtsRfPowerDsConfigDocsisAtt    Integer32,
                    hwCmtsRfPowerDsStatusCatvAtt      Integer32,
                    hwCmtsRfPowerDsStatusDocsisAtt    Integer32,
                    hwCmtsRfPowerDsMinCatvAtt         Integer32,
                    hwCmtsRfPowerDsMinDocsisAtt       Integer32,
                    hwCmtsRfPowerCatvCwAndDocScqamDiff  Integer32
                   }

    hwCmtsRfPowerDsCatvDocsisDiff OBJECT-TYPE
          SYNTAX     Integer32(-60..150)
          UNITS   "0.1dB"
          MAX-ACCESS read-write
          STATUS     current
          DESCRIPTION
                "Indicates the difference of transmit power between CATV digital TV channel and DOCSIS 
                single carrier quadrature amplitude modulation channel.
                Default: 60"
          ::= { hwCmtsRfPowerEntry 1 }
          
    hwCmtsRfPowerDsAdjustOperation OBJECT-TYPE
          SYNTAX  INTEGER {
                           startAdjust(1),
                           invalid(-1)
                          }
          MAX-ACCESS read-write
          STATUS     current
          DESCRIPTION
                "Indicates the operation type of downstream RF power adjustment.
                The system returns invalid value upon a reading request.
                Options:
                1. startAdjust(1)  - Enable automatic downstream RF power adjustment
                2. invalid(-1)     - The invalid value 
                "
          ::= { hwCmtsRfPowerEntry 2 }
          
    hwCmtsRfPowerDsAdjustMode OBJECT-TYPE
          SYNTAX  INTEGER {
                           auto(1),
                           manual(2)
                          }
          MAX-ACCESS read-write
          STATUS     current
          DESCRIPTION
                "Indicates the adjustment mode of the downstream RF power.
                Options:
                1. auto(1)      - Adjust RF power automatically
                2. manual(2)    - Adjust RF power manually
                Default: auto(1)
                "
          ::= { hwCmtsRfPowerEntry 3 }
          
    hwCmtsRfPowerDsConfigCatvAtt OBJECT-TYPE
          SYNTAX     Integer32(0..200)
          UNITS   "0.1dB"
          MAX-ACCESS read-write
          STATUS     current
          DESCRIPTION
                "Indicates the configuration value of the CATV attenuation of the downstream RF power.
                The adjustment accuracy is 0.5 dB, and the configured value must be an integer multiple of 5.
                Default: 0"
          ::= { hwCmtsRfPowerEntry 4 }
          
    hwCmtsRfPowerDsConfigDocsisAtt OBJECT-TYPE
          SYNTAX     Integer32(0..200)
          UNITS   "0.1dB"
          MAX-ACCESS read-write
          STATUS     current
          DESCRIPTION
                "Indicates the configuration value of the DOCSIS attenuation of the downstream RF power.
                The adjustment accuracy is 0.5 dB, and the configured value must be an integer multiple of 5. 
                Default: 0"
          ::= { hwCmtsRfPowerEntry 5 }
          
    hwCmtsRfPowerDsStatusCatvAtt OBJECT-TYPE
          SYNTAX     Integer32
          UNITS   "0.1dB"
          MAX-ACCESS read-only
          STATUS     current
          DESCRIPTION
                "Indicates the actual value of the CATV attenuation of the downstream RF power.
                -1 represents invalid value."
          ::= { hwCmtsRfPowerEntry 6 }
          
    hwCmtsRfPowerDsStatusDocsisAtt OBJECT-TYPE
          SYNTAX     Integer32
          UNITS   "0.1dB"
          MAX-ACCESS read-only
          STATUS     current
          DESCRIPTION
                "Indicates the actual value of the DOCSIS attenuation of the downstream RF power.
                -1 represents invalid value."
          ::= { hwCmtsRfPowerEntry 7 }
          
     hwCmtsRfPowerDsMinCatvAtt OBJECT-TYPE
          SYNTAX     Integer32(0..200)
          UNITS   "0.1dB"
          MAX-ACCESS read-write
          STATUS     current
          DESCRIPTION
                "Indicates the minimum value of the CATV attenuation of the downstream RF power.
                Default: 0"
          ::= { hwCmtsRfPowerEntry 8 }
          
    hwCmtsRfPowerDsMinDocsisAtt OBJECT-TYPE
          SYNTAX     Integer32(0..200)
          UNITS   "0.1dB"
          MAX-ACCESS read-write
          STATUS     current
          DESCRIPTION
                "Indicates the minimum value of the DOCSIS attenuation of the downstream RF power.
                Default: 0"
          ::= { hwCmtsRfPowerEntry 9 }
    hwCmtsRfPowerCatvCwAndDocScqamDiff OBJECT-TYPE
          SYNTAX     Integer32(-60..150)
          UNITS   "0.1dB"
          MAX-ACCESS read-write
          STATUS     current
          DESCRIPTION
                "Indicates the difference of transmit power between CATV continuous wave channel and DOCSIS 
                single carrier quadrature amplitude modulation channel.
                Default: 60"
          ::= { hwCmtsRfPowerEntry 10 }
                             
  -- Table hwCmtsRfPowerTable End
  
  -- Table hwCmtsRfPowerUsTable Begin
    hwCmtsRfPowerUsTable OBJECT-TYPE
          SYNTAX     SEQUENCE OF HwCmtsRfPowerUsEntry
          MAX-ACCESS not-accessible
          STATUS     current
          DESCRIPTION
               "This table describes the configuration of upstream RF power.
               The indexes of this table are hwFrameIndex and hwCmtsRfPowerUsConfigGroupId.
               "
          ::= { hwCmtsAccessObject 71 }  
    
    hwCmtsRfPowerUsEntry OBJECT-TYPE
          SYNTAX     HwCmtsRfPowerUsEntry
          MAX-ACCESS not-accessible
          STATUS     current
          DESCRIPTION
               "This table describes the configuration of upstream RF power.
               The indexes of this entry are hwFrameIndex and hwCmtsRfPowerUsConfigGroupId.
               "
          INDEX       { hwFrameIndex, hwCmtsRfPowerUsConfigGroupId }
          ::= { hwCmtsRfPowerUsTable 1 }
          
     HwCmtsRfPowerUsEntry ::=
          SEQUENCE {
                    hwCmtsRfPowerUsConfigGroupId     Integer32,
                    hwCmtsRfPowerUsConfigAttenuation Integer32,
                    hwCmtsRfPowerUsConfigEq          Integer32,
                    hwCmtsRfPowerUsStatusAttenuation Integer32,
                    hwCmtsRfPowerUsStatusEq          Integer32
                   }
                     
     hwCmtsRfPowerUsConfigGroupId OBJECT-TYPE
          SYNTAX     Integer32(1..2) 
          MAX-ACCESS not-accessible
          STATUS     current
          DESCRIPTION
                "Indicates the upstream RF power adjustment group ID."    
          ::= { hwCmtsRfPowerUsEntry 1 }
     
     hwCmtsRfPowerUsConfigAttenuation OBJECT-TYPE
          SYNTAX     Integer32(0..200) 
          UNITS   "0.1dB"
          MAX-ACCESS read-write
          STATUS     current
          DESCRIPTION
                "Indicates the attenuation value of the upstream RF power.
                 The adjustment accuracy is 0.5 dB, and the configured value must be an integer multiple of 5. 
                Default: 0" 
          ::= { hwCmtsRfPowerUsEntry 2 }
          
      hwCmtsRfPowerUsConfigEq OBJECT-TYPE
          SYNTAX     Integer32(0..50) 
          UNITS   "0.1dB"
          MAX-ACCESS read-write
          STATUS     current
          DESCRIPTION
                "Indicates the equalizer value of the upstream RF power.
                 The adjustment accuracy is 0.5 dB, and the configured value must be an integer multiple of 5. 
                Default: 0"
          ::= { hwCmtsRfPowerUsEntry 3 }
          
    hwCmtsRfPowerUsStatusAttenuation OBJECT-TYPE
          SYNTAX     Integer32 
          UNITS   "0.1dB"
          MAX-ACCESS read-only
          STATUS     current
          DESCRIPTION
                "Indicates the actual value of the attenuation of the upstream RF power. 
                 -1 represents invalid value." 
          ::= { hwCmtsRfPowerUsEntry 4 }
          
      hwCmtsRfPowerUsStatusEq OBJECT-TYPE
          SYNTAX     Integer32 
          UNITS   "0.1dB"
          MAX-ACCESS read-only
          STATUS     current
          DESCRIPTION
                "Indicates the actual value of the equalizer of the upstream RF power. 
                 -1 represents invalid value."
          ::= { hwCmtsRfPowerUsEntry 5 }       
          
  -- Table hwCmtsRfPowerUsTable End
  
  
  -- Table hwCmtsRfPowerDsMonitorStatusTable Begin
    hwCmtsRfPowerDsMonitorStatusTable OBJECT-TYPE
          SYNTAX     SEQUENCE OF  HwCmtsRfPowerDsMonitorStatusEntry
          MAX-ACCESS not-accessible
          STATUS     current
          DESCRIPTION
               "This table describes the query of RF downstream transmit power monitoring information. 
                The information includes the expected power and actual power.
                The indexes of this table are hwFrameIndex, hwCmtsRfPowerDsMonitorStatusGroupId and hwCmtsRfPowerDsMonitorStatusFreqIndex.
               "
          ::= { hwCmtsAccessObject 72 }  
    
    hwCmtsRfPowerDsMonitorStatusEntry OBJECT-TYPE
          SYNTAX     HwCmtsRfPowerDsMonitorStatusEntry
          MAX-ACCESS not-accessible
          STATUS     current
          DESCRIPTION
               "This table describes the query of RF downstream transmit power monitoring information. 
                The information includes the expected power and actual power.
                The indexes of this entry are hwFrameIndex, hwCmtsRfPowerDsMonitorStatusGroupId and hwCmtsRfPowerDsMonitorStatusFreqIndex.
               "
          INDEX       {hwFrameIndex, hwCmtsRfPowerDsMonitorStatusGroupId, hwCmtsRfPowerDsMonitorStatusFreqIndex}
          ::= { hwCmtsRfPowerDsMonitorStatusTable 1 }
          
     HwCmtsRfPowerDsMonitorStatusEntry ::=
          SEQUENCE {
                    hwCmtsRfPowerDsMonitorStatusGroupId Integer32,
                    hwCmtsRfPowerDsMonitorStatusFreqIndex  Integer32,
                    hwCmtsRfPowerDsMonitorStatusFrequency  Integer32,
                    hwCmtsRfPowerDsMonitorStatusFreqWidth  INTEGER,
                    hwCmtsRfPowerDsMonitorStatusFreqType   INTEGER,
                    hwCmtsRfPowerDsMonitorStatusFreqExpectPower  Integer32,
                    hwCmtsRfPowerDsMonitorStatusFreqMeterPower   Integer32
                   }

     hwCmtsRfPowerDsMonitorStatusGroupId OBJECT-TYPE
          SYNTAX     Integer32(0..4) 
          MAX-ACCESS not-accessible
          STATUS     current
          DESCRIPTION
                "Indicates the main path ID and the group ID.
                 The main path ID is 0.
                 The group ID range is from 1 to 4."
          ::= { hwCmtsRfPowerDsMonitorStatusEntry 1 }
          
      hwCmtsRfPowerDsMonitorStatusFreqIndex OBJECT-TYPE
          SYNTAX     Integer32(1..6) 
          MAX-ACCESS not-accessible
          STATUS     current
          DESCRIPTION
                "Indicates the index of frequency."  
          ::= { hwCmtsRfPowerDsMonitorStatusEntry 2 }       

     hwCmtsRfPowerDsMonitorStatusFrequency OBJECT-TYPE
          SYNTAX     Integer32(85000000..1002000000)
          UNITS   "Hz"
          MAX-ACCESS read-only
          STATUS     current
          DESCRIPTION
                "Indicates the central frequency.
                Range: 85000000-1002000000"
          ::= { hwCmtsRfPowerDsMonitorStatusEntry 3 }

     hwCmtsRfPowerDsMonitorStatusFreqWidth OBJECT-TYPE
           SYNTAX INTEGER{kHz6000(1), 
                          kHz8000(2)}
           MAX-ACCESS read-only
           STATUS current
           DESCRIPTION
                "Indicates the RF power monitor downstream frequency width.
                 Options:
                 1. kHz6000(1)  -6000kHz
                 2. kHz8000(2)  -8000kHz
                "
          ::= { hwCmtsRfPowerDsMonitorStatusEntry 4 }

     hwCmtsRfPowerDsMonitorStatusFreqType OBJECT-TYPE
           SYNTAX INTEGER{catvQam(1), 
                           docScqam(2),
                           catvCw(3)}
           MAX-ACCESS read-only
           STATUS current
           DESCRIPTION
                "Indicates the RF power monitor downstream type.
                 Options:
                 1. catvQam(1)    -CATV digital TV channel
                 2. docScqam(2)   -DOCSIS single carrier quadrature amplitude modulation channel
                 3. catvCw(3)     -CATV continuous wave channel
                "
          ::= { hwCmtsRfPowerDsMonitorStatusEntry 5 }

     hwCmtsRfPowerDsMonitorStatusFreqExpectPower OBJECT-TYPE
          SYNTAX     Integer32
          UNITS   "0.1dBmV"
          MAX-ACCESS read-only
          STATUS     current
          DESCRIPTION
                "Indicates the RF expected power.
                If -2147483647 is returned, the query failed. The possible cause is that a board error occurs, the query times out, or the system is adjusting the RF.
                "
          ::= { hwCmtsRfPowerDsMonitorStatusEntry 6 }          

     hwCmtsRfPowerDsMonitorStatusFreqMeterPower OBJECT-TYPE
          SYNTAX     Integer32
          UNITS   "0.1dBmV"
          MAX-ACCESS read-only
          STATUS     current
          DESCRIPTION
                "Indicates the RF actual power.
                If -2147483647 is returned, the query failed. The possible cause is that a board error occurs, the query times out, or the system is adjusting the RF.
                "
          ::= { hwCmtsRfPowerDsMonitorStatusEntry 7 }      
              
  -- Table hwCmtsRfPowerDsMonitorStatusTable End  
  
  -- Table hwCmtsRfPowerDsMonitorTempTable Begin
    hwCmtsRfPowerDsMonitorTempTable OBJECT IDENTIFIER ::= {hwCmtsAccessObject 73}
    hwCmtsRfPowerDsMonitorTempFrameIndex  OBJECT-TYPE
          SYNTAX     Integer32(-1|0..512)
          MAX-ACCESS read-write
          STATUS     current
          DESCRIPTION
               "Indicates the frame ID of CMC.
                -1 represents that the frame ID is not configured.
               "
          ::= { hwCmtsRfPowerDsMonitorTempTable 1 }

    hwCmtsRfPowerDsMonitorTempGroupId OBJECT-TYPE
          SYNTAX     Integer32(0..4)
          MAX-ACCESS read-write
          STATUS     current
          DESCRIPTION
                "Indicates the main path ID and the group ID.
                 The main path ID is 0.
                 The group ID range is from 1 to 4."
          ::= { hwCmtsRfPowerDsMonitorTempTable 2 }
          
    hwCmtsRfPowerDsMonitorTempFrequency OBJECT-TYPE
          SYNTAX     Integer32(-1|85000000..1002000000)
          UNITS   "Hz"
          MAX-ACCESS read-write
          STATUS     current
          DESCRIPTION
                "Indicates the spectrum frequency of RF output power monitoring.                
                 -1 represents that the spectrum frequency is not configured."  
          ::= { hwCmtsRfPowerDsMonitorTempTable 3 }
          
    hwCmtsRfPowerDsMonitorTempFreqWidth OBJECT-TYPE
          SYNTAX     INTEGER{kHz6000(1), 
                             kHz8000(2)} 
          MAX-ACCESS read-write
          STATUS     current
          DESCRIPTION
                "Indicates the spectrum width of RF output power monitoring.
                Default: kHz8000(2)
                Options:
                1. kHz6000(1)  -6000kHz
                2. kHz8000(2)  -8000kHz
                "  
          ::= { hwCmtsRfPowerDsMonitorTempTable 4 }
          
    hwCmtsRfPowerDsMonitorTempFreqType OBJECT-TYPE
          SYNTAX     INTEGER{catvQam(1), 
                             docScqam(2),
                             catvCw(3),
                             docOfdm(4)} 
          MAX-ACCESS read-write
          STATUS     current
          DESCRIPTION
                "Indicates the spectrum type of RF output power monitoring.
                Default: docScqam(2)
                Options:
                1. catvQam(1)  -CATV digital TV channel
                2. docScqam(2) -DOCSIS single carrier quadrature amplitude modulation channel
                3. catvCw(3)   -CATV continuous wave channel
                4. docOfdm(4)  -DOCSIS OFDM downstream channel 
                "  
          ::= { hwCmtsRfPowerDsMonitorTempTable 5 }
          
    hwCmtsRfPowerDsMonitorTempExpectPower OBJECT-TYPE
          SYNTAX     Integer32 
          UNITS   "0.1dBmV"
          MAX-ACCESS read-only
          STATUS     current
          DESCRIPTION
                "Indicates the RF expected power.
                If -2147483647 is returned, the query failed.
                "  
          ::= { hwCmtsRfPowerDsMonitorTempTable 6 }
          
    hwCmtsRfPowerDsMonitorTempFreqMeterPower OBJECT-TYPE
          SYNTAX     Integer32 
          UNITS   "0.1dBmV"
          MAX-ACCESS read-only
          STATUS     current
          DESCRIPTION
                "Indicates the RF actual power.
                If -2147483647 is returned, the query failed.
                "  
          ::= { hwCmtsRfPowerDsMonitorTempTable 7 }     
          
    -- Table hwCmtsRfPowerDsMonitorTempTable End 
    
    
    -- Table hwCmtsRfPowerDsMonitorConfigTable Begin
    hwCmtsRfPowerDsMonitorConfigTable OBJECT-TYPE
          SYNTAX     SEQUENCE OF HwCmtsRfPowerDsMonitorConfigEntry
          MAX-ACCESS not-accessible
          STATUS     current
          DESCRIPTION
               "This table describes the configuration of RF power monitor downstream.
               The indexes of this table are hwFrameIndex and hwCmtsRfPowerDsMonitorIndex.
               "
          ::= { hwCmtsAccessObject 74 }

    hwCmtsRfPowerDsMonitorConfigEntry OBJECT-TYPE
          SYNTAX     HwCmtsRfPowerDsMonitorConfigEntry
          MAX-ACCESS not-accessible
          STATUS     current
          DESCRIPTION
               "This table describes the configuration of RF power monitor downstream.
               The indexes of this entry are hwFrameIndex and hwCmtsRfPowerDsMonitorIndex.
               "
          INDEX       { hwFrameIndex, hwCmtsRfPowerDsMonitorIndex }
          ::= { hwCmtsRfPowerDsMonitorConfigTable 1 }

    HwCmtsRfPowerDsMonitorConfigEntry ::=
          SEQUENCE {
                    hwCmtsRfPowerDsMonitorIndex Integer32,
                    hwCmtsRfPowerDsMonitorFrequency Integer32,
                    hwCmtsRfPowerDsMonitorFreqWidth INTEGER,
                    hwCmtsRfPowerDsMonitorFreqType INTEGER,
                    hwCmtsRfPowerDsMonitorRowStatus RowStatus,
                    hwCmtsRfPowerDsMonitorFreqFunction  INTEGER
                   }

    hwCmtsRfPowerDsMonitorIndex OBJECT-TYPE
          SYNTAX     Integer32(1..6|2147483647)
          MAX-ACCESS not-accessible
          STATUS     current
          DESCRIPTION
                "Indicates the spectrum index of RF output power monitoring.
                 Use index 2147483647 to issue the set command to enable the system to 
                 assign an index for RF output power monitoring."
          ::= { hwCmtsRfPowerDsMonitorConfigEntry 1 }
          
    hwCmtsRfPowerDsMonitorFrequency OBJECT-TYPE
          SYNTAX     Integer32(85000000..1002000000)
          UNITS   "Hz"
          MAX-ACCESS read-create
          STATUS     current
          DESCRIPTION
                "Indicates the spectrum frequency of RF output power monitoring.
                Range: 85000000-1002000000
                "
          ::= { hwCmtsRfPowerDsMonitorConfigEntry 2 }
          
    hwCmtsRfPowerDsMonitorFreqWidth OBJECT-TYPE
          SYNTAX     INTEGER{kHz6000(1), 
                             kHz8000(2)}
          MAX-ACCESS read-create
          STATUS     current
          DESCRIPTION
                "Indicates the spectrum width of RF output power monitoring.
                Default: kHz8000(2)
                Options:
                1. kHz6000(1) - 6000KHz     
                2. kHz8000(2) - 8000KHz      
                "
          ::= { hwCmtsRfPowerDsMonitorConfigEntry 3 }
          
    hwCmtsRfPowerDsMonitorFreqType OBJECT-TYPE
          SYNTAX     INTEGER{catvQam(1), 
                           docScqam(2),
                           catvCw(3)}
          MAX-ACCESS read-create
          STATUS     current
          DESCRIPTION
                "Indicates the spectrum type of RF output power monitoring.
                Not more than one monitoring frequency of CATV type (CATV types include catv-qaw and catv-cw) and with the adjust-power function can be configured.
                Not more than one monitoring frequency of DOCSIS type (DOCSIS type includes doc-scqam) and with the adjust-power function can be configured.
                Default: docScqam(2)
                Options:
                1. catvQam(1)   -CATV digital TV channel     
                2. docScqam(2)  -DOCSIS single carrier quadrature amplitude modulation channel 
                3. catvCw(3)    -CATV continuous wave channel
                "
          ::= { hwCmtsRfPowerDsMonitorConfigEntry 4 }
          
    hwCmtsRfPowerDsMonitorRowStatus OBJECT-TYPE
          SYNTAX     RowStatus
          MAX-ACCESS read-create
          STATUS     current
          DESCRIPTION
                "Indicates the row status to create or 
                delete the RF power monitor downstream.
                "
          ::= { hwCmtsRfPowerDsMonitorConfigEntry 5 }
          
    hwCmtsRfPowerDsMonitorFreqFunction OBJECT-TYPE
          SYNTAX     INTEGER{adjustPower(1), 
                             queryPower(2)}
          MAX-ACCESS read-create
          STATUS     current
          DESCRIPTION
                "Indicates the monitoring frequency function of the RF output port.
                Not more than one monitoring frequency with the adjust-power function and of CATV type (CATV types include catv-qam and catv-cw) can be configured.
                Not more than one monitoring frequency with the adjust-power function and of DOCSIS type (DOCSIS type includes doc-scqam) can be configured.
                Default: adjustPower(1)
                Options:
                1. adjustPower(1) -adjusts the power     
                2. queryPower(2)  -only queries the power      
                "
          ::= { hwCmtsRfPowerDsMonitorConfigEntry 6 }

   -- Table hwCmtsRfPowerDsMonitorConfigTable End
   
   -- Table hwCmtsUsHistorySpectrumCfgTable Begin
    hwCmtsUsHistorySpectrumCfgTable OBJECT IDENTIFIER ::= {hwCmtsAccessObject 75}
    hwCmtsUsHistorySpectrumSwitch  OBJECT-TYPE
          SYNTAX   INTEGER
          {
           enable(1), 
           disable(2),
           invalid(-1)
          }
          MAX-ACCESS read-write
          STATUS     current
          DESCRIPTION
               "Indicates the switch of upstream history frequency spectrum scanning function. 
          Options:
          1. enable(1)     -Enable the upstream history frequency spectrum scanning function
          2. disable(2)    -Disable the upstream history frequency spectrum scanning function
          3. invalid(-1)   -Invalid
          Default: disable(2)
               "
          ::= { hwCmtsUsHistorySpectrumCfgTable 1 }

    hwCmtsUsHistorySpectrumMode OBJECT-TYPE
          SYNTAX     INTEGER
          {
           noise(1), 
           carrier(2),
           freeRunning(3),
           invalid(-1)
          }
          MAX-ACCESS read-write
          STATUS     current
          DESCRIPTION
                "Indicates the upstream history frequency spectrum scanning mode.
                 Options:
           1. noise(1)       -Scanning history noise frequency spectrum
           2. carrier(2)     -Scanning history carrier frequency spectrum
           3. freeRunning(3) -Scanning history noise or carrier frequency spectrum
           4. invalid(-1)    -Invalid
           Default: noise(1)
                "
          ::= { hwCmtsUsHistorySpectrumCfgTable 2 }
          
    hwCmtsUsHistorySpectrumResolution OBJECT-TYPE
          SYNTAX     INTEGER
          {
           hz300K(1), 
           invalid(-1)
          }
          MAX-ACCESS read-write
          STATUS     current
          DESCRIPTION
                "Indicates the upstream history frequency spectrum scanning resolution.
                 Options:
           1. hz300K(1)     -Sets the upstream history frequency spectrum scanning resolution to 300Khz
                 2. invalid(-1)   -Invalid
                 Default: hz300K(1)
          "  
          ::= { hwCmtsUsHistorySpectrumCfgTable 3 }
          
    hwCmtsUsHistorySpectrumSampleTime OBJECT-TYPE
          SYNTAX     INTEGER
          {
           s15(1), 
           s9(2),
           invalid(-1)
          } 
          MAX-ACCESS read-write
          STATUS     current
          DESCRIPTION
                "Indicates the upstream history frequency spectrum scanning period.
                 Options:
                 1. s15(1)      -Sets the upstream history frequency spectrum scanning period to 15s
           2. s9(2)       -Sets the upstream history frequency spectrum scanning period to 9s
                 3. invalid(-1) -Invalid
                 Default: s15(1)
                "  
          ::= { hwCmtsUsHistorySpectrumCfgTable 4 }
          
    hwCmtsUsHistorySpectrumFrequencyStart OBJECT-TYPE
          SYNTAX     Integer32(-1|0..204000000)
          UNITS   "Hz"
          MAX-ACCESS read-write
          STATUS     current
          DESCRIPTION
                "Indicates the start frequency for upstream history spectrum scanning.
           -1 represent that the upstream history spectrum configuration of start frequency has invalid configuration data.
           Default: 0
                "  
          ::= { hwCmtsUsHistorySpectrumCfgTable 5 }
          
    hwCmtsUsHistorySpectrumFrequencyEnd OBJECT-TYPE
          SYNTAX     Integer32(-1|0..204000000)
          UNITS   "Hz"
          MAX-ACCESS read-write
          STATUS     current
          DESCRIPTION
                "Indicates the end frequency for upstream history spectrum scanning.
           Requirement: The difference between the end frequency and the start frequency must be greater than 
           the upstream history frequency spectrum scanning resolution.
           -1 represent that the upstream history spectrum configuration of end frequency has invalid configuration data.
           Default: 204000000
                "  
          ::= { hwCmtsUsHistorySpectrumCfgTable 6 }
          
    hwCmtsUsHistorySpectrumUploadTime  OBJECT-TYPE
          SYNTAX     Integer32 (120..840)
          UNITS   "seconds"
          MAX-ACCESS read-write  
          STATUS     current  
          DESCRIPTION
                "The time for uploading files, relative time, indicates the relative time to the 15 whole minutes time.
                "
          DEFVAL     {120}
          ::= { hwCmtsUsHistorySpectrumCfgTable 7 }  
          
   -- Table hwCmtsUsHistorySpectrumCfgTable End 
    
    -- Table hwCmtsUsRasterCfgTable begin
        
    hwCmtsUsRasterCfgTable OBJECT-TYPE
        SYNTAX     SEQUENCE OF HwCmtsUsRasterCfgEntry
        MAX-ACCESS not-accessible
        STATUS     current
        DESCRIPTION
            "Indicates the parameter of a raster.
             The index of this table is hwCmtsUsRasterId.
            "
        ::= { hwCmtsAccessObject 76 }

    hwCmtsUsRasterCfgEntry OBJECT-TYPE
        SYNTAX     HwCmtsUsRasterCfgEntry
        MAX-ACCESS not-accessible
        STATUS     current
        DESCRIPTION
            "Indicates the parameter of a raster.
             The index of this entry is hwCmtsUsRasterId.
            "
        INDEX       { hwCmtsUsRasterId }
        ::= { hwCmtsUsRasterCfgTable 1 }

    HwCmtsUsRasterCfgEntry ::=
        SEQUENCE {
                 hwCmtsUsRasterId                              Integer32,
                 hwCmtsUsRasterCenterFrequency                 Integer32,
                 hwCmtsUsRasterBandwidth                       Integer32,
                 hwCmtsUsRasterCheckCnr1                       Integer32,
                 hwCmtsUsRasterCheckCnr1Rule                   INTEGER,
                 hwCmtsUsRasterCheckCnr1ReportMode             INTEGER,
                 hwCmtsUsRasterCheckCnr1ReportPeriod           Integer32,
                 hwCmtsUsRasterCheckCnr1ReportThreshold        Integer32,
                 hwCmtsUsRasterCheckCnr2                       Integer32,
                 hwCmtsUsRasterCheckCnr2Rule                   INTEGER,
                 hwCmtsUsRasterCheckCnr2ReportMode             INTEGER,
                 hwCmtsUsRasterCheckCnr2ReportPeriod           Integer32,
                 hwCmtsUsRasterCheckCnr2ReportThreshold        Integer32,
                 hwCmtsUsRasterCheckCnr3                       Integer32,
                 hwCmtsUsRasterCheckCnr3Rule                   INTEGER,
                 hwCmtsUsRasterCheckCnr3ReportMode             INTEGER,
                 hwCmtsUsRasterCheckCnr3ReportPeriod           Integer32,
                 hwCmtsUsRasterCheckCnr3ReportThreshold        Integer32,
                 hwCmtsUsRasterRowstatus                       RowStatus
        }

  hwCmtsUsRasterId OBJECT-TYPE
            SYNTAX Integer32  (1..32)
            MAX-ACCESS not-accessible
            STATUS current
            DESCRIPTION
                "Indicates the index of the raster.
                "
         ::= { hwCmtsUsRasterCfgEntry 1 }

    hwCmtsUsRasterCenterFrequency OBJECT-TYPE
            SYNTAX Integer32  (-1|0..204000000)
            UNITS   "Hz"
            MAX-ACCESS read-write
            STATUS current
            DESCRIPTION
                "Indicates the center frequency of the raster.
                 -1 represent that the center frequency is not assigned.
                "
         ::= { hwCmtsUsRasterCfgEntry 2 }

    hwCmtsUsRasterBandwidth OBJECT-TYPE
            SYNTAX  Integer32 (-1|0..6400000)
            UNITS   "Hz"
            MAX-ACCESS  read-write
            STATUS  current
            DESCRIPTION
                "The band width of a raster.
                Only three width values are supported currently.
                -1 represent that the band width is not assigned.
                Options:
                1600000,3200000,6400000
                Default value: 3200000"
         ::= { hwCmtsUsRasterCfgEntry 3 }

    hwCmtsUsRasterCheckCnr1 OBJECT-TYPE
            SYNTAX  Integer32 (-1|0..70)
            UNITS   "dBmv"
            MAX-ACCESS  read-write
            STATUS  current
            DESCRIPTION
                "The raster check cnr of a raster.
                -1 represent that the raster check cnr is not assigned."
         ::= { hwCmtsUsRasterCfgEntry 4 }

    hwCmtsUsRasterCheckCnr1Rule OBJECT-TYPE
            SYNTAX  INTEGER {
                             up(1),
                             down(2),
           invalidValue(-1)
                            }
            MAX-ACCESS  read-write
            STATUS  current
            DESCRIPTION
                "The raster check rule of a raster.
                Options:
                1. up(1) - fail when cnr more than threshold
                2. down(2) - fail when cnr less than threshold
                3. invalidValue(-1) - Invalid value
                Default value: up(1)"
         ::= { hwCmtsUsRasterCfgEntry 5 }

    hwCmtsUsRasterCheckCnr1ReportMode OBJECT-TYPE
            SYNTAX  INTEGER {
                             period(1),
                             instant(2),
           invalidValue(-1)
                            }
            MAX-ACCESS  read-write
            STATUS  current
            DESCRIPTION
                "The raster report mode of a raster.
                Options:
                1. period(1) - report when cnr more than threshold
                2. instant(2) - report when cnr less than threshold
                3. invalidValue(-1) - Invalid value
                Default value: period(1)"
         ::= { hwCmtsUsRasterCfgEntry 6 }

    hwCmtsUsRasterCheckCnr1ReportPeriod OBJECT-TYPE
            SYNTAX  Integer32 (-1|1..1440)
            UNITS   "minute"
            MAX-ACCESS  read-write
            STATUS  current
            DESCRIPTION
                "The raster check report period of a raster.
                -1 represent that the raster check report period is not assigned.
                Default value: 15."
         ::= { hwCmtsUsRasterCfgEntry 7 }

    hwCmtsUsRasterCheckCnr1ReportThreshold OBJECT-TYPE
            SYNTAX  Integer32 (-1|1..100)
            MAX-ACCESS  read-write
            STATUS  current
            DESCRIPTION
                "The raster check report threshold of a raster.
                -1 represent that the raster check report threshold is not assigned."
         ::= { hwCmtsUsRasterCfgEntry 8 }

    hwCmtsUsRasterCheckCnr2 OBJECT-TYPE
            SYNTAX  Integer32 (-1|0..70)
            UNITS   "dBmv"
            MAX-ACCESS  read-write
            STATUS  current
            DESCRIPTION
                "The raster check cnr of a raster.
                -1 represent that the raster check cnr is not assigned."
         ::= { hwCmtsUsRasterCfgEntry 9 }

    hwCmtsUsRasterCheckCnr2Rule OBJECT-TYPE
            SYNTAX  INTEGER {
                             up(1),
                             down(2),
           invalidValue(-1)
                            }
            MAX-ACCESS  read-write
            STATUS  current
            DESCRIPTION
                "The raster check rule of a raster.
                Options:
                1. up(1) - fail when cnr more than threshold
                2. down(2) - fail when cnr less than threshold
                3. invalidValue(-1) - Invalid value
                Default value: up(1)"
         ::= { hwCmtsUsRasterCfgEntry 10 }

    hwCmtsUsRasterCheckCnr2ReportMode OBJECT-TYPE
            SYNTAX  INTEGER {
                             period(1),
                             instant(2),
           invalidValue(-1)
                            }
            MAX-ACCESS  read-write
            STATUS  current
            DESCRIPTION
                "The raster report mode of a raster.
                Options:
                1. period(1) - report when cnr more than threshold
                2. instant(2) - report when cnr less than threshold
                3. invalidValue(-1) - Invalid value
                Default value: period(1)"
         ::= { hwCmtsUsRasterCfgEntry 11 }

    hwCmtsUsRasterCheckCnr2ReportPeriod OBJECT-TYPE
            SYNTAX  Integer32 (-1|1..1440)
            UNITS   "minute"
            MAX-ACCESS  read-write
            STATUS  current
            DESCRIPTION
                "The raster check report period of a raster.
                -1 represent that the raster check report period is not assigned.
                Default value: 15."
         ::= { hwCmtsUsRasterCfgEntry 12 }

    hwCmtsUsRasterCheckCnr2ReportThreshold OBJECT-TYPE
            SYNTAX  Integer32 (-1|1..100)
            MAX-ACCESS  read-write
            STATUS  current
            DESCRIPTION
                "The raster check report threshold of a raster.
                -1 represent that the raster check report threshold is not assigned."
         ::= { hwCmtsUsRasterCfgEntry 13 }

    hwCmtsUsRasterCheckCnr3 OBJECT-TYPE
            SYNTAX  Integer32 (-1|0..70)
            UNITS   "dBmv"
            MAX-ACCESS  read-write
            STATUS  current
            DESCRIPTION
                "The raster check cnr of a raster.
                -1 represent that the raster check cnr is not assigned."
         ::= { hwCmtsUsRasterCfgEntry 14 }

    hwCmtsUsRasterCheckCnr3Rule OBJECT-TYPE
            SYNTAX  INTEGER {
                             up(1),
                             down(2),
           invalidValue(-1)
                            }
            MAX-ACCESS  read-write
            STATUS  current
            DESCRIPTION
                "The raster check rule of a raster.
                Options:
                1. up(1) - fail when cnr more than threshold
                2. down(2) - fail when cnr less than threshold
                3. invalidValue(-1) - Invalid value
                Default value: up(1)"
         ::= { hwCmtsUsRasterCfgEntry 15 }

    hwCmtsUsRasterCheckCnr3ReportMode OBJECT-TYPE
            SYNTAX  INTEGER {
                             period(1),
                             instant(2),
           invalidValue(-1)
                            }
            MAX-ACCESS  read-write
            STATUS  current
            DESCRIPTION
                "The raster report mode of a raster.
                Options:
                1. period(1) - report when cnr more than threshold
                2. instant(2) - report when cnr less than threshold
                3. invalidValue(-1) - Invalid value
                Default value: period(1)"
         ::= { hwCmtsUsRasterCfgEntry 16 }

    hwCmtsUsRasterCheckCnr3ReportPeriod OBJECT-TYPE
            SYNTAX  Integer32 (-1|1..1440)
            UNITS   "minute"
            MAX-ACCESS  read-write
            STATUS  current
            DESCRIPTION
                "The raster check report period of a raster.
                -1 represent that the raster check report period is not assigned.
                Default value: 15."
         ::= { hwCmtsUsRasterCfgEntry 17 }

    hwCmtsUsRasterCheckCnr3ReportThreshold OBJECT-TYPE
            SYNTAX  Integer32 (-1|1..100)
            MAX-ACCESS  read-write
            STATUS  current
            DESCRIPTION
                "The raster check report threshold of a raster.
                -1 represent that the raster check report threshold is not assigned."
         ::= { hwCmtsUsRasterCfgEntry 18 }

    hwCmtsUsRasterRowstatus OBJECT-TYPE
          SYNTAX     RowStatus
          MAX-ACCESS read-create
          STATUS     current
          DESCRIPTION
                "Indicates the row status to create or 
                 delete a raster."
          ::= { hwCmtsUsRasterCfgEntry 19 }
     
    -- Table hwCmtsUsRasterCfgTable end

    -- Table hwCmtsUsRasterCheckTable begin
        
    hwCmtsUsRasterCheckTable OBJECT-TYPE
        SYNTAX     SEQUENCE OF HwCmtsUsRasterCheckEntry
        MAX-ACCESS not-accessible
        STATUS     current
        DESCRIPTION
            "This table describes the configuration of Raster Switch.
            The indexes of this table are ifIndex and hwCmtsUsRasterCheckSgId.
            "
        ::= { hwCmtsAccessObject 77 }

    hwCmtsUsRasterCheckEntry OBJECT-TYPE
        SYNTAX     HwCmtsUsRasterCheckEntry
        MAX-ACCESS not-accessible
        STATUS     current
        DESCRIPTION
            "This table describes the configuration of Raster Switch.
            The indexes of this entry are ifIndex and hwCmtsUsRasterCheckSgId.
            "
        INDEX       { ifIndex,hwCmtsUsRasterCheckSgId }
        ::= { hwCmtsUsRasterCheckTable 1 }              

    HwCmtsUsRasterCheckEntry ::=
        SEQUENCE {
                   hwCmtsUsRasterCheckSgId Integer32,
                   hwCmtsUsRasterCheckIdList OCTET STRING,
                   hwCmtsUsRasterCheckCnr1SwitchList OCTET STRING,
                   hwCmtsUsRasterCheckCnr2SwitchList OCTET STRING,
                   hwCmtsUsRasterCheckCnr3SwitchList OCTET STRING
                 }

   hwCmtsUsRasterCheckSgId OBJECT-TYPE
            SYNTAX Integer32  (1..2)
            MAX-ACCESS not-accessible
            STATUS current
            DESCRIPTION
                "Indicates the MAC domain upstream service group ID.
                "
         ::= { hwCmtsUsRasterCheckEntry 1 }

    hwCmtsUsRasterCheckIdList OBJECT-TYPE
          SYNTAX  OCTET STRING (SIZE (0..32))
          MAX-ACCESS  read-write
          STATUS  current
          DESCRIPTION
                "Indicates the raster ID list.
                 The list is variable, each byte represents a raster ID, the ID is constraint by hwCmtsUsRasterId.
                "
          ::= { hwCmtsUsRasterCheckEntry 2 } 
          
    hwCmtsUsRasterCheckCnr1SwitchList OBJECT-TYPE
          SYNTAX  OCTET STRING (SIZE (0..32))
          MAX-ACCESS  read-write
          STATUS  current
          DESCRIPTION
                "Indicates the raster switch status list for first-threshold.
                 Each byte represents a raster switch status. Raster switch statuses are in one-to-one mapping with those in hwCmtsUsRasterCheckIdList.
                 The raster switch status can be 1:enable(1), 2:disable(2).         
                "
          ::= { hwCmtsUsRasterCheckEntry 3 }  

    hwCmtsUsRasterCheckCnr2SwitchList OBJECT-TYPE
          SYNTAX  OCTET STRING (SIZE (0..32))
          MAX-ACCESS  read-write
          STATUS  current
          DESCRIPTION
                "Indicates the raster switch status list for second-threshold.
                 Each byte represents a raster switch status. Raster switch statuses are in one-to-one mapping with those in hwCmtsUsRasterCheckIdList.
                 The raster switch status can be 1:enable(1), 2:disable(2).         
                "
          ::= { hwCmtsUsRasterCheckEntry 4 }  
          
    hwCmtsUsRasterCheckCnr3SwitchList OBJECT-TYPE
          SYNTAX  OCTET STRING (SIZE (0..32))
          MAX-ACCESS  read-write
          STATUS  current
          DESCRIPTION
                "Indicates the raster switch status list for third-threshold.
                 Each byte represents a raster switch status. Raster switch statuses are in one-to-one mapping with those in hwCmtsUsRasterCheckIdList.
                 The raster switch status can be 1:enable(1), 2:disable(2).         
                "
          ::= { hwCmtsUsRasterCheckEntry 5 }       
                  
 --Table hwCmtsUsRasterCheckTable end
 
    --Table hwDocsIf3CmtsCmDepartureReasonTable begin
        
    hwDocsIf3CmtsCmDepartureReasonTable OBJECT-TYPE
        SYNTAX     SEQUENCE OF HwDocsIf3CmtsCmDepartureReasonEntry
        MAX-ACCESS not-accessible
        STATUS     current
        DESCRIPTION
            "
            Indicates the cable modem departure reason.
            The index of this table is docsIf3CmtsCmRegStatusId and hwDocsIf3CmtsCmDepartureReasonIndex.
            "
        ::= { hwCmtsAccessObject 78 }

    hwDocsIf3CmtsCmDepartureReasonEntry OBJECT-TYPE
        SYNTAX     HwDocsIf3CmtsCmDepartureReasonEntry
        MAX-ACCESS not-accessible
        STATUS     current
        DESCRIPTION
            "
            Indicates the cable modem departure reason.
            The index of this entry is docsIf3CmtsCmRegStatusId and hwDocsIf3CmtsCmDepartureReasonIndex.
            "
        INDEX       { docsIf3CmtsCmRegStatusId, hwDocsIf3CmtsCmDepartureReasonIndex  }
        ::= { hwDocsIf3CmtsCmDepartureReasonTable 1 }

    HwDocsIf3CmtsCmDepartureReasonEntry ::=
        SEQUENCE {
                 hwDocsIf3CmtsCmDepartureReasonIndex                    Integer32,
                 hwDocsIf3CmtsCmDepartureReasonTime                     DateAndTime,
                 hwDocsIf3CmtsCmDepartureReasonCode                     Integer32
        }
        
    hwDocsIf3CmtsCmDepartureReasonIndex OBJECT-TYPE
          SYNTAX  Integer32(0..31)
          MAX-ACCESS  not-accessible
          STATUS  current
          DESCRIPTION
                "Indicates the index of the hwDocsIf3CmtsCmDepartureReasonTable."
          ::= { hwDocsIf3CmtsCmDepartureReasonEntry 1 }
        
    hwDocsIf3CmtsCmDepartureReasonTime OBJECT-TYPE
            SYNTAX DateAndTime 
            MAX-ACCESS read-only
            STATUS current
            DESCRIPTION
                "Indicates the cable modem departure time. 
                 0 represents invalid value.               
                "
         ::= { hwDocsIf3CmtsCmDepartureReasonEntry 2 }

    hwDocsIf3CmtsCmDepartureReasonCode OBJECT-TYPE
            SYNTAX Integer32
            MAX-ACCESS read-only
            STATUS current
            DESCRIPTION
                "Indicates the cable modem departure reason code.
                1. POWER-ON(1)
                2. T17_LOST-SYNC(2)
                3. ALL_US_FAILED(3)
                4. BAD_DHCP_ACK(4)
                5. LINK_LOCAL_ADDRESS_IN_USE(5)
                6. T6_EXPIRED(6)
                7. REG_RSP_NOT_OK(7)
                8. BAD_RCC_TCC(8)
                9. FAILED_PRIM_DS(9)
                10. TCS_FAILED_ON_ALL_US(10)
                11. MTCM_CHANGE(15)
                12. T4_EXPIRED(16)
                13. NO_PRIM_SF_USCHAN(17)
                14. CM_CTRL_INIT(18)
                15. DYNAMIC-RANGE-WINDOW-VIOLATION(19)
                16. IP_PROV_MODE_OVERRIDE(20)
                17. SW_UPGRADE_REBOOT(21)
                18. SNMP_RESET(22)
                19. REG_RSP_MISSING_RCC(23)
                20. REG_RSP_MISSING_TCC(24)
                21. REG_RSP_MTC_NOT_ENABLED(25)
                22. DHCPv6_BAD_REPLY(26)
                23. Other reasons of NE rejection(1000)
                24. EAE authentication fail(1001)
                25. MIC authentication fail(1002)
                26. BPI authentication fail(1003)
                27. MAC address clone(1004)
                28. Exceed system spec(1005)
                29. CM MAC address not in whitelist(1006)
                30. DHCP fail(1007)
                31. System overload(1008)
                32. System resource not enough(1009)
                33. Service type override(1010)
                34. Reset CM(1011)
                35. Other reasons of board rejection(2000)
                36. Register ack message return fail(2001)
                37. Register ack message timeout(2002)
                38. Admission control reject(2003)
                39. Channel config modify(2004)
                40. Station maintenance range missing(2005)
                41. invalid value(-1)
                Note:If the departure reason is CM registration, the Error ID range is 1-999. 
                If the departure reason is that the NE does not allow the CM to go online, the Error ID range is 1000-1999. 
                If the departure reason is that the board does not allow the CM to go online, the Error ID range is 2000-2999.
                "
         ::= { hwDocsIf3CmtsCmDepartureReasonEntry 3 }         
        
    --Table hwDocsIf3CmtsCmDepartureReasonTable end   
 
    -- Table hwCmtsCmTrapCtrlTable Begin
    hwCmtsCmTrapCtrlTable OBJECT IDENTIFIER ::= {hwCmtsAccessObject 79}
    hwCmtsCmGlobalTrapOnline  OBJECT-TYPE
          SYNTAX   INTEGER
          {
           enable(1), 
           disable(2),
           firstEnable(3)
          }
          MAX-ACCESS read-write
          STATUS     current
          DESCRIPTION
               "Indicates the switch of reporting a trap when a CM goes online. 
          Options:
          1. enable(1)     -Enable the switch of reporting a trap when a CM goes online
          2. disable(2)    -Disable the switch of reporting a trap when a CM goes online
          3. firstEnable(3)   -Enable the switch of reporting a trap when a CM goes online for the first time
          Default: disable(2)
               "
          ::= { hwCmtsCmTrapCtrlTable 1 }

    hwCmtsCmGlobalTrapOffline  OBJECT-TYPE
          SYNTAX   INTEGER
          {
           enable(1), 
           disable(2)
          }
          MAX-ACCESS read-write
          STATUS     current
          DESCRIPTION
               "Indicates the switch of reporting a trap when a CM goes offline.  
          Options:
          1. enable(1)     -Enable the switch of reporting a trap when a CM goes offline
          2. disable(2)    -Disable the switch of reporting a trap when a CM goes offline
          Default: disable(2)
               "
          ::= { hwCmtsCmTrapCtrlTable 2 }
   
    -- Table hwCmtsCmTrapCtrlTable End 

-- Table hwCmtsCmTrapAlarmConfigTable begin
        
    hwCmtsCmTrapAlarmConfigTable OBJECT-TYPE
        SYNTAX     SEQUENCE OF HWCmtsCmTrapAlarmConfigEntry
        MAX-ACCESS not-accessible
        STATUS     current
        DESCRIPTION
            "This table describes the configuration of the CM online/offline trap switch and alarm switch.
            The index of this table is docsIf3CmtsCmRegStatusId.
            "
        ::= { hwCmtsAccessObject 80 }

    hwCmtsCmTrapAlarmConfigEntry OBJECT-TYPE
        SYNTAX     HWCmtsCmTrapAlarmConfigEntry
        MAX-ACCESS not-accessible
        STATUS     current
        DESCRIPTION
            "This table describes the configuration of the CM online/offline trap switch and alarm switch.
            The index of this entry is docsIf3CmtsCmRegStatusId.
            "
        INDEX       { docsIf3CmtsCmRegStatusId}
        ::= { hwCmtsCmTrapAlarmConfigTable 1 }              

    HWCmtsCmTrapAlarmConfigEntry ::=
        SEQUENCE {
                   hwCmtsCmTrapOnline INTEGER,
                   hwCmtsCmTrapOffline INTEGER,
                   hwCmtsCmAlarmOnOffline INTEGER,
                   hwCmtsCmAlarmDesc OCTET STRING,
                   hwCmtsCmTrapAlarmIfIndex Integer32
                 }

    hwCmtsCmTrapOnline  OBJECT-TYPE
          SYNTAX   INTEGER
          {
           global(1),
           enable(2), 
           disable(3)
          }
          MAX-ACCESS read-write
          STATUS     current
          DESCRIPTION
               "Indicates the switch of reporting a trap when a CM goes online. 
          Options:
          1. global(1)     -As same as the configuration of the leaf hwCmtsCmGlobalTrapOnline 
          2. enable(2)     -Enable the switch of reporting a trap when a CM goes online
          3. disable(3)    -Disable the switch of reporting a trap when a CM goes online
          Default: global(1)
               "
          ::= { hwCmtsCmTrapAlarmConfigEntry 1 }

    hwCmtsCmTrapOffline  OBJECT-TYPE
          SYNTAX   INTEGER
          {
           global(1),
           enable(2), 
           disable(3)
          }
          MAX-ACCESS read-write
          STATUS     current
          DESCRIPTION
               "Indicates the switch of reporting a trap when a CM goes offline. 
          Options:
          1. global(1)     -As same as the configuration of the leaf hwCmtsCmGlobalTrapOffline
          2. enable(2)     -Enable the switch of reporting a trap when a CM goes offline
          3. disable(3)    -Disable the switch of reporting a trap when a CM goes offline
          Default: global(1)
               "
          ::= { hwCmtsCmTrapAlarmConfigEntry 2 }

    hwCmtsCmAlarmOnOffline  OBJECT-TYPE
          SYNTAX   INTEGER
          {
           enable(1), 
           disable(2)
          }
          MAX-ACCESS read-write
          STATUS     current
          DESCRIPTION
               "Indicates the switch of reporting an alarm when a CM goes offline/online. 
          Options:
          1. enable(1)     -Enable the switch of reporting an alarm when a CM goes offline/online
          2. disable(2)    -Disable the switch of reporting an alarm when a CM goes offline/online
          Default: disable(2)
               "
          ::= { hwCmtsCmTrapAlarmConfigEntry 3 }
          
    hwCmtsCmAlarmDesc OBJECT-TYPE
          SYNTAX  OCTET STRING (SIZE (0..16))
          MAX-ACCESS  read-write
          STATUS  current
          DESCRIPTION
                "Indicates the description of CM.
                "
          ::= { hwCmtsCmTrapAlarmConfigEntry 4 } 
          
    hwCmtsCmTrapAlarmIfIndex OBJECT-TYPE
          SYNTAX     Integer32
          MAX-ACCESS read-only
          STATUS     current
          DESCRIPTION
               "Indicates the ifIndex of RF port for CM.
               "  
          ::= { hwCmtsCmTrapAlarmConfigEntry 5 }

 --Table hwCmtsCmTrapAlarmConfigTable end
 
    -- Table hwCmtsCablePerformanceCurrTable begin
    
    hwCmtsCablePerformanceCurrTable OBJECT-TYPE
          SYNTAX     SEQUENCE OF HwCmtsCablePerformanceCurrEntry
          MAX-ACCESS not-accessible
          STATUS     current
          DESCRIPTION
                "
                Indicates periodic performance statistics of the upstream channel and port.
                The index of this table is ifIndex.
                "
          ::= { hwCmtsAccessObject 81 }

    hwCmtsCablePerformanceCurrEntry OBJECT-TYPE
          SYNTAX     HwCmtsCablePerformanceCurrEntry
          MAX-ACCESS not-accessible
          STATUS     current
          DESCRIPTION
                "
                Indicates periodic performance statistics of the upstream channel and port.
                The index of this entry is ifIndex.
                "
          INDEX       { ifIndex }
          ::= { hwCmtsCablePerformanceCurrTable 1 }

    HwCmtsCablePerformanceCurrEntry ::=
          SEQUENCE {
                    hwCmtsCablePerformanceCurr15MStartTime                OCTET STRING,
                    hwCmtsCablePerformanceCurr15MElapsedTime              Integer32,
                    hwCmtsCablePerformanceCurr15MValidityFlag             Gauge32,
                    hwCmtsCablePerformanceCurr15MSuccessReg               Counter32,
                    hwCmtsCablePerformanceCurr15MFailReg                  Counter32,
                    hwCmtsCablePerformanceCurr15MRepeatReg                Counter32,
                    hwCmtsCablePerformanceCurr15MSuccessPeriodRng         Counter32,
                    hwCmtsCablePerformanceCurr15MPeriodRngLoss            Counter32,
                    hwCmtsCablePerformanceCurr15MSeriousPeriodRngLoss     Counter32,
                    hwCmtsCablePerformanceCurr15MPowerAdjust              Counter32,
                    hwCmtsCablePerformanceCurr15MSeriousPowerAdjust       Counter32,
                    hwCmtsCablePerformanceCurr1DayStartTime               OCTET STRING,
                    hwCmtsCablePerformanceCurr1DayElapsedTime             Integer32,
                    hwCmtsCablePerformanceCurr1DayValidityFlag            Gauge32,
                    hwCmtsCablePerformanceCurr1DaySuccessReg              Counter32,
                    hwCmtsCablePerformanceCurr1DayFailReg                 Counter32,
                    hwCmtsCablePerformanceCurr1DayRepeatReg               Counter32, 
                    hwCmtsCablePerformanceCurr1DaySuccessPeriodRng        Counter32,
                    hwCmtsCablePerformanceCurr1DayPeriodRngLoss           Counter32,
                    hwCmtsCablePerformanceCurr1DaySeriousPeriodRngLoss    Counter32,
                    hwCmtsCablePerformanceCurr1DayPowerAdjust             Counter32,
                    hwCmtsCablePerformanceCurr1DaySeriousPowerAdjust      Counter32,
                    hwCmtsCablePerformanceEverBeforeStartTime             OCTET STRING,
                    hwCmtsCablePerformanceEverBeforeElapsedTime           Integer32,
                    hwCmtsCablePerformanceEverBeforeValidityFlag          Gauge32,
                    hwCmtsCablePerformanceEverBeforeSuccessReg            Counter32,
                    hwCmtsCablePerformanceEverBeforeFailReg               Counter32,
                    hwCmtsCablePerformanceEverBeforeRepeatReg             Counter32,
                    hwCmtsCablePerformanceEverBeforeSuccessPeriodRng      Counter32,
                    hwCmtsCablePerformanceEverBeforePeriodRngLoss         Counter32,
                    hwCmtsCablePerformanceEverBeforeSeriousPeriodRngLoss  Counter32,
                    hwCmtsCablePerformanceEverBeforePowerAdjust           Counter32,
                    hwCmtsCablePerformanceEverBeforeSeriousPowerAdjust    Counter32
                   }

    hwCmtsCablePerformanceCurr15MStartTime OBJECT-TYPE
          SYNTAX  OCTET STRING
          MAX-ACCESS  read-only
          STATUS  current
          DESCRIPTION
                "
                Indicates the start time of the current 15-minute statistical period.
                "
          ::= { hwCmtsCablePerformanceCurrEntry 1 }
          
    hwCmtsCablePerformanceCurr15MElapsedTime OBJECT-TYPE
          SYNTAX  Integer32
          UNITS   "s"
          MAX-ACCESS  read-only
          STATUS  current
          DESCRIPTION
                "
                Indicates the elapsed time in the current 15-minute statistical period.
                -1 represents invalid value.
                "
          ::= { hwCmtsCablePerformanceCurrEntry 2 }
          
    hwCmtsCablePerformanceCurr15MValidityFlag OBJECT-TYPE
          SYNTAX  Gauge32 (1..2)
          MAX-ACCESS  read-only
          STATUS  current
          DESCRIPTION
                "
                Indicates the flag for statistical information.
                Options:
                1-Yes
                2-No
                "
          ::= { hwCmtsCablePerformanceCurrEntry 3 }                    

    hwCmtsCablePerformanceCurr15MSuccessReg OBJECT-TYPE
          SYNTAX  Counter32
          MAX-ACCESS  read-only
          STATUS  current
          DESCRIPTION
                "
                Indicates the number of registration request initiated by a CM during the current 15-minute.
                "
          ::= { hwCmtsCablePerformanceCurrEntry 4 }

    hwCmtsCablePerformanceCurr15MFailReg OBJECT-TYPE
          SYNTAX  Counter32
          MAX-ACCESS  read-only
          STATUS  current
          DESCRIPTION
                "
                Indicates the number of CM registration failure during the current 15-minute.
                "
          ::= { hwCmtsCablePerformanceCurrEntry 5 }

    hwCmtsCablePerformanceCurr15MRepeatReg OBJECT-TYPE
          SYNTAX  Counter32
          MAX-ACCESS  read-only
          STATUS  current
          DESCRIPTION
                "
                Indicates the number of repeated registration during the current 15-minute.
                "
          ::= { hwCmtsCablePerformanceCurrEntry 6 }
          
    hwCmtsCablePerformanceCurr15MSuccessPeriodRng OBJECT-TYPE
          SYNTAX  Counter32
          MAX-ACCESS  read-only
          STATUS  current
          DESCRIPTION
                "
                Indicates the number of successful periodic ranging request during the current 15-minute.
                4294967295 represents invalid value.
                "
          ::= { hwCmtsCablePerformanceCurrEntry 7 }

    hwCmtsCablePerformanceCurr15MPeriodRngLoss OBJECT-TYPE
          SYNTAX  Counter32
          MAX-ACCESS  read-only
          STATUS  current
          DESCRIPTION
                "
                Indicates the number of lost periodic ranging request during the current 15-minute.
                4294967295 represents invalid value.
                "
          ::= { hwCmtsCablePerformanceCurrEntry 8 }

    hwCmtsCablePerformanceCurr15MSeriousPeriodRngLoss OBJECT-TYPE
          SYNTAX  Counter32
          MAX-ACCESS  read-only
          STATUS  current
          DESCRIPTION
                "
                Indicates the number of consecutive periodic ranging request failure during the current 15-minute.
                4294967295 represents invalid value.
                "
          ::= { hwCmtsCablePerformanceCurrEntry 9 }

    hwCmtsCablePerformanceCurr15MPowerAdjust OBJECT-TYPE
          SYNTAX  Counter32
          MAX-ACCESS  read-only
          STATUS  current
          DESCRIPTION
                "
                Indicates the number of transmit power adjustment during the current 15-minute.
                4294967295 represents invalid value.
                "
          ::= { hwCmtsCablePerformanceCurrEntry 10 }

    hwCmtsCablePerformanceCurr15MSeriousPowerAdjust OBJECT-TYPE
          SYNTAX  Counter32
          MAX-ACCESS  read-only
          STATUS  current
          DESCRIPTION
                "
                Indicates the number of severe transmit power adjustment during the current 15-minute.
                4294967295 represents invalid value.
                "
          ::= { hwCmtsCablePerformanceCurrEntry 11 }          
    
    hwCmtsCablePerformanceCurr1DayStartTime OBJECT-TYPE
          SYNTAX  OCTET STRING
          MAX-ACCESS  read-only
          STATUS  current
          DESCRIPTION
                "
                Indicates the start time of the current 24-hour statistical period.
                "
          ::= { hwCmtsCablePerformanceCurrEntry 12 }
          
    hwCmtsCablePerformanceCurr1DayElapsedTime OBJECT-TYPE
          SYNTAX  Integer32
          UNITS   "s"
          MAX-ACCESS  read-only
          STATUS  current
          DESCRIPTION
                "
                Indicates the elapsed time in the current 24-hour statistical period.
                -1 represents invalid value.
                "
          ::= { hwCmtsCablePerformanceCurrEntry 13 }          

    hwCmtsCablePerformanceCurr1DayValidityFlag OBJECT-TYPE
          SYNTAX  Gauge32 (1..2)
          MAX-ACCESS  read-only
          STATUS  current
          DESCRIPTION
                "
                Indicates the flag for statistical information.
                Options:
                1-Yes
                2-No
                "
          ::= { hwCmtsCablePerformanceCurrEntry 14 }          
    
    hwCmtsCablePerformanceCurr1DaySuccessReg  OBJECT-TYPE
          SYNTAX  Counter32
          MAX-ACCESS  read-only
          STATUS  current
          DESCRIPTION
                "
                Indicates the number of registration request initiated by a CM during the current 24-hour.
                "
          ::= { hwCmtsCablePerformanceCurrEntry 15 }

    hwCmtsCablePerformanceCurr1DayFailReg OBJECT-TYPE
          SYNTAX  Counter32
          MAX-ACCESS  read-only
          STATUS  current
          DESCRIPTION
                "
                Indicates the number of CM registration failure during the current 24-hour.
                "
          ::= { hwCmtsCablePerformanceCurrEntry 16 }

    hwCmtsCablePerformanceCurr1DayRepeatReg OBJECT-TYPE
          SYNTAX  Counter32
          MAX-ACCESS  read-only
          STATUS  current
          DESCRIPTION
                "
                Indicates the number of repeated registration during the current 24-hour.
                "
          ::= { hwCmtsCablePerformanceCurrEntry 17 }
          
    hwCmtsCablePerformanceCurr1DaySuccessPeriodRng OBJECT-TYPE
          SYNTAX  Counter32
          MAX-ACCESS  read-only
          STATUS  current
          DESCRIPTION
                "
                Indicates the number of successful periodic ranging request during the current 24-hour.
                4294967295 represents invalid value.
                "
          ::= { hwCmtsCablePerformanceCurrEntry 18 }

    hwCmtsCablePerformanceCurr1DayPeriodRngLoss OBJECT-TYPE
          SYNTAX  Counter32
          MAX-ACCESS  read-only
          STATUS  current
          DESCRIPTION
                "
                Indicates the number of lost periodic ranging request during the current 24-hour.
                4294967295 represents invalid value.
                "
          ::= { hwCmtsCablePerformanceCurrEntry 19 }

    hwCmtsCablePerformanceCurr1DaySeriousPeriodRngLoss OBJECT-TYPE
          SYNTAX  Counter32
          MAX-ACCESS  read-only
          STATUS  current
          DESCRIPTION
                "
                Indicates the number of consecutive periodic ranging request failure during the current 24-hour.
                4294967295 represents invalid value.
                "
          ::= { hwCmtsCablePerformanceCurrEntry 20 }

    hwCmtsCablePerformanceCurr1DayPowerAdjust OBJECT-TYPE
          SYNTAX  Counter32
          MAX-ACCESS  read-only
          STATUS  current
          DESCRIPTION
                "
                Indicates the number of transmit power adjustment during the current 24-hour.
                4294967295 represents invalid value.
                "
          ::= { hwCmtsCablePerformanceCurrEntry 21 }

    hwCmtsCablePerformanceCurr1DaySeriousPowerAdjust OBJECT-TYPE
          SYNTAX  Counter32
          MAX-ACCESS  read-only
          STATUS  current
          DESCRIPTION
                "
                Indicates the number of severe transmit power adjustment during the current 24-hour.
                4294967295 represents invalid value.
                "
          ::= { hwCmtsCablePerformanceCurrEntry 22 }          
    
    hwCmtsCablePerformanceEverBeforeStartTime  OBJECT-TYPE
          SYNTAX  OCTET STRING
          MAX-ACCESS  read-only
          STATUS  current
          DESCRIPTION
                "
                Indicates the start time of the statistical period.
                "
          ::= { hwCmtsCablePerformanceCurrEntry 23 }
          
    hwCmtsCablePerformanceEverBeforeElapsedTime OBJECT-TYPE
          SYNTAX  Integer32
          UNITS   "s"
          MAX-ACCESS  read-only
          STATUS  current
          DESCRIPTION
                "
                Indicates the elapsed time in the statistical period.
                -1 represents invalid value.
                "
          ::= { hwCmtsCablePerformanceCurrEntry 24 }          
    
    hwCmtsCablePerformanceEverBeforeValidityFlag OBJECT-TYPE
          SYNTAX  Gauge32 (1..2)
          MAX-ACCESS  read-only
          STATUS  current
          DESCRIPTION
                "
                Indicates the flag for statistical information.
                Options:
                1-Yes
                2-No
                "
          ::= { hwCmtsCablePerformanceCurrEntry 25 }
              
    hwCmtsCablePerformanceEverBeforeSuccessReg OBJECT-TYPE
          SYNTAX  Counter32
          MAX-ACCESS  read-only
          STATUS  current
          DESCRIPTION
                "
                Indicates the number of previous successfully registered.
                "
          ::= { hwCmtsCablePerformanceCurrEntry 26 }

    hwCmtsCablePerformanceEverBeforeFailReg OBJECT-TYPE
          SYNTAX  Counter32
          MAX-ACCESS  read-only
          STATUS  current
          DESCRIPTION
                "
                Indicates the number of previous registration failed.
                "
          ::= { hwCmtsCablePerformanceCurrEntry 27 }

    hwCmtsCablePerformanceEverBeforeRepeatReg OBJECT-TYPE
          SYNTAX  Counter32
          MAX-ACCESS  read-only
          STATUS  current
          DESCRIPTION
                "
                Indicates the number of previous repeated registration.
                "
          ::= { hwCmtsCablePerformanceCurrEntry 28 }
          
    hwCmtsCablePerformanceEverBeforeSuccessPeriodRng OBJECT-TYPE
          SYNTAX  Counter32
          MAX-ACCESS  read-only
          STATUS  current
          DESCRIPTION
                "
                Indicates the number of previous successful periodic ranging request.
                4294967295 represents invalid value.
                "
          ::= { hwCmtsCablePerformanceCurrEntry 29 }

    hwCmtsCablePerformanceEverBeforePeriodRngLoss OBJECT-TYPE
          SYNTAX  Counter32
          MAX-ACCESS  read-only
          STATUS  current
          DESCRIPTION
                "
                Indicates the number of previous loss of periodic ranging request.
                4294967295 represents invalid value.
                "
          ::= { hwCmtsCablePerformanceCurrEntry 30 }

    hwCmtsCablePerformanceEverBeforeSeriousPeriodRngLoss OBJECT-TYPE
          SYNTAX  Counter32
          MAX-ACCESS  read-only
          STATUS  current
          DESCRIPTION
                "
                Indicates the number of previous loss of the consecutive periodic ranging request.
                4294967295 represents invalid value.
                "
          ::= { hwCmtsCablePerformanceCurrEntry 31 }

    hwCmtsCablePerformanceEverBeforePowerAdjust OBJECT-TYPE
          SYNTAX  Counter32
          MAX-ACCESS  read-only
          STATUS  current
          DESCRIPTION
                "
                Indicates the number of previous transmit power adjustment.
                4294967295 represents invalid value.
                "
          ::= { hwCmtsCablePerformanceCurrEntry 32 }

    hwCmtsCablePerformanceEverBeforeSeriousPowerAdjust OBJECT-TYPE
          SYNTAX  Counter32
          MAX-ACCESS  read-only
          STATUS  current
          DESCRIPTION
                " 
                Indicates the number of previous severe power adjustment.
                4294967295 represents invalid value.
                "
          ::= { hwCmtsCablePerformanceCurrEntry 33 }          
         
    -- Table hwCmtsCablePerformanceCurrTable end
    
    -- Table hwDocsCmtsOssAdaptSwitchTable begin
    hwDocsCmtsOssAdaptSwitchTable OBJECT IDENTIFIER ::= {hwCmtsAccessObject 82}
    hwDocsCmtsOssAdaptCmStateSwitch  OBJECT-TYPE
          SYNTAX   INTEGER
          {
           standard(1), 
           extended(2)
          }
          MAX-ACCESS read-write
          STATUS     current
          DESCRIPTION
               "Indicates the adaption switch to control the returned value of node docsIfCmtsCmStatusValue when the CM is online. 
          Options:
          1. standard(1)   -The returned value of docsIfCmtsCmStatusValue is registrationComplete(6) when the switch is standard
          2. extended(2)   -The returned value of docsIfCmtsCmStatusValue is operational(8) when the switch is extended
          Default: extended(2)
               "
          ::= { hwDocsCmtsOssAdaptSwitchTable 1 }

    hwDocsCmtsOssAdaptCmUsIndexSwitch  OBJECT-TYPE
          SYNTAX   INTEGER
          {
           standard(1), 
           extended(2)
          }
          MAX-ACCESS read-write
          STATUS     current
          DESCRIPTION
               "Indicates the adaption switch to control the returned value of node docsIf3CmtsCmUsStatusChIfIndex. 
          Options:
          1. standard(1)   -The returned value of docsIf3CmtsCmUsStatusChIfIndex is channel ifIndex when the switch is standard
          2. extended(2)   -The returned value of docsIf3CmtsCmUsStatusChIfIndex is channel ID when the switch is extended
          Default: extended(2)
               "
          ::= { hwDocsCmtsOssAdaptSwitchTable 2 }

    -- Table hwDocsCmtsOssAdaptSwitchTable end 
    
    -- Table hwDocsPnmBulkCtlTable begin 
    hwDocsPnmBulkCtlTable OBJECT IDENTIFIER  ::= {hwCmtsAccessObject 83}
    hwDocsPnmBulkTransProtocol  OBJECT-TYPE
          SYNTAX  INTEGER
          {
           tftp(1),
           ftp(2),
           sftp(3)
          }
          MAX-ACCESS  read-write
          STATUS  current
          DESCRIPTION
                "
                Indicates the transport protocol for the pnm server. 
                Options:
                1. tftp(1)-indicates that TFTP is used to perform the backup through the network port.
                           Select tftp(1) when the transport protocol of the pnm server is configured to TFTP.
                           When TFTP is used for backup, you need not enter the user name (hwDocsPnmBulkUserName)
                           and the password (hwDocsPnmBulkUserPassword).
                2. ftp(2) -indicates that FTP is used to perform the backup through the network port.
                           Select ftp(2) when the transport protocol of the pnm server is configured to FTP.
                           When FTP is used for the backup, you need to enter the user name (hwDocsPnmBulkUserName)
                           and the password (hwDocsPnmBulkUserPassword).
                3. sftp(3)-indicates that SFTP is used to perform the backup through the network port.
                           Select sftp(3) when the transport protocol of the pnm server is configured to SFTP.
                           When SFTP is used for backup, you need to enter the user name (hwDocsPnmBulkUserName)
                           and the password (hwDocsPnmBulkUserPassword).
                           The instructions and data are encrypted during transmission. 
                The SFTP transport protocol is recommended.        
                Default: tftp(1)
                "
          ::= { hwDocsPnmBulkCtlTable 1 }
          
    hwDocsPnmBulkTransPort  OBJECT-TYPE
          SYNTAX Integer32 (1..65535)
          MAX-ACCESS  read-write
          STATUS  current
          DESCRIPTION
                "
                Port number. It is only used by SFTP.
                Default: 22
                "
          ::= { hwDocsPnmBulkCtlTable 2 } 
          
    hwDocsPnmBulkUserName  OBJECT-TYPE
          SYNTAX OCTET STRING (SIZE (0..40))
          MAX-ACCESS  read-write
          STATUS  current
          DESCRIPTION
                "
                The backup user name, which is required in FTP mode and SFTP mode
                but is not required in TFTP mode. 
                "
          ::= { hwDocsPnmBulkCtlTable 3 } 
          
    hwDocsPnmBulkUserPassword  OBJECT-TYPE
          SYNTAX OCTET STRING (SIZE (0..40))
          MAX-ACCESS  read-write
          STATUS  current
          DESCRIPTION
                "
                The backup password, which is required in FTP mode and SFTP mode
                but is not required in TFTP mode.
                The password is encrypted in data base.
                "
          ::= { hwDocsPnmBulkCtlTable 4 }
    -- Table hwDocsPnmBulkCtlTable end 

  --Table hwCmtsUsCalibrationCfgTable begin

    hwCmtsUsCalibrationCfgTable OBJECT-TYPE
        SYNTAX     SEQUENCE OF HwCmtsUsCalibrationCfgEntry
        MAX-ACCESS not-accessible
        STATUS     current
        DESCRIPTION
            "Indicates the upstream calibration function.
            The index of this table is cable port ifIndex.
            "
        ::= { hwCmtsAccessObject 84 }

    hwCmtsUsCalibrationCfgEntry OBJECT-TYPE
        SYNTAX     HwCmtsUsCalibrationCfgEntry
        MAX-ACCESS not-accessible
        STATUS     current
        DESCRIPTION
            "Indicates the upstream calibration function.
            The index of this entry is cable port ifIndex.
            "
        INDEX       { ifIndex }
        ::= { hwCmtsUsCalibrationCfgTable 1 }

    HwCmtsUsCalibrationCfgEntry ::=
        SEQUENCE {
                 hwCmtsUsCalibrationSwitch INTEGER,
                 hwCmtsUsCalibrationMode INTEGER,
                 hwCmtsUsCalibrationResolution INTEGER,
                 hwCmtsUsCalibrationSampleTime INTEGER,
                 hwCmtsUsCalibrationUsSgId Integer32,
                 hwCmtsUsCalibrationFrequencyList OCTET STRING
        }
        
    hwCmtsUsCalibrationSwitch OBJECT-TYPE
            SYNTAX  INTEGER{enable(1),disable(2)}
            MAX-ACCESS read-write
            STATUS current
            DESCRIPTION
                "Indicates the upstream calibration function.
                Default:disable(2)
                Options:
                1. enable(1) - Indicates the upstream calibration function is enable
                2. disable(2) - Indicates the upstream calibration function is disable
                "
         ::= { hwCmtsUsCalibrationCfgEntry 1 }
   
    hwCmtsUsCalibrationMode OBJECT-TYPE
            SYNTAX  INTEGER{noise(1),freeRunning(2),invalid(-1)}
            MAX-ACCESS read-write
            STATUS current
            DESCRIPTION
                "Indicates the upstream calibration mode.
                Default:noise(1)
                Options:
                1. noise(1) -Scanning noise frequency calibration
                2. freeRunning(2) -Scanning noise or carrier frequency calibration
                5. invalid(-1) -Invalid               
                "
         ::= { hwCmtsUsCalibrationCfgEntry 2 }
     
    hwCmtsUsCalibrationResolution OBJECT-TYPE
            SYNTAX INTEGER{hz50K(1), 
                           hz100K(2),
                           hz150K(3),
                           hz200K(4),
                           hz250K(5),
                           hz300K(6),
                           hz350K(7),
                           hz400K(8),
                           hz450K(9),
                           hz500K(10),
                           hz60K(11), 
                           hz120K(12),
                           hz180K(13),
                           hz240K(14),
                           hz360K(15),
                           hz420K(16),
                           hz480K(17),
                           hz540K(18),
                           hz600K(19),
                           hz1200K(20),                        
                           invalid(-1)}
            MAX-ACCESS read-write
            STATUS current
            DESCRIPTION
                "Indicates the upstream calibration resolution.
                 Default: hz300K(6)
                 Options:
                 1. hz50K(1)       - Sets the upstream calibration resolution to 50Khz
                 2. hz100K(2)      - Sets the upstream calibration resolution to 100Khz
                 3. hz150K(3)      - Sets the upstream calibration resolution to 150Khz
                 4. hz200K(4)      - Sets the upstream calibration resolution to 200Khz
                 5. hz250K(5)      - Sets the upstream calibration resolution to 250Khz
                 6. hz300K(6)      - Sets the upstream calibration resolution to 300Khz
                 7. hz350K(7)      - Sets the upstream calibration resolution to 350Khz
                 8. hz400K(8)      - Sets the upstream calibration resolution to 400Khz
                 9. hz450K(9)      - Sets the upstream calibration resolution to 450Khz
                 10. hz500K(10)    - Sets the upstream calibration resolution to 500Khz
                 11. hz60K(11)     - Sets the upstream calibration resolution to 60Khz
                 12. hz120K(12)    - Sets the upstream calibration resolution to 120Khz
                 13. hz180K(13)    - Sets the upstream calibration resolution to 180Khz
                 14. hz240K(14)    - Sets the upstream calibration resolution to 240Khz
                 15. hz360K(15)    - Sets the upstream calibration resolution to 360Khz
                 16. hz420K(16)    - Sets the upstream calibration resolution to 420Khz
                 17. hz480K(17)    - Sets the upstream calibration resolution to 480Khz
                 18. hz540K(18)    - Sets the upstream calibration resolution to 540Khz
                 19. hz600K(19)    - Sets the upstream calibration resolution to 600Khz
                 20. hz1200K(20)   - Sets the upstream calibration resolution to 1200Khz               
                 21. invalid(-1)   - Invalid value
                "
         ::= { hwCmtsUsCalibrationCfgEntry 3 }

    hwCmtsUsCalibrationSampleTime OBJECT-TYPE
            SYNTAX INTEGER{ms1000(1),
                           invalid(-1)}
            MAX-ACCESS read-write
            STATUS current
            DESCRIPTION
                "Indicates the upstream calibration period.
                 Default: ms1000(1).
                 Options:
                 1. ms1000(10) - Sets the upstream calibration period to 1000ms
                 2. invalid(-1) - Getting is invalid
                "
         ::= { hwCmtsUsCalibrationCfgEntry 4 }
                 
     hwCmtsUsCalibrationUsSgId OBJECT-TYPE
          SYNTAX  Integer32(1..2)
          MAX-ACCESS  read-write
          STATUS  current
          DESCRIPTION
                "
                Indicates the US-SG-ID for the upstream calibration.
                Default: 1
                "
          ::= { hwCmtsUsCalibrationCfgEntry 5 }

    hwCmtsUsCalibrationFrequencyList OBJECT-TYPE
            SYNTAX      OCTET STRING (SIZE(0 | 1..8000))
            UNITS   "Hz"
            MAX-ACCESS read-write
            STATUS current
            DESCRIPTION
                "The frequency list for the upstream calibration scanning.
                 It can contain as most as 50 frequencies.
                 Every 10 octets represent a frequency,
                 (,) used to indicate a separation of the different frequencies.
                "
         ::= { hwCmtsUsCalibrationCfgEntry 6 }
              
    --Table hwCmtsUsCalibrationCfgTable end

-- Table hwCmtsUsSpectrumUdpCfgTable Begin
    hwCmtsUsSpectrumUdpCfgTable OBJECT IDENTIFIER ::= {hwCmtsAccessObject 85}
    
    hwCmtsUsSpectrumUdpDestIpAddrType OBJECT-TYPE
        SYNTAX InetAddressType
        MAX-ACCESS read-write
        STATUS current
        DESCRIPTION
            "
            Indicates the Destination IP address type.
            Options:
            1. unknown(0)   -invalid value
            2. ipv4(1)      -indicates that the IP address type is ipv4
            3. ipv6(2)      -indicates that the IP address type is ipv6
            4. ipv4z(3)     -indicates that the IP address type is ipv4z
            5. ipv6z(4)     -indicates that the IP address type is ipv6z
            6. dns(16)      -indicates that the IP address type is dns         
            "
        ::= { hwCmtsUsSpectrumUdpCfgTable 1 }
        
     hwCmtsUsSpectrumUdpDestIpAddr OBJECT-TYPE
      SYNTAX InetAddress
      MAX-ACCESS read-write
      STATUS current
      DESCRIPTION
          "
          Indicates the Destination IP address.
          "
      ::= { hwCmtsUsSpectrumUdpCfgTable 2 }

     hwCmtsUsSpectrumUdpDestPort OBJECT-TYPE
      SYNTAX Integer32 (-1|0..65535)
      MAX-ACCESS read-write
      STATUS current
      DESCRIPTION
          "
          Indicates the Destination Port.
          -1 represents invalid value.
          "
      ::= { hwCmtsUsSpectrumUdpCfgTable 3 }

    hwCmtsUsSpectrumUdpSourceIpAddrType OBJECT-TYPE
        SYNTAX InetAddressType
        MAX-ACCESS read-write
        STATUS current
        DESCRIPTION
            "
            Indicates the Source IP address type.
            Options:
            1. unknown(0)   -invalid value
            2. ipv4(1)      -indicates that the IP address type is ipv4
            3. ipv6(2)      -indicates that the IP address type is ipv6
            4. ipv4z(3)     -indicates that the IP address type is ipv4z
            5. ipv6z(4)     -indicates that the IP address type is ipv6z
            6. dns(16)      -indicates that the IP address type is dns            
            "
        ::= { hwCmtsUsSpectrumUdpCfgTable 4 }
        
     hwCmtsUsSpectrumUdpSourceIpAddr OBJECT-TYPE
      SYNTAX InetAddress
      MAX-ACCESS read-write
      STATUS current
      DESCRIPTION
          "
          Indicates the Source IP address.
          "
      ::= { hwCmtsUsSpectrumUdpCfgTable 5 }

     hwCmtsUsSpectrumUdpPassword OBJECT-TYPE
          SYNTAX  OCTET STRING (SIZE (0..32))
          MAX-ACCESS  read-write
          STATUS  current
          DESCRIPTION
                "Authentication password.
                "
          ::= { hwCmtsUsSpectrumUdpCfgTable 6 }
          
    hwCmtsUsSpectrumUdpRetransTime OBJECT-TYPE
          SYNTAX  Integer32 (0..2)
          MAX-ACCESS  read-write
          STATUS  current
          DESCRIPTION
                "
                Indicates the retransmission limit.
                Options:
                0.no retransmission(0)
                1.retransfer once(1)
                2.retransfer twice(2)
                Default: no retransmission(0)
                "
          ::= { hwCmtsUsSpectrumUdpCfgTable 7 }  
     
    -- Table hwCmtsUsSpectrumUdpCfgTable End  
    
    -- Table hwDocsPnmCmtsUsFecStatisticTable begin
   
    hwDocsPnmCmtsUsFecStatisticTable  OBJECT-TYPE
          SYNTAX      SEQUENCE OF HwDocsPnmCmtsUsFecStatisticEntry
          MAX-ACCESS  not-accessible
          STATUS      current
          DESCRIPTION
                "
                Indicates FEC statistics of the upstream channel and port.
                The index of this table is ifIndex.
                "
          ::= { hwCmtsAccessObject 86 }
          
    hwDocsPnmCmtsUsFecStatisticEntry  OBJECT-TYPE
          SYNTAX      HwDocsPnmCmtsUsFecStatisticEntry
          MAX-ACCESS  not-accessible
          STATUS      current
          DESCRIPTION
                "
                Indicates FEC statistics of the upstream channel and port.
                The index of this entry is ifIndex.
                "
          INDEX      { ifIndex }
          ::= { hwDocsPnmCmtsUsFecStatisticTable 1 }
          
   HwDocsPnmCmtsUsFecStatisticEntry ::=
       SEQUENCE{
          hwDocsPnmCmtsUsFecStatisticEnable       TruthValue,
          hwDocsPnmCmtsUsFecStatisticCmMacAddr    MacAddress,
          hwDocsPnmCmtsUsFecStatisticTimeout      Unsigned32,
          hwDocsPnmCmtsUsFecStatisticTimeStamp    OCTET STRING,
          hwDocsPnmCmtsUsFecStatisticFecSeconds   Unsigned32,
          hwDocsPnmCmtsUsFecStatisticMeasStatus   MeasStatusType,
          hwDocsPnmCmtsUsFecStatisticFileName     SnmpAdminString
      }
      
   hwDocsPnmCmtsUsFecStatisticEnable    OBJECT-TYPE
      SYNTAX      TruthValue
      MAX-ACCESS  read-write
      STATUS      current
      DESCRIPTION
          "Setting this object to a value of 'true' instructs the CMTS to begin
          collection of FEC Statistic data and when enabled, the CMTS continues
          producing new data at its own rate.
          
          This value is only allowed to be set to 'true' if the value of
          'hwDocsPnmCmtsUsFecStatisticMeasStatus' is a value other than 'busy'.
                    
          Setting this object to a value of 'false' instructs the CM to stop
          the collection of FEC Statistic data.
          
          This object returns 'true' if the CMTS is actively collecting FEC Statistic
          data. Otherwise it returns 'false'.
          
          Interaction with other table rows:

          - This object returns 'inconsistentValue' if set to 'true' while the
          value of 'hwDocsPnmCmtsUsFecStatisticMeasStatus' is a value of 'busy'.
          
          - Default values are provided for read-write objects in this table; thus,
          this object may be set to 'true' without explicitly setting these values.
          However, the default values may not be appropriate and care should be
          taken to insure these values are correct for the desired test case.

          - Setting this value to 'true' will change the value of the 
          'hwDocsPnmCmtsUsFecStatisticMeasStatus' to 'busy'.
          "
      REFERENCE
         "DOCSIS 3.1 CCAP Operations Support System Interface Specification, 
         CM-SP-CCAP-OSSIv3.1, PNM section."
      DEFVAL      { false }
      ::= { hwDocsPnmCmtsUsFecStatisticEntry 1 }
      
  hwDocsPnmCmtsUsFecStatisticCmMacAddr  OBJECT-TYPE
      SYNTAX      MacAddress  
      MAX-ACCESS  read-write
      STATUS      current
      DESCRIPTION
          "This attribute represents the MAC address of the CM whose FEC Statistic
          is being measured.
          
          This object cannot be changed while a capture is in progress. It will 
          return a value of 'inconsistentValue' if set while the value of 
          'hwDocsPnmCmtsUsFecStatisticMeasStatus' is set to a value of 'busy'.
          "
      REFERENCE
          "DOCSIS 3.1 CCAP Operations Support System Interface Specification, 
          CM-SP-CCAP-OSSIv3.1, PNM section."
      DEFVAL { '000000000000'H } 
      ::= { hwDocsPnmCmtsUsFecStatisticEntry 2 }
      
  hwDocsPnmCmtsUsFecStatisticTimeout    OBJECT-TYPE
      SYNTAX      Unsigned32  (0..600)
      UNITS       "seconds"
      MAX-ACCESS  read-write
      STATUS      current
      DESCRIPTION
          "This object sets a seconds time-out timer for capturing FEC Statistic data.
          
          When the timeout expires the 'hwDocsPnmCmtsUsFecStatisticEnable' object will be 
          set to 'false' and the capture will stop. When this happens, the data collected 
          up to this point will be saved in the the file defined by the 'hwDocsPnmCmtsUsFec-
          StatisticFileName', and the value of 'hwDcsPnmCmtsUsFecStatisticMeasStatus'will 
          be set to 'sampleReady'.
          
          Setting this value does not start a capture. Captures can only be started by
          setting the 'hwDocsPnmCmtsUsFecStatisticEnable' object.
          
          If this object is written while the 'hwDocsPnmCmtsUsFecStatisticEnable' object 
          is 'true', and will return a value of 'inconsistentValue'.
          
          If this object is set to a value of 'zero', there is no timeout and the collection 
          of data will continue indefinitely until 'hwDocsPnmCmtsUsFecStatisticEnable' is 
          set to 'false'. "
          
      REFERENCE
         "DOCSIS 3.1 CCAP Operations Support System Interface Specification, 
         CM-SP-CCAP-OSSIv3.1, PNM section."
      DEFVAL { 180 }
      ::= { hwDocsPnmCmtsUsFecStatisticEntry 3 }
      
  hwDocsPnmCmtsUsFecStatisticTimeStamp  OBJECT-TYPE
      SYNTAX      OCTET STRING (SIZE(8))
      UNITS       "seconds"
      MAX-ACCESS  read-only
      STATUS      current
      DESCRIPTION
          "This attribute represents the time when the collection of FEC Statistic 
          data was monitored/started. the timestamp is defined as the number of seconds 
          that have elapsed since midnight Coordinated Universal Time(UTC), Thursday, 
          1 January 1970.
          "
      REFERENCE
         "DOCSIS 3.1 CCAP Operations Support System Interface Specification, 
         CM-SP-CCAP-OSSIv3.1, PNM section."
      ::= { hwDocsPnmCmtsUsFecStatisticEntry 4 }
       
  hwDocsPnmCmtsUsFecStatisticFecSeconds OBJECT-TYPE
      SYNTAX      Unsigned32
      UNITS       "seconds"
      MAX-ACCESS  read-only
      STATUS      current
      DESCRIPTION
          "This attribute indicates the number of seconds of uncorrectable FEC code.
          "
      REFERENCE
         "DOCSIS 3.1 CCAP Operations Support System Interface Specification, 
         CM-SP-CCAP-OSSIv3.1, PNM section."
      ::= { hwDocsPnmCmtsUsFecStatisticEntry 5 }
      
  hwDocsPnmCmtsUsFecStatisticMeasStatus OBJECT-TYPE 
      SYNTAX      MeasStatusType
      MAX-ACCESS  read-only
      STATUS      current
      DESCRIPTION
          "This attribute is used to determine the status of the measurement,
          The PNM server will query this value to determine when the file
          is ready for tranfer.
          "
      REFERENCE
         "DOCSIS 3.1 CCAP Operations Support System Interface Specification, 
         CM-SP-CCAP-OSSIv3.1, PNM section."
      ::= { hwDocsPnmCmtsUsFecStatisticEntry 6 }
      
  hwDocsPnmCmtsUsFecStatisticFileName   OBJECT-TYPE
      SYNTAX      SnmpAdminString
      MAX-ACCESS  read-write
      STATUS      current
      DESCRIPTION
          "This object is the name of the file at the CMTS which is to be 
          transferred to the PNM server. The data is stored as 32 bit integers 
          for the hit and dwell count values. This value can only be changed 
          while a test is not in progress. An attempt to set this value while the 
          value of 'hwDocsPnmCmtsUsHistMeasStatus' is 'busy' will return 
          'inconsistentValue'.

          If the value of this object is the DEFVAL (empty string), then a 
          default filename value will be used. Otherwise the value set will be 
          used as the filename.

          If a default filename value is used, it is generated as the test name 
          plus the CMTS MAC Address plus the 'epoch time'. The epoch time (also known 
          as 'unix time') is defined as the number of seconds that have elapsed 
          since midnight Coordinated Universal Time (UTC),Thursday, 1 January 1970.
          Hence, the format would be:

                            PNMFecSum_<CCAPID>_<epoch> 

          Syntax of the file is as follows:
           File Type set to '00000001' (without the quotes)      4 bytes
           Capture Time                                          4 bytes
           ifIndex                                               4 bytes
           Unique CCAP ID                                      256 bytes
           CM MAC Address                                        6 bytes
           TestStartTimestamp                                    4 bytes
           TestEndTimestamp                                      4 bytes
           Total fec second                                      2 bytes
           Length (in bytes) of the FEC Data                     2 bytes
           Total Codewords                               (600) * 4 bytes
           Corrected Codewords                           (600) * 4 bytes
           Uncorrectable Codewords                       (600) * 4 bytes
          "
      REFERENCE
         "DOCSIS 3.1 CCAP Operations Support System Interface Specification, 
         CM-SP-CCAP-OSSIv3.1, PNM section."
      DEFVAL { "" }
      ::= { hwDocsPnmCmtsUsFecStatisticEntry 7 }
          
   -- Table hwDocsPnmCmtsUsFecStatisticTable end
   
    -- Table hwCmtsRfPowerDsAmpGroupTable Begin
    hwCmtsRfPowerDsAmpGroupTable OBJECT-TYPE
          SYNTAX     SEQUENCE OF HwCmtsRfPowerDsAmpGroupEntry
          MAX-ACCESS not-accessible
          STATUS     current
          DESCRIPTION
               "This table describes the work mode of downstream group rf power amplifier.
               The indexes of this table are hwFrameIndex and hwCmtsRfPowerDsAmpGroupId."
          ::= { hwCmtsAccessObject 89 }  
    
    hwCmtsRfPowerDsAmpGroupEntry OBJECT-TYPE
          SYNTAX     HwCmtsRfPowerDsAmpGroupEntry
          MAX-ACCESS not-accessible
          STATUS     current
          DESCRIPTION
               "This table describes the work mode of downstream group rf power amplifier.
               The indexes of this entry are hwFrameIndex and hwCmtsRfPowerDsAmpGroupId."
          INDEX       { hwFrameIndex, hwCmtsRfPowerDsAmpGroupId }
          ::= { hwCmtsRfPowerDsAmpGroupTable 1 }
          
    HwCmtsRfPowerDsAmpGroupEntry ::=
          SEQUENCE {
                    hwCmtsRfPowerDsAmpGroupId          Integer32,
                    hwCmtsRfPowerDsGroupAmpConfigMode  INTEGER,
                    hwCmtsRfPowerDsGroupAmpStatusMode  INTEGER
                   }

    hwCmtsRfPowerDsAmpGroupId OBJECT-TYPE
          SYNTAX     Integer32(1..4) 
          MAX-ACCESS not-accessible
          STATUS     current
          DESCRIPTION
                "Indicates the group ID."
          ::= { hwCmtsRfPowerDsAmpGroupEntry 1 }

    hwCmtsRfPowerDsGroupAmpConfigMode OBJECT-TYPE
          SYNTAX     INTEGER {
                               highQuality(1),
                               balance(2),
                               lowPower(3)
                              }
          MAX-ACCESS read-write
          STATUS     current
          DESCRIPTION
                "Indicates the configuration value of work mode of downstream group rf power amplifier."
          DEFVAL       { balance }
          ::= { hwCmtsRfPowerDsAmpGroupEntry 2 }

    hwCmtsRfPowerDsGroupAmpStatusMode OBJECT-TYPE
           SYNTAX INTEGER{
                            highQuality(1),
                            balance(2),
                            lowPower(3),
                            invalid(-1)
                          }
           MAX-ACCESS read-only
           STATUS current
           DESCRIPTION
                "Indicates the actual value of work mode of downstream group rf power amplifier."
          ::= { hwCmtsRfPowerDsAmpGroupEntry 3 }     
              
  -- Table hwCmtsRfPowerDsAmpGroupTable End 
   
   -- Table hwCmtsDownstreamSweepTable Begin
    
  hwCmtsDownstreamSweepTable OBJECT-TYPE
      SYNTAX      SEQUENCE OF HwCmtsDownstreamSweepEntry
      MAX-ACCESS  not-accessible
      STATUS      current
      DESCRIPTION
            "
            Indicates a downstream sweeping table.
            The index of this table is cable port ifIndex.
            "
      ::= { hwCmtsAccessObject 90 }
      
  hwCmtsDownstreamSweepEntry OBJECT-TYPE
      SYNTAX      HwCmtsDownstreamSweepEntry
      MAX-ACCESS  not-accessible
      STATUS      current
      DESCRIPTION
            "
            Indicates a downstream sweeping table.
            The index of this entry is cable port ifIndex.
            "
      INDEX       { ifIndex }
      ::= { hwCmtsDownstreamSweepTable 1 }
      
  HwCmtsDownstreamSweepEntry ::=
      SEQUENCE{
         hwCmtsDownstreamSweepOperation                   INTEGER,                      
         hwCmtsDownstreamSweepFreqList                    OCTET STRING,
         hwCmtsDownstreamSweepFreqWidth                   Integer32,
         hwCmtsDownstreamSweepRfPower                     Integer32,
         hwCmtsDownstreamSingleSweepSignalSendTime        Integer32,
         hwCmtsDownstreamSweepTimeOut                     Integer32,
         hwCmtsDownstreamSweepStatus                      INTEGER,
         hwCmtsDownstreamSweepSupportFlag                 INTEGER,
         hwCmtsDownstreamSweepMaxPermitRfPower            Integer32,
         hwCmtsDownstreamSweepRemainingTime               Integer32
      }
      
  hwCmtsDownstreamSweepOperation OBJECT-TYPE
      SYNTAX      INTEGER 
          {
             start   (1),
             stop    (2)
           }
      MAX-ACCESS  read-write
      STATUS      current
      DESCRIPTION
            "
            Indicates an operation to control sweeping.
            Options:
            1.start(1) - indicates the dowmstream sweeping is started.
            2.stop(2) - indicates the dowmstream sweeping is stoped.
            "
      ::= { hwCmtsDownstreamSweepEntry 1 }

  hwCmtsDownstreamSweepFreqList OBJECT-TYPE
      SYNTAX      OCTET STRING (SIZE (0 | 1..8000))
      UNITS       "Hz"
      MAX-ACCESS  read-write
      STATUS      current
      DESCRIPTION
            "
            The frequency list for the downstream sweeping.
            It can contain as most as 32 frequencies.
            Every 10 octets represent a frequency.
            (,) used to indicate a separation of the different frequencies. 
            "
      ::= { hwCmtsDownstreamSweepEntry 2 }
      
  hwCmtsDownstreamSweepFreqWidth OBJECT-TYPE
      SYNTAX      Integer32 (-1|50000..1000000)
      UNITS       "Hz"
      MAX-ACCESS  read-write
      STATUS      current
      DESCRIPTION
            "
            Indicates the CW signal spectrum width.
            The value must be an integer multiple of 100000.
            Invalid value is -1.
            "
      DEFVAL       { 100000 }
      ::= { hwCmtsDownstreamSweepEntry 3 }

  hwCmtsDownstreamSweepRfPower OBJECT-TYPE
      SYNTAX      Integer32 
      UNITS       "0.1dBmV"
      MAX-ACCESS  read-write
      STATUS      current
      DESCRIPTION
            "
            Indicates the CW signal Tx power.
            The minimum value is determined by the product, the same as D3.0 channels.
            Invalid value is -2147483647.
            "
      DEFVAL       { 450 }
      ::= { hwCmtsDownstreamSweepEntry 4 }
      
  hwCmtsDownstreamSingleSweepSignalSendTime OBJECT-TYPE
      SYNTAX      Integer32 (-1|200..5000)
      UNITS       "ms"
      MAX-ACCESS  read-write
      STATUS      current
      DESCRIPTION
            "
            Indicates the duration of sending a single sweep signal for once.
            Invalid value is -1.
            "
      DEFVAL       { 500 }
      ::= { hwCmtsDownstreamSweepEntry 5 }
      
  hwCmtsDownstreamSweepTimeOut OBJECT-TYPE
      SYNTAX      Integer32 (-1|10..86400)
      UNITS       "s"
      MAX-ACCESS  read-write
      STATUS      current
      DESCRIPTION
            "
            Indicates the sweeping timeout period.
            Invalid value is -1.
            "
      DEFVAL       { 900 }
      ::= { hwCmtsDownstreamSweepEntry 6 }
      
  hwCmtsDownstreamSweepStatus OBJECT-TYPE
      SYNTAX      INTEGER 
          {
             idle (1),
             sweeping (2)
          }
      MAX-ACCESS  read-only
      STATUS      current
      DESCRIPTION
            "
            Indicates the status of the downstream sweeping.
            Options:
            1.idle(1) 
            2.sweeping(2) 
            "
      ::= { hwCmtsDownstreamSweepEntry 7 }
      
  hwCmtsDownstreamSweepSupportFlag OBJECT-TYPE
      SYNTAX      INTEGER 
          {
             unknown (1),
             support (2),
             unsupport(3),
             invalid (-1)
          }
      MAX-ACCESS  read-only
      STATUS      current
      DESCRIPTION
            "
            Indicates the flag of a cable board support the downstream sweeping. 
						Options:
						1.unknown(1)
						2.support(2)
						3.unsupport(3)
						4.invalid(-1)
            "
      ::= { hwCmtsDownstreamSweepEntry 8 }
      
  hwCmtsDownstreamSweepMaxPermitRfPower OBJECT-TYPE
      SYNTAX      Integer32
      UNITS       "0.1dBmV"
      MAX-ACCESS  read-only
      STATUS      current
      DESCRIPTION
            "
            Indicates the Maximum sending power of CW signal be allowed.
            Invalid value is -2147483647. 
            "
      ::= { hwCmtsDownstreamSweepEntry 9 }
      
  hwCmtsDownstreamSweepRemainingTime OBJECT-TYPE
      SYNTAX      Integer32
      UNITS       "s"
      MAX-ACCESS  read-only
      STATUS      current
      DESCRIPTION
            "
            Indicates the remaining time of the downstream sweeping.
            "
      ::= { hwCmtsDownstreamSweepEntry 10 }
            
   -- Table hwCmtsDownstreamSweepTable End
     
--        DOCSIF TRAP

        hwCmtsDownstreamChannelStatusChangeTrap NOTIFICATION-TYPE
            OBJECTS {
                    hwFrameIndex,
                    hwSlotIndex,
                    hwPortIndex,
                    docsIfDownChannelId,
                    ifAdminStatus,
                    ifOperStatus
             }
            STATUS current
            DESCRIPTION
                "CMTS downstream channel operation status change trap.
                 This trap message is generated when the operation status of downstream channel changes.
                "
            ::= { hwdocsIfCmtsTraps     0 1 }

        hwCmtsUpstreamChannelStatusChangeTrap NOTIFICATION-TYPE
            OBJECTS {
                    hwFrameIndex,
                    hwSlotIndex,
                    hwPortIndex,
                    docsIfUpChannelId,
                    ifAdminStatus,
                    ifOperStatus
             }
            STATUS current
            DESCRIPTION
                "CMTS upstream channel operation status change trap.
                 This trap message is generated when the operation status of upstream channel changes.
                "
            ::= { hwdocsIfCmtsTraps     0 2 }

        hwDocsIf3CmtsCmRemoteQueryTrap NOTIFICATION-TYPE
            OBJECTS {
                    docsIf3CmtsCmRegStatusId,
                    hwDocsIf3CmtsCmDsChannelIdList,
                    hwDocsIf3CmtsCmDsRxPowerList,
                    hwDocsIf3CmtsCmDsSnrList,
                    hwDocsIf3CmtsCmUsChannlIdList,
                    hwDocsIf3CmtsCmUsTxPowerList,
                    hwDocsIf3CmtsCmUsTxTimingOffsetList,
                    hwDocsIf3CmtsCmSysDesc,
                    hwCmtsCmRegRemoteStatus,
                    hwDocsIf3CmtsCmRegStatusT1Timeouts,
                    hwDocsIf3CmtsCmRegStatusT2Timeouts,
                    hwDocsIf3CmtsCmUsStatusT3Timeouts,
                    hwDocsIf3CmtsCmUsStatusT4Timeouts,
                    hwDocsIf3CmtsCmIGMPVersion,                
                    hwDocsIf3CmtsCmDsUncorrectedErrorCodeList,
                    hwDocsIf3CmtsCmDsCorrectedErrorCodeList,
                    hwDocsIf3CmtsCmDsGoodCodeList,                
                    hwDocsIf3CmMdCfgIpProvMode,
                    hwDocsIf3CmtsCmDsMerList,
                    hwDocsIf3CmtsCmDsMerSamplesList,
                    hwDocsIf3CmtsCmDsMicroreflectionsList,
                    hwDocsIf3CmtsCmDsPer,
                    hwDocsIf3CmtsCmUsRangingStatusList                
             }
            STATUS current
            DESCRIPTION
                "
                CM remote query trap.
                This trap message is generated when querying the information about a remote CM.
                "
            ::= { hwdocsIfCmtsTraps     0 3 }

        hwCmtsCmDataChangeTrap NOTIFICATION-TYPE
            OBJECTS {
                    hwConfigChangeIP,
                    hwCmtsCmDataChangeCmNum,
                    hwCmtsCmDataChangeCmIdList,
                    hwCmtsCmDataChangeCmOperTypeList,
                    hwCmtsCmDataChangeCmMacAddrList,
                    hwCmtsCmDataChangeCmcIfindexList                    
             }
            STATUS current
            DESCRIPTION
                "CM data change trap.
                 This trap message is generated when the CM data changed.
                "
            ::= { hwdocsIfCmtsTraps     0 4 }

            hwCmtsUnstableConnCmExceedThresholdAlarmTrap NOTIFICATION-TYPE
            OBJECTS {                                                  
                    hwFrameIndex,
                    hwSlotIndex,
                    hwPortIndex,
                    hwCmtsMassUnstableConnCmNum,
                    hwCmtsMassUnstableConnCmPercent
             }
            STATUS current
            DESCRIPTION
                "
                Unstable cable modem exceed the threshold trap.
                This trap message is generated when unstable cable modem exceed the threshold.
                "  
            ::= { hwdocsIfCmtsTraps     0 5 } 
            
            hwCmtsOfflineCmExceedThresholdAlarmTrap NOTIFICATION-TYPE
            OBJECTS {                                                  
                    hwFrameIndex,
                    hwSlotIndex,
                    hwPortIndex,
                    hwCmtsMassOfflineCmNum,
                    hwCmtsMassOfflineCmPercent
             }
            STATUS current
            DESCRIPTION
                "
                Offline cable modem exceed the threshold trap.
                This trap message is generated when offline cable modem exceed the threshold.
                "  
            ::= { hwdocsIfCmtsTraps     0 6 } 
                        
            hwCmtsOverCmSpecAlarmTrap NOTIFICATION-TYPE
            OBJECTS {                                                  
                    hwFrameIndex,
                    hwSlotIndex,
                    hwPortIndex,
                    hwCmtsOverCmSpec20Num,
                    hwCmtsOverCmSpec30Num,
                    hwCmtsGoingOnlineCmNum,
                    hwCmtsOverCmSpec31Num
             }
            STATUS current
            DESCRIPTION
                "
                The number of connected CMs has reached the maximum specifications.
                Number of connected CMs has reached the maximum specifications. When the number of connected CMs reaches the maximum specifications of the CMTS, this trap is generated.
                "  
            ::= { hwdocsIfCmtsTraps     0 7 } 
      
        hwCmtsEQAMChannelUtilizationAlarmTrap NOTIFICATION-TYPE
            OBJECTS {                                                  
                    hwFrameIndex,
                    hwSlotIndex,
                    hwPortIndex,
                    hwCmtsEQAMChannelIndex,
                    hwCmtsEQAMChannelUtilization
             }
            STATUS current
            DESCRIPTION
                " 
                The EQAM Utilization Threshold trap.
                This trap message is generated when the EQAM Utilization exceed the threshold.
                "  
            ::= { hwdocsIfCmtsTraps     0 8 }
            
        hwCmtsSNRDegradeAlarmTrap NOTIFICATION-TYPE
            OBJECTS {                                                  
                    hwFrameIndex,
                    hwSlotIndex,
                    hwPortIndex,
                    docsIfUpChannelId,
                    hwCmtsUpChannelSnr
             }
            STATUS current
            DESCRIPTION
                " 
                The SNR degrade threshold trap.
                This trap message is generated when the upstream SNR below the threshold.
                "  
            ::= { hwdocsIfCmtsTraps     0 9 }       
            
        hwCmtsSNRRestoreAlarmTrap NOTIFICATION-TYPE
            OBJECTS {                                                  
                    hwFrameIndex,
                    hwSlotIndex,
                    hwPortIndex,
                    docsIfUpChannelId,
                    hwCmtsUpChannelSnr
             }
            STATUS current
            DESCRIPTION
                " 
                The SNR restore threshold trap.
                This trap message is generated when the upstream SNR exceed the threshold.
                "  
            ::= { hwdocsIfCmtsTraps     0 10 } 
            
        hwCmtsUpstreamAbnormalStateAlarmTrap NOTIFICATION-TYPE
            OBJECTS {                                                  
                    hwFrameIndex,
                    hwSlotIndex,
                    hwPortIndex,
                    docsIfUpChannelId
             }
            STATUS current
            DESCRIPTION
                " 
                The upstream abnormal state trap.
                This trap message is generated when the upstream channel was disabled.
                "  
            ::= { hwdocsIfCmtsTraps     0 11 }     
            
        hwCmtsUpstreamNormalStateAlarmTrap NOTIFICATION-TYPE
            OBJECTS {                                                  
                    hwFrameIndex,
                    hwSlotIndex,
                    hwPortIndex,
                    docsIfUpChannelId
             }
            STATUS current
            DESCRIPTION
                " 
                The upstream normal state trap.
                This trap message is generated when the upstream channel was re-enabled.
                "  
            ::= { hwdocsIfCmtsTraps     0 12 }        
            
        hwCmtsDownstreamAbnormalStateAlarmTrap NOTIFICATION-TYPE
            OBJECTS {                                                  
                    hwFrameIndex,
                    hwSlotIndex,
                    hwPortIndex,
                    docsIfDownChannelId
             }
            STATUS current
            DESCRIPTION
                " 
                The downstream abnormal state trap.
                This trap message is generated when the downstream channel was disabled.
                "  
            ::= { hwdocsIfCmtsTraps     0 13 }     
            
        hwCmtsDownstreamNormalStateAlarmTrap NOTIFICATION-TYPE
            OBJECTS {                                                  
                    hwFrameIndex,
                    hwSlotIndex,
                    hwPortIndex,
                    docsIfDownChannelId
             }
            STATUS current
            DESCRIPTION
                " 
                The downstream normal state trap.
                This trap message is generated when the downstream channel was re-enabled.
                "  
            ::= { hwdocsIfCmtsTraps     0 14 } 
            
        hwCmtsPortStatusChangeTrap NOTIFICATION-TYPE
            OBJECTS {
                    hwConfigChangeIP,
                    hwFrameIndex,
                    hwSlotIndex,
                    hwPortIndex,
                    ifAdminStatus,
                    ifOperStatus
             }
            STATUS current
            DESCRIPTION
                "RF port status change trap.
                 This trap message is generated when admin or operation status of the port changes.
                "
            ::= { hwdocsIfCmtsTraps     0 15 }

        hwCmtsAdmissionCtrlAlarmMinorFaultTrap NOTIFICATION-TYPE
            OBJECTS {
                    hwFrameIndex,
                    hwSlotIndex,
                    hwPortIndex,
                    hwCmtsAdmCtrlChlBandwidthChannelType,
                    hwCmtsAdmissionCtrlBandwidthChannelID,
                    hwCmtsAdmissionCtrlBandwidthAdCtrlType,
                    hwCmtsAdmissionCtrlBandwidthCurBandwidth
             }
            STATUS current
            DESCRIPTION
                "The admission control minor threshold fault trap.
                 This trap message is generated when the channel bandwidth usage is higher than the minor alarm threshold.
                "
            ::= { hwdocsIfCmtsTraps     0 16 }
            
        hwCmtsAdmissionCtrlAlarmMinorRestoreTrap NOTIFICATION-TYPE
            OBJECTS {
                    hwFrameIndex,
                    hwSlotIndex,
                    hwPortIndex,
                    hwCmtsAdmCtrlChlBandwidthChannelType,
                    hwCmtsAdmissionCtrlBandwidthChannelID,
                    hwCmtsAdmissionCtrlBandwidthAdCtrlType,
                    hwCmtsAdmissionCtrlBandwidthCurBandwidth
             }
            STATUS current
            DESCRIPTION
                "The admission control minor threshold restore trap.
                 This trap message is generated when the channel bandwidth usage is lower than the minor alarm restore threshold.
                "
            ::= { hwdocsIfCmtsTraps     0 17 }
        hwCmtsAdmissionCtrlAlarmMajorFaultTrap NOTIFICATION-TYPE
            OBJECTS {
                    hwFrameIndex,
                    hwSlotIndex,
                    hwPortIndex,
                    hwCmtsAdmCtrlChlBandwidthChannelType,
                    hwCmtsAdmissionCtrlBandwidthChannelID,
                    hwCmtsAdmissionCtrlBandwidthAdCtrlType,
                    hwCmtsAdmissionCtrlBandwidthCurBandwidth
             }
            STATUS current
            DESCRIPTION
                "The admission control major threshold fault trap.
                 This trap message is generated when the channel bandwidth usage is higher than the major alarm threshold.
                "
            ::= { hwdocsIfCmtsTraps     0 18 }
            
        hwCmtsAdmissionCtrlAlarmMajorRestoreTrap NOTIFICATION-TYPE
            OBJECTS {
                    hwFrameIndex,
                    hwSlotIndex,
                    hwPortIndex,
                    hwCmtsAdmCtrlChlBandwidthChannelType,
                    hwCmtsAdmissionCtrlBandwidthChannelID,
                    hwCmtsAdmissionCtrlBandwidthAdCtrlType,
                    hwCmtsAdmissionCtrlBandwidthCurBandwidth
             }
            STATUS current
            DESCRIPTION
                "The admission control major threshold restore trap.
                 This trap message is generated when the channel bandwidth usage is lower than the major alarm restore threshold.
                "
            ::= { hwdocsIfCmtsTraps     0 19 }
                        
        hwCmtsUnstableConnCmExceedThresholdNormalTrap NOTIFICATION-TYPE
            OBJECTS {
                    hwFrameIndex,
                    hwSlotIndex,
                    hwPortIndex,
                    hwCmtsMassUnstableConnCmNum,
                    hwCmtsMassUnstableConnCmPercent
             }
            STATUS current
            DESCRIPTION
                "
                The number of unstable cable modem is lower than the threshold trap.
                This trap message is generated when the number of unstable cable modem is lower than the threshold.
                "  
            ::= { hwdocsIfCmtsTraps     0 20 }
                        
        hwCmtsOfflineCmExceedThresholdNormalTrap NOTIFICATION-TYPE
            OBJECTS {
                    hwFrameIndex,
                    hwSlotIndex,
                    hwPortIndex,
                    hwCmtsMassOfflineCmNum,
                    hwCmtsMassOfflineCmPercent
             }
            STATUS current
            DESCRIPTION
                "
                The number of offline cable modem is lower than the threshold trap.
                This trap message is generated when the number of offline cable modem is lower than the threshold.
                " 
            ::= { hwdocsIfCmtsTraps     0 21 }
      
        hwCmtsCmAccessThresholdAlarmMinorFaultTrap NOTIFICATION-TYPE
            OBJECTS {
                    hwFrameIndex,
                    hwSlotIndex,
                    hwPortIndex,
                    hwDocsIf3CmtsCmAccessNumUpperThreshold,
                    hwDocsIf3CmtsCmAccessNumLowerThreshold,
                    hwDocsIf3CmtsCmAccessCurrentNum                    
             }
            STATUS current
            DESCRIPTION
                "The number of access cable modems has reached the maximum number allowed trap.
                 This trap message is generated when the number of access cable modems has reached the maximum number allowed.
                "
            ::= { hwdocsIfCmtsTraps     0 22 }
            
        hwCmtsCmAccessThresholdAlarmMajorRestoreTrap NOTIFICATION-TYPE
            OBJECTS {
                    hwFrameIndex,
                    hwSlotIndex,
                    hwPortIndex,
                    hwDocsIf3CmtsCmAccessNumUpperThreshold,
                    hwDocsIf3CmtsCmAccessNumLowerThreshold,
                    hwDocsIf3CmtsCmAccessCurrentNum 
             }
            STATUS current
            DESCRIPTION
                "The number of access cable modems restore trap.
                 This trap message is generated when the number of access cable modems is lower than restore threshold.
                "
            ::= { hwdocsIfCmtsTraps     0 23 }

        hwCmtsCmWhitelistMacTrap NOTIFICATION-TYPE
            OBJECTS {                                                  
                    hwFrameIndex,
                    hwSlotIndex,
                    hwPortIndex,
                    hwCmtsCmWhitelistMac
             }
            STATUS current
            DESCRIPTION
                "
                The CM was rejected for its MAC not in CM whitelist allowed trap.
                This trap message is generated when the CM has been rejected for its MAC not in CM whitelist.
                "  
            ::= { hwdocsIfCmtsTraps     0 24 }    

        hwCmtsRfTxPowerAbnormalFaultTrap NOTIFICATION-TYPE
            OBJECTS {                                                  
                    hwFrameIndex,
                    hwCmtsDownstreamRfPowerAdjustmentGroupID
             }
            STATUS current
            DESCRIPTION
                "
                The RF transmit power is abnormal trap.
                This trap message is generated when the intelligent RF adjustment failed.
                "  
            ::= { hwdocsIfCmtsTraps     0 25 }    

        hwCmtsRfTxPowerAbnormalRestoreTrap NOTIFICATION-TYPE
            OBJECTS {                                                  
                    hwFrameIndex,
                    hwCmtsDownstreamRfPowerAdjustmentGroupID
             }
            STATUS current
            DESCRIPTION
                "
                The RF transmit power is abnormal restore trap.
                This trap message is generated when the intelligent RF adjustment.
                "  
            ::= { hwdocsIfCmtsTraps     0 26 }   

        hwCmtsRasterStatusCheckTrap NOTIFICATION-TYPE
            OBJECTS {                                                  
                    hwCmtsRasterStatusCheckPara
             }
            STATUS current
            DESCRIPTION
                "The raster check status changed trap.
                 This trap message is generated when the raster status changed.
                "  
            ::= { hwdocsIfCmtsTraps     0 27 }

        hwCmtsCmOnOfflineTrap NOTIFICATION-TYPE
            OBJECTS {                                                  
                    hwCmtsCmTrapTimeTicks,
                    hwCmtsCmDataChangeCmNum,
                    hwCmtsCmDataChangeCmIdList,
                    hwCmtsCmTrapCmStatusList,
                    hwCmtsCmDataChangeCmMacAddrList,
                    hwCmtsCmTrapCmIPTypeList,
                    hwCmtsCmTrapCmIPList
             }
            STATUS current
            DESCRIPTION
                "The CM online/offline trap.
                 This trap message is generated when the CM goes online or offline.
                "  
            ::= { hwdocsIfCmtsTraps     0 28 }                  

        hwCmtsCmAlarmCmFaultTrap NOTIFICATION-TYPE
            OBJECTS {                                                  
                    hwFrameIndex,
                    hwSlotIndex,
                    hwPortIndex,
                    docsIf3CmtsCmRegStatusId,
                    hwCmtsCmMAC,
                    hwCmtsCmAlarmDesc
             }
            STATUS current
            DESCRIPTION
                "The CM offline trap.
                 This trap message is generated when the CM goes offline.
                "  
            ::= { hwdocsIfCmtsTraps     0 29 }

        hwCmtsCmAlarmCmRestoreTrap NOTIFICATION-TYPE
            OBJECTS {                                                  
                    hwFrameIndex,
                    hwSlotIndex,
                    hwPortIndex,
                    docsIf3CmtsCmRegStatusId,
                    hwCmtsCmMAC,
                    hwCmtsCmAlarmDesc
             }
            STATUS current
            DESCRIPTION
                "The CM offline recovery trap.
                 This trap message is generated when the CM goes online after being offline.
                "  
            ::= { hwdocsIfCmtsTraps     0 30 }  

        hwCmtsEqamChannelStatusChangeTrap NOTIFICATION-TYPE
            OBJECTS {
                    hwFrameIndex,
                    hwSlotIndex,
                    hwPortIndex,
                    hwCmtsEqamChannelId,
                    ifAdminStatus,
                    ifOperStatus
             }
            STATUS current
            DESCRIPTION
                "CMTS Eqam channel operation status change trap.
                 This trap message is generated when the operation status of Eqam channel changes.
                "
            ::= { hwdocsIfCmtsTraps     0 31 }

        hwCmtsEqamAbnormalStateAlarmTrap NOTIFICATION-TYPE
            OBJECTS {
                    hwFrameIndex,
                    hwSlotIndex,
                    hwPortIndex,
                    hwCmtsEqamChannelId
             }
            STATUS current
            DESCRIPTION
                "The Eqam channel abnormal state trap.
                This trap message is generated when the Eqam channel was disabled.
                "
            ::= { hwdocsIfCmtsTraps     0 32 }

        hwCmtsEqamNormalStateAlarmTrap NOTIFICATION-TYPE
            OBJECTS {
                    hwFrameIndex,
                    hwSlotIndex,
                    hwPortIndex,
                    hwCmtsEqamChannelId
             }
            STATUS current
            DESCRIPTION
                "The Eqam channel normal state trap.
                This trap message is generated when the Eqam channel was re-enabled.
                "
            ::= { hwdocsIfCmtsTraps     0 33 }

 --     hwcmtsTrapsVbOids

        hwDocsIf3CmtsCmDsChannelIdList OBJECT-TYPE
            SYNTAX      OCTET STRING
            MAX-ACCESS accessible-for-notify
            STATUS current
            DESCRIPTION
                "
                Indicates list of downstream channel indexes.
                "
            ::= { hwcmtsTrapsVbOids 1 }

        hwDocsIf3CmtsCmDsRxPowerList OBJECT-TYPE
            SYNTAX      OCTET STRING
            UNITS       "0.1 dBmV"
            MAX-ACCESS accessible-for-notify
            STATUS current
            DESCRIPTION
                "
                Indicates list of the receiver power of downstream channels.
                "
            ::= { hwcmtsTrapsVbOids 2 }

        hwDocsIf3CmtsCmDsSnrList OBJECT-TYPE
            SYNTAX     OCTET STRING
            UNITS       "0.1 dB"
            MAX-ACCESS accessible-for-notify
            STATUS current
            DESCRIPTION
                "
                Indicates list of the SNR of downstream channels.
                "
            ::= { hwcmtsTrapsVbOids 3 }

         hwDocsIf3CmtsCmUsChannlIdList OBJECT-TYPE
            SYNTAX      OCTET STRING
            MAX-ACCESS accessible-for-notify
            STATUS current
            DESCRIPTION
                "
                The up channel list of CM.
                "
            ::= { hwcmtsTrapsVbOids 4 }

       hwDocsIf3CmtsCmUsTxPowerList OBJECT-TYPE
            SYNTAX      OCTET STRING
            MAX-ACCESS accessible-for-notify
            STATUS current
            DESCRIPTION
                "
                The up channel power list of CM.
                "
            ::= { hwcmtsTrapsVbOids 5 }

       hwDocsIf3CmtsCmUsTxTimingOffsetList OBJECT-TYPE
            SYNTAX      OCTET STRING
            MAX-ACCESS accessible-for-notify
            STATUS current
            DESCRIPTION
                "
                The send time offset list of CM.
                "
            ::= { hwcmtsTrapsVbOids 6 }

       hwDocsIf3CmtsCmSysDesc OBJECT-TYPE
            SYNTAX      OCTET STRING
            MAX-ACCESS accessible-for-notify
            STATUS current
            DESCRIPTION
                "
                The system description of CM.
                "
            ::= { hwcmtsTrapsVbOids 7 }

       hwCmtsCmRegRemoteStatus OBJECT-TYPE
            SYNTAX      Integer32
            MAX-ACCESS accessible-for-notify
            STATUS current
            DESCRIPTION
                "
                The remote status of CM as indicated by the value of
                docsIf3CmStatusValue.
                "
            ::= { hwcmtsTrapsVbOids 8 }

         hwCmtsCmDataChangeCmNum OBJECT-TYPE
            SYNTAX      Integer32
            MAX-ACCESS accessible-for-notify
            STATUS current
            DESCRIPTION
                "
                The number of CM which has changed.
                "
            ::= { hwcmtsTrapsVbOids 9 }

        hwCmtsCmDataChangeCmIdList OBJECT-TYPE
            SYNTAX      OCTET STRING
            MAX-ACCESS accessible-for-notify
            STATUS current
            DESCRIPTION
                "
                The list of CM which has changed.
                "
            ::= { hwcmtsTrapsVbOids 10 }

        hwCmtsCmDataChangeCmOperTypeList OBJECT-TYPE
            SYNTAX     OCTET STRING
            MAX-ACCESS accessible-for-notify
            STATUS current
            DESCRIPTION
                "
                The operation type list of configuration changed CM.
                operation type:
                    1: create CM.
                    2: delete CM.
                "
            ::= { hwcmtsTrapsVbOids 11 }

        hwCmtsCmDataChangeCmMacAddrList OBJECT-TYPE
            SYNTAX     OCTET STRING
            MAX-ACCESS accessible-for-notify
            STATUS current
            DESCRIPTION
                "
                The MAC address list of configuration changed CM.
                "
            ::= { hwcmtsTrapsVbOids 12 }
            
        hwCmtsMassUnstableConnCmNum OBJECT-TYPE
            SYNTAX     Integer32
            MAX-ACCESS accessible-for-notify
            STATUS current
            DESCRIPTION
                "
                The number of unstable connection cable modem.
                "
            ::= { hwcmtsTrapsVbOids 13 }
            
        hwCmtsMassOfflineCmNum OBJECT-TYPE
            SYNTAX     Integer32
            MAX-ACCESS accessible-for-notify
            STATUS current
            DESCRIPTION
                "
                The number of offline cable modem.
                "
            ::= { hwcmtsTrapsVbOids 14 }

        hwDocsIf3CmtsCmRegStatusT1Timeouts OBJECT-TYPE
            SYNTAX     Integer32
            MAX-ACCESS accessible-for-notify
            STATUS current
            DESCRIPTION
                "
                The number of T1 timeouts.
                T1 represents waiting for UCD.
                -1 represents invalid value.
                "
            ::= { hwcmtsTrapsVbOids 15 }

        hwDocsIf3CmtsCmRegStatusT2Timeouts OBJECT-TYPE
            SYNTAX     Integer32
            MAX-ACCESS accessible-for-notify
            STATUS current
            DESCRIPTION
                "
                The number of T2 timeouts.
                T2 represents waiting for broadcast ranging.
                -1 represents invalid value.
                "
            ::= { hwcmtsTrapsVbOids 16 }

        hwDocsIf3CmtsCmUsStatusT3Timeouts OBJECT-TYPE
            SYNTAX     OCTET STRING
            MAX-ACCESS accessible-for-notify
            STATUS current
            DESCRIPTION
                "
                List of the number of T3 timeouts of upstream channels. 
                T3 represents waiting for ranging response.                
                "
            ::= { hwcmtsTrapsVbOids 17 }

        hwDocsIf3CmtsCmUsStatusT4Timeouts OBJECT-TYPE
            SYNTAX     OCTET STRING
            MAX-ACCESS accessible-for-notify
            STATUS current
            DESCRIPTION
                "
                List of the number of T4 timeouts of upstream channels. 
                T4 represents waiting for unicast ranging opportunity.                
                "
            ::= { hwcmtsTrapsVbOids 18 }

        hwDocsIf3CmtsCmIGMPVersion OBJECT-TYPE
          SYNTAX  INTEGER 
                 {              
                 v1(1),
                 v2(2),
                 v3(3),
                 invalidValue(-1)                 
                 }
            MAX-ACCESS accessible-for-notify
            STATUS current
            DESCRIPTION
                "
                Indicates the version of the IGMP/MLD.
                Options:
                1. v1(1) - Version 1
                2. v2(2) - Version 2
                3. v3(3) - Version 3
                4. invalidValue(-1) - Invalid value
                "
            ::= { hwcmtsTrapsVbOids 19 }  
         
     hwCmtsOverCmSpec20Num OBJECT-TYPE
            SYNTAX     Integer32
            MAX-ACCESS accessible-for-notify
            STATUS current
            DESCRIPTION
                "
                The number of online cable modems in 2.0 version.
                "
            ::= { hwcmtsTrapsVbOids 20 }
      
     hwCmtsOverCmSpec30Num OBJECT-TYPE
            SYNTAX     Integer32
            MAX-ACCESS accessible-for-notify
            STATUS current
            DESCRIPTION
                "
                The number of online cable modems in 3.0 version.
                "
            ::= { hwcmtsTrapsVbOids 21 }
        
        hwCmtsEQAMChannelIndex OBJECT-TYPE
            SYNTAX     Integer32
            MAX-ACCESS accessible-for-notify
            STATUS current
            DESCRIPTION
                "
                The EQAM channel Index.
                "
            ::= { hwcmtsTrapsVbOids 22 }
            
        hwCmtsEQAMChannelUtilization OBJECT-TYPE
            SYNTAX     Integer32
            UNITS       "%"
            MAX-ACCESS accessible-for-notify
            STATUS current
            DESCRIPTION
                "
                The EQAM utilization threshold. 
                "
            ::= { hwcmtsTrapsVbOids 23 }            
            
        hwDocsIf3CmtsCmDsMerList OBJECT-TYPE
            SYNTAX     OCTET STRING
            UNITS       "TenthdB"
            MAX-ACCESS accessible-for-notify
            STATUS current
            DESCRIPTION
                "
                Indicates list of the modulation Error Ratio (MER) of downstream channels.
                "
            ::= { hwcmtsTrapsVbOids 24 }                                                              
                                                  
        hwDocsIf3CmtsCmDsMerSamplesList OBJECT-TYPE
            SYNTAX     OCTET STRING
            MAX-ACCESS accessible-for-notify
            STATUS current
            DESCRIPTION
                "
                Indicates list of the modulation Error Ratio (MER) sample of CMTS,MER samples is a statistically significant number.
                "
            ::= { hwcmtsTrapsVbOids 25 }                                                              
                     
       hwDocsIf3CmtsCmDsMicroreflectionsList OBJECT-TYPE
            SYNTAX     OCTET STRING
            UNITS       "-dBc"
            MAX-ACCESS accessible-for-notify
            STATUS current
            DESCRIPTION
                "
                Indicates list of the microreflections received on the downstream channels.
                "
            ::= { hwcmtsTrapsVbOids 26 }  
        
     hwDocsIf3CmtsCmDsUncorrectedErrorCodeList OBJECT-TYPE
          SYNTAX     OCTET STRING
          MAX-ACCESS accessible-for-notify
          STATUS current
          DESCRIPTION
                "
                List of the number of the codewords received with uncorrectable
                errors from the CM on the downstream channels.
                "
          ::= { hwcmtsTrapsVbOids 27 }                    
          
    hwDocsIf3CmtsCmDsCorrectedErrorCodeList OBJECT-TYPE
          SYNTAX     OCTET STRING
          MAX-ACCESS accessible-for-notify
          STATUS current
          DESCRIPTION
                "
                List of the number of the codewords received with correctable 
                errors from the CM on the downstream channels.
                "
          ::= { hwcmtsTrapsVbOids 28 }
          
    hwDocsIf3CmtsCmDsGoodCodeList OBJECT-TYPE
          SYNTAX     OCTET STRING
          MAX-ACCESS accessible-for-notify
          STATUS current
          DESCRIPTION
                "
                List of the number of the codewords received without error
                from the CM on the downstream channels.
                "
          ::= { hwcmtsTrapsVbOids 29 }                       

       hwDocsIf3CmMdCfgIpProvMode OBJECT-TYPE
            SYNTAX      INTEGER {
                ipv4Only(0),
                ipv6Only(1),
                honorMdd(4),
                invalidValue(-1)
            }
            MAX-ACCESS accessible-for-notify
            STATUS current
            DESCRIPTION
                "This attribute configures the CM IP provisioning mode override.
                Options:
                1. ipv4Only (0)            - When this attribute is set to 'ipv4Only' the CM will acquire
                                             a single IPv4 address for the CM management stack.
                2. ipv6Only (1)            - When this attribute is set to 'ipv6Only' the CM will acquire
                                             a single IPv6 address for the CM management stack. 
                3. honorMdd (4)            - When this attribute is set to 'honorMdd' the CM will acquire 
                                             an IPv6 or IPv4 address as directed by the MDD message for 
                                             provisioning and operation.                    
                4. invalidValue(-1)        - Invalid value. 
                "
            ::= { hwcmtsTrapsVbOids 30 }              
                                                                      
       hwDocsIf3CmtsCmDsPer OBJECT-TYPE
            SYNTAX     Integer32
            UNITS       "0.00001"
            MAX-ACCESS accessible-for-notify
            STATUS current
            DESCRIPTION
                "
                Indicates the rate of package error received on the downstream channels.
                -1 represents invalid value.
                "
            ::= { hwcmtsTrapsVbOids 31 }    

       hwCmtsAdmissionCtrlBandwidthChannelID OBJECT-TYPE
            SYNTAX     Integer32
            MAX-ACCESS accessible-for-notify
            STATUS current
            DESCRIPTION
                "
                Indicates the channel ID.
                "
            ::= { hwcmtsTrapsVbOids 32 }
            
       hwCmtsAdmissionCtrlBandwidthAdCtrlType OBJECT-TYPE
            SYNTAX     Integer32
            MAX-ACCESS accessible-for-notify
            STATUS current
            DESCRIPTION
                "
                Indicates the admission control type.
                "
            ::= { hwcmtsTrapsVbOids 33 }
            
       hwCmtsAdmissionCtrlBandwidthCurBandwidth OBJECT-TYPE
            SYNTAX     Integer32
            MAX-ACCESS accessible-for-notify
            STATUS current
            DESCRIPTION
                "
                Indicates the current bandwidth.
                "
            ::= { hwcmtsTrapsVbOids 34 }         
            
        hwDocsIf3CmtsCmUsRangingStatusList OBJECT-TYPE
            SYNTAX     OCTET STRING
            MAX-ACCESS accessible-for-notify
            STATUS current
            DESCRIPTION
                "
                Indicates the list of the CM upstream channel ranging state.
                "
            ::= { hwcmtsTrapsVbOids 35 } 
            
       hwDocsIf3CmtsCmAccessCurrentNum OBJECT-TYPE
            SYNTAX     Integer32
            MAX-ACCESS accessible-for-notify
            STATUS current
            DESCRIPTION
                "
                Indicates The number of access cable modems.
                -1 represents invalid value.
                "
            ::= { hwcmtsTrapsVbOids 36 }        
                           
       hwCmtsAdmCtrlChlBandwidthChannelType OBJECT-TYPE
            SYNTAX     OCTET STRING
            MAX-ACCESS accessible-for-notify
            STATUS current
            DESCRIPTION
                "
                Indicates the channel type.
                "
            ::= { hwcmtsTrapsVbOids 37 } 

      hwCmtsCmWhitelistMac OBJECT-TYPE
            SYNTAX     MacAddress
            MAX-ACCESS accessible-for-notify
            STATUS current
            DESCRIPTION
                "
                Indicates the MAC address of the CPE.
                "
            ::= { hwcmtsTrapsVbOids 38 }
            
      hwCmtsGoingOnlineCmNum OBJECT-TYPE
            SYNTAX     Integer32
            MAX-ACCESS accessible-for-notify
            STATUS current
            DESCRIPTION
                "
                The number of CMs going online.
                "
            ::= { hwcmtsTrapsVbOids 39 }
            
      hwCmtsDownstreamRfPowerAdjustmentGroupID OBJECT-TYPE
            SYNTAX     Integer32
            MAX-ACCESS accessible-for-notify
            STATUS current
            DESCRIPTION
                "
                Indicates the RF power adjustment group id.
                "
            ::= { hwcmtsTrapsVbOids 40 }
            
      hwCmtsRasterStatusCheckPara OBJECT-TYPE
            SYNTAX    OCTET STRING (SIZE (1..8000))
            MAX-ACCESS accessible-for-notify
            STATUS current
            DESCRIPTION
                "Indicates the raster check status."
            ::= { hwcmtsTrapsVbOids 41 }

      hwCmtsCmTrapTimeTicks OBJECT-TYPE
            SYNTAX    Integer32
            MAX-ACCESS accessible-for-notify
            STATUS current
            DESCRIPTION
                "Indicates the sending time of CM online/offline trap."
            ::= { hwcmtsTrapsVbOids 42 }
 
        hwCmtsCmTrapCmStatusList OBJECT-TYPE
            SYNTAX     OCTET STRING
            MAX-ACCESS accessible-for-notify
            STATUS current
            DESCRIPTION
                "Indicates the list of the CM status.
                Options:
                1. online             - The CM status is online
                2. offline            - The CM status is offline
                "
            ::= { hwcmtsTrapsVbOids 43 }

        hwCmtsCmTrapCmIPTypeList OBJECT-TYPE
            SYNTAX     OCTET STRING
            MAX-ACCESS accessible-for-notify
            STATUS current
            DESCRIPTION
                "Indicates the list of the CM IP type .
                Options:
                1. ipv4             - The CM IP type is ipv4.
                2. ipv6             - The CM IP type is ipv6  
                "
            ::= { hwcmtsTrapsVbOids 44 }

        hwCmtsCmTrapCmIPList OBJECT-TYPE
            SYNTAX     OCTET STRING
            MAX-ACCESS accessible-for-notify
            STATUS current
            DESCRIPTION
                "
                The IP address list of CM.
                "
            ::= { hwcmtsTrapsVbOids 45 }

       hwCmtsCmMAC OBJECT-TYPE
            SYNTAX     MacAddress
            MAX-ACCESS accessible-for-notify
            STATUS current
            DESCRIPTION
                "
                Indicates the MAC address of the CM.
                "
            ::= { hwcmtsTrapsVbOids 46 }
      
        hwCmtsOverCmSpec31Num OBJECT-TYPE
            SYNTAX     Integer32
            MAX-ACCESS accessible-for-notify
            STATUS current
            DESCRIPTION
                "
                The number of online cable modems in 3.1 version.
                "
            ::= { hwcmtsTrapsVbOids 47 }
            
        hwCmtsMassUnstableConnCmPercent OBJECT-TYPE
            SYNTAX     Unsigned32(0..100)
            UNITS      "percent"
            MAX-ACCESS accessible-for-notify
            STATUS current
            DESCRIPTION
                "
                Percentage of unstable connection cable modems.
                "
            ::= { hwcmtsTrapsVbOids 48 }
            
        hwCmtsMassOfflineCmPercent OBJECT-TYPE
            SYNTAX     Unsigned32(0..100)
            UNITS      "percent"            
            MAX-ACCESS accessible-for-notify
            STATUS current
            DESCRIPTION
                "
                Percentage of offline cable modems.
                "
            ::= { hwcmtsTrapsVbOids 49 }

        hwCmtsCmDataChangeCmcIfindexList OBJECT-TYPE
            SYNTAX      OCTET STRING
            MAX-ACCESS accessible-for-notify
            STATUS current
            DESCRIPTION
                "
                CMC ifIndex list to which the configuration-changed CM belongs.
                "
            ::= { hwcmtsTrapsVbOids 50 }

    hwCmtsServiceObject OBJECT IDENTIFIER ::= { hwCmtsObject  22}

    hwPacketCableObject OBJECT IDENTIFIER ::= { hwCmtsServiceObject  1}

    -- hwPacketCableObject   begin
      hwPacketCableConfigObject OBJECT IDENTIFIER ::= { hwPacketCableObject  1}

      -- hwPacketCableConfigObject   begin

        hwPacketCable1DotxSwitch OBJECT-TYPE
          SYNTAX  INTEGER
              {
                 enable(1),
                 disable(2)
              }
          MAX-ACCESS  read-write
          STATUS  current
          DESCRIPTION
                "
                The switch of PacketCable 1.x function.
                Options:
                1. enable(1)        - Indicates the switch is enable
                2. disable(2)       - Indicates the switch is disable
                Default: disable(2)
                "
          ::= { hwPacketCableConfigObject 1 }

        hwPacketCableMultimediaSwitch OBJECT-TYPE
          SYNTAX  INTEGER
              {
                 enable(1),
                 disable(2)
              }
          MAX-ACCESS  read-write
          STATUS  current
          DESCRIPTION
                "
                The switch of PacketCable Multimedia function.
                Options:
                1. enable(1)        - Indicates the switch is enable
                2. disable(2)       - Indicates the switch is disable
                Default: disable(2)
                "
          ::= { hwPacketCableConfigObject 2 }

        hwPacketCableAuthorizeCommonMtaSwitch OBJECT-TYPE
          SYNTAX  INTEGER
              {
                 enable(1),
                 disable(2)
              }
          MAX-ACCESS  read-write
          STATUS  current
          DESCRIPTION
                "
                This switch indicats that whether the Common DOCSIS MTA is authorized to create, modify or delete the dynamic service-flow.
                Options:
                1. enable(1)        - Indicates the switch is enable
                2. disable(2)       - Indicates the switch is disable
                Default: disable(2)
                "
          ::= { hwPacketCableConfigObject 3 }

        hwPacketCableMaxGateCount OBJECT-TYPE
          SYNTAX  Unsigned32
          MAX-ACCESS  read-write
          STATUS  current
          DESCRIPTION
                "
                The maximum count of the Gate in the system.
                The default value is the max value of this object, and the max value is specified in different systems.
                "
          ::= { hwPacketCableConfigObject 4 }

        hwPacketCable1DotxTimerT0 OBJECT-TYPE
          SYNTAX  Unsigned32(0 | 1..1000000)
          UNITS       "seconds"
          MAX-ACCESS  read-write
          STATUS  current
          DESCRIPTION
                "
                In PacketCable 1.x this timer is implemented in the CMTS in the Gate state machine, and limits the period of time that a gate
                may be allocated without the gate parameters being set.
                In the set operation, if is set to 0, it indicates that reset the timer to the default value.
                In the query operation, if it is not set, the value obtained is the default value.
                Range: 0 | 1..1000000
                Default: 30
                "
          ::= { hwPacketCableConfigObject 5 }

        hwPacketCable1DotxTimerT1 OBJECT-TYPE
          SYNTAX  Unsigned32(0 | 1..1000000)
          UNITS       "seconds"
          MAX-ACCESS  read-write
          STATUS  current
          DESCRIPTION
                "
                In PacketCable 1.x this timer is implemented in the CMTS in the Gate state machine, and limits the period of time that may
                elapse between the authorization and a commit is performed.
                In the set operation, if is set to 0, it indicates that reset the timer to the default value.
                In the query operation, if it is not set, the value obtained is the default value.
                Range: 0 | 1..1000000
                Default: 200
                "
          ::= { hwPacketCableConfigObject 6 }

        hwPacketCableMultimediaTimerT1 OBJECT-TYPE
          SYNTAX  Unsigned32(0 | 1..1000000)
          UNITS       "seconds"
          MAX-ACCESS  read-write
          STATUS  current
          DESCRIPTION
                "
                In PacketCable Multimedia this timer limits the amount of time the authorization remains valid.
                In the set operation, if is set to 0, it indicates that reset the timer to the default value.
                In the query operation, if it is not set, the value obtained is the default value.
                Range: 0 | 1..1000000
                Default: 200
                "
          ::= { hwPacketCableConfigObject 7 }

        hwPacketCable1dotxSendSubscriberID OBJECT-TYPE
          SYNTAX  INTEGER
              {
                 enable(1),
                 disable(2)
              }
          MAX-ACCESS  read-write
          STATUS  current
          DESCRIPTION
                "
                In PacketCable 1.x this switch indicates that whether the SubscriberID is carried in Gate-Info, Gate-Delete, Gate-Open, Gate-Close packets.
                Options:
                1. enable(1)        - Indicates the switch is enable
                2. disable(2)       - Indicates the switch is disable
                Default: disable(2)
                "
          ::= { hwPacketCableConfigObject 8 }

        -- hwPacketCableConfigObject    end

      --Table   hwPacketcableGateInfoTable  begin

        hwPacketcableGateInfoTable OBJECT-TYPE
            SYNTAX     SEQUENCE OF HwPacketcableGateInfoEntry
            MAX-ACCESS not-accessible
            STATUS     current
            DESCRIPTION
                "
                Indicates the information of packetcable gate.
                The index of this table is hwPacketcableGateID.
                "
            ::= { hwPacketCableObject 2 }

        hwPacketcableGateInfoEntry OBJECT-TYPE
            SYNTAX     HwPacketcableGateInfoEntry
            MAX-ACCESS not-accessible
            STATUS     current
            DESCRIPTION
                "
                Indicates the information of packetcable gate.
                The index of this entry is hwPacketcableGateID.
                "
            INDEX       { hwPacketcableGateID }
            ::= { hwPacketcableGateInfoTable 1 }

        HwPacketcableGateInfoEntry ::=
            SEQUENCE {
                hwPacketcableGateID                      Unsigned32,
                hwPacketcableSubscriberIdType            InetAddressType,
                hwPacketcableSubscriberID                InetAddress,
                hwPacketcableGcAddressType               InetAddressType,
                hwPacketcableGcAddress                   InetAddress,
                hwPacketcableGateState                   INTEGER,
                hwPacketcableUpstreamServiceFlowId       Unsigned32,
                hwPacketcableDownstreamServiceFlowId     Unsigned32,
                hwPacketcableGateIfindex                 InterfaceIndexOrZero
            }

        hwPacketcableGateID  OBJECT-TYPE
            SYNTAX     Unsigned32
            MAX-ACCESS   not-accessible
            STATUS      current
            DESCRIPTION
                "
                The identifier of the Gate which identifies the Gate referenced in the command message, or referenced by the CMTS for a response message.
                The CMTS must ensure the GateID is unique. If the CMTS supports PacketCable 1.x and PacketCable Multimedia,
                the PacketCable Multimedia GateID must not duplicate a PacketCable 1.x GateID currently in use.
                "
            ::= { hwPacketcableGateInfoEntry 1 }

        hwPacketcableSubscriberIdType  OBJECT-TYPE
            SYNTAX     InetAddressType
            MAX-ACCESS   read-only
            STATUS      current
            DESCRIPTION
                "
                The type of the SubscriberID. There are two different versions of the SubscriberID object which differ in the IP version of the addresses that they
                contain. This object only supports ipv4(1) currently.
                "
            ::= { hwPacketcableGateInfoEntry 2 }

        hwPacketcableSubscriberID  OBJECT-TYPE
            SYNTAX     InetAddress
            MAX-ACCESS   read-only
            STATUS      current
            DESCRIPTION
                "
                The SubscriberID which identifies the user requesting the service. This object contains a value giving the IP address.
                example: 10.11.234.123.
                "
            ::= { hwPacketcableGateInfoEntry 3 }

        hwPacketcableGcAddressType  OBJECT-TYPE
            SYNTAX     InetAddressType
            MAX-ACCESS   read-only
            STATUS      current
            DESCRIPTION
                "
                This object indicats the type of internet address of the Gate Controller, but this object only support ipv4(1) currently.
                "
            ::= { hwPacketcableGateInfoEntry 4 }

        hwPacketcableGcAddress  OBJECT-TYPE
            SYNTAX     InetAddress
            MAX-ACCESS   read-only
            STATUS      current
            DESCRIPTION
                "
                The internet address of the Gate Controller. example: 10.11.234.123.

                An InetAddress value is always interpreted within the context
                of an InetAddressType value.  Every usage of the InetAddress
                extual convention is required to specify the InetAddressType
                object that provides the context.  It is suggested that the
                InetAddressType object be logically registered before the
                object(s) that use the InetAddress textual convention, if
                they appear in the same logical row.

                The value of an InetAddress object must always be
                consistent with the value of the associated InetAddressType
                object.  Attempts to set an InetAddress object to a value
                inconsistent with the associated InetAddressType
                must fail with an inconsistentValue error.

                When this textual convention is used as the syntax of an
                index object, there may be issues with the limit of 128
                sub-identifiers specified in SMIv2, STD 58.  In this case,
                the object definition MUST include a 'SIZE' clause to
                limit the number of potential instance sub-identifiers;
                otherwise the applicable constraints MUST be stated in
                the appropriate conceptual row DESCRIPTION clauses, or
                in the surrounding documentation if there is no single
                DESCRIPTION clause that is appropriate.
                "
            ::= { hwPacketcableGateInfoEntry 5 }

        hwPacketcableGateState  OBJECT-TYPE
            SYNTAX     INTEGER
            {
                allocated(1),
                authorized(2),
                reserved(3),
                committed(4),
                committedRecovery(5),
                idle(6)
            }
            MAX-ACCESS   read-only
            STATUS      current
            DESCRIPTION
                "
                The state of the Gate.
                Options:
                1. allocated(1)            - Indicates the allocated state
                2. authorized(2)           - Indicates the authorized state
                3. reserved(3)             - Indicates the reserved state
                4. committed(4)            - Indicates the committed state
                5. committedRecovery(5)    - Indicates the committed-recovery state
                6. idle(6)                 - Indicates the idle state
                "
            ::= { hwPacketcableGateInfoEntry 6 }

        hwPacketcableUpstreamServiceFlowId  OBJECT-TYPE
            SYNTAX     Unsigned32
            MAX-ACCESS   read-only
            STATUS      current
            DESCRIPTION
                "
                The index of the upstream service flow, which is obtained from docsQosServiceFlowId(OID:1.3.6.1.2.1.10.127.7.1.3.1.1).
                "
            ::= { hwPacketcableGateInfoEntry 7 }

        hwPacketcableDownstreamServiceFlowId  OBJECT-TYPE
            SYNTAX     Unsigned32
            MAX-ACCESS   read-only
            STATUS      current
            DESCRIPTION
                "
                The index of the downstream service flow, which is obtained from docsQosServiceFlowId(OID:1.3.6.1.2.1.10.127.7.1.3.1.1).
                "
            ::= { hwPacketcableGateInfoEntry 8 }

        hwPacketcableGateIfindex  OBJECT-TYPE
            SYNTAX     InterfaceIndexOrZero
            MAX-ACCESS   read-only
            STATUS      current
            DESCRIPTION
                "
                The ifIndex is an ifType of docsCableMaclayer(127).
                "
            ::= { hwPacketcableGateInfoEntry 9 }

      --Table   hwPacketcableGateInfoTable  begin

      --Table   hwPacketcableGateStatisticsTable  begin

        hwPacketcableGateStatisticsTable OBJECT-TYPE
            SYNTAX     SEQUENCE OF HwPacketcableGateStatisticsEntry
            MAX-ACCESS not-accessible
            STATUS     current
            DESCRIPTION
                "
                Indicates the statistics of the gate.
                The index of this table is hwPacketcableVersion.
                "
            ::= { hwPacketCableObject 3 }

        hwPacketcableGateStatisticsEntry OBJECT-TYPE
            SYNTAX     HwPacketcableGateStatisticsEntry
            MAX-ACCESS not-accessible
            STATUS     current
            DESCRIPTION
                "
                Indicates the statistics of the gate.
                The index of this entry is hwPacketcableVersion.
                "
            INDEX       { hwPacketcableVersion }
            ::= { hwPacketcableGateStatisticsTable 1 }

        HwPacketcableGateStatisticsEntry ::=
            SEQUENCE {
                hwPacketcableVersion               INTEGER,
                hwPacketcableGateAllocNum          Counter32,
                hwPacketcableGateAllocAckNum       Counter32,
                hwPacketcableGateAllocErrNum       Counter32,
                hwPacketcableGateSetNum            Counter32,
                hwPacketcableGateSetAckNum         Counter32,
                hwPacketcableGateSetErrNum         Counter32,
                hwPacketcableGateInfoNum           Counter32,
                hwPacketcableGateInfoAckNum        Counter32,
                hwPacketcableGateInfoErrNum        Counter32,
                hwPacketcableGateDeleteNum         Counter32,
                hwPacketcableGateDeleteAckNum      Counter32,
                hwPacketcableGateDeleteErrNum      Counter32,
                hwPacketcableGateOpenNum           Counter32,
                hwPacketcableGateCloseNum          Counter32,
                hwPacketcableGateReportStateNum    Counter32,
                hwPacketcableGateCmdErrNum         Counter32
            }

        hwPacketcableVersion  OBJECT-TYPE
            SYNTAX     INTEGER
            {
                packetcable1x(1),
                packetcableMultimedia(2)
            }
            MAX-ACCESS   not-accessible
            STATUS      current
            DESCRIPTION
                "
                The version of PacketCable.
                Options:
                1. packetcable1x(1)            - Indicates the PacketCable 1.x
                2. packetcableMultimedia(2)    - Indicates the PacketCable Multimedia
                "
            ::= { hwPacketcableGateStatisticsEntry 1 }

        hwPacketcableGateAllocNum  OBJECT-TYPE
            SYNTAX     Counter32
            MAX-ACCESS   read-only
            STATUS      current
            DESCRIPTION
                "
                The count of the received Gate-Alloc packet.
                "
            ::= { hwPacketcableGateStatisticsEntry 2 }

        hwPacketcableGateAllocAckNum  OBJECT-TYPE
            SYNTAX     Counter32
            MAX-ACCESS   read-only
            STATUS      current
            DESCRIPTION
                "
                The count of the received Gate-Alloc-Ack packet.
                "
            ::= { hwPacketcableGateStatisticsEntry 3 }

        hwPacketcableGateAllocErrNum  OBJECT-TYPE
            SYNTAX     Counter32
            MAX-ACCESS   read-only
            STATUS      current
            DESCRIPTION
                "
                The count of the received Gate-Alloc-Err packet.
                "
            ::= { hwPacketcableGateStatisticsEntry 4 }

        hwPacketcableGateSetNum  OBJECT-TYPE
            SYNTAX     Counter32
            MAX-ACCESS   read-only
            STATUS      current
            DESCRIPTION
                "
                The count of the received Gate-Set packet.
                "
            ::= { hwPacketcableGateStatisticsEntry 5 }

        hwPacketcableGateSetAckNum  OBJECT-TYPE
            SYNTAX     Counter32
            MAX-ACCESS   read-only
            STATUS      current
            DESCRIPTION
                "
                The count of the received Gate-Set-Ack packet.
                "
            ::= { hwPacketcableGateStatisticsEntry 6 }

        hwPacketcableGateSetErrNum  OBJECT-TYPE
            SYNTAX     Counter32
            MAX-ACCESS   read-only
            STATUS      current
            DESCRIPTION
                "
                The count of the received Gate-Set-Err packet.
                "
            ::= { hwPacketcableGateStatisticsEntry 7 }

        hwPacketcableGateInfoNum  OBJECT-TYPE
            SYNTAX     Counter32
            MAX-ACCESS   read-only
            STATUS      current
            DESCRIPTION
                "
                The count of the received Gate-Info packet.
                "
            ::= { hwPacketcableGateStatisticsEntry 8 }

        hwPacketcableGateInfoAckNum  OBJECT-TYPE
            SYNTAX     Counter32
            MAX-ACCESS   read-only
            STATUS      current
            DESCRIPTION
                "
                The count of the received Gate-Info-Ack packet.
                "
            ::= { hwPacketcableGateStatisticsEntry 9 }

        hwPacketcableGateInfoErrNum  OBJECT-TYPE
            SYNTAX     Counter32
            MAX-ACCESS   read-only
            STATUS      current
            DESCRIPTION
                "
                The count of the received Gate-Info-Err packet.
                "
            ::= { hwPacketcableGateStatisticsEntry 10 }

        hwPacketcableGateDeleteNum  OBJECT-TYPE
            SYNTAX     Counter32
            MAX-ACCESS   read-only
            STATUS      current
            DESCRIPTION
                "
                The count of the received Gate-Delete packet.
                "
            ::= { hwPacketcableGateStatisticsEntry 11 }

        hwPacketcableGateDeleteAckNum  OBJECT-TYPE
            SYNTAX     Counter32
            MAX-ACCESS   read-only
            STATUS      current
            DESCRIPTION
                "
                The count of the received Gate-Delete-Ack packet.
                "
            ::= { hwPacketcableGateStatisticsEntry 12 }

        hwPacketcableGateDeleteErrNum  OBJECT-TYPE
            SYNTAX     Counter32
            MAX-ACCESS   read-only
            STATUS      current
            DESCRIPTION
                "
                The count of the received Gate-Delete-Err packet.
                "
            ::= { hwPacketcableGateStatisticsEntry 13 }

        hwPacketcableGateOpenNum  OBJECT-TYPE
            SYNTAX     Counter32
            MAX-ACCESS   read-only
            STATUS      current
            DESCRIPTION
                "
                The count of the received Gate-Open packet.
                "
            ::= { hwPacketcableGateStatisticsEntry 14 }

        hwPacketcableGateCloseNum  OBJECT-TYPE
            SYNTAX     Counter32
            MAX-ACCESS   read-only
            STATUS      current
            DESCRIPTION
                "
                The count of the received Gate-Close packet.
                "
            ::= { hwPacketcableGateStatisticsEntry 15 }

        hwPacketcableGateReportStateNum  OBJECT-TYPE
            SYNTAX     Counter32
            MAX-ACCESS   read-only
            STATUS      current
            DESCRIPTION
                "
                The count of the received Gate-Report-State packet.
                "
            ::= { hwPacketcableGateStatisticsEntry 16 }

        hwPacketcableGateCmdErrNum  OBJECT-TYPE
            SYNTAX     Counter32
            MAX-ACCESS   read-only
            STATUS      current
            DESCRIPTION
                "
                The count of the received Gate-Cmd-Err packet.
                "
            ::= { hwPacketcableGateStatisticsEntry 17 }

      --Table   hwPacketcableGateStatisticsTable  begin

    -- hwPacketCableObject  end

    hwCmtsTrafficBurstConfigObject OBJECT IDENTIFIER ::= { hwCmtsServiceObject  2}

    --hwCmtsTrafficBurstConfigObject begin

      hwCmtsTrafficBurstUpstreamEnable OBJECT-TYPE
        SYNTAX TruthValue
        MAX-ACCESS read-write
        STATUS current
        DESCRIPTION
              "Indicates upstream traffic burst status.
               Options:
               1. true(1)  -enable upstream traffic burst
               2. false(2) -disable upstream traffic burst
               Default: false(2)
              "
        ::= { hwCmtsTrafficBurstConfigObject 1 }

      hwCmtsTrafficBurstDownstreamEnable OBJECT-TYPE
        SYNTAX TruthValue
        MAX-ACCESS read-write
        STATUS current
        DESCRIPTION
              "Indicates downstream traffic burst status.
               Options:
               1. true(1)  -enable downstream traffic burst
               2. false(2) -disable downstream traffic burst
               Default: false(2)
              "
        ::= { hwCmtsTrafficBurstConfigObject 2 }

    --hwCmtsTrafficBurstConfigObject end

    hwCmtsQoSAdjustConfigObject OBJECT IDENTIFIER ::= { hwCmtsServiceObject 3 }
        
        hwCmtsQosAdjustRuleTable OBJECT-TYPE
            SYNTAX SEQUENCE OF HwCmtsQosAdjustRuleEntry
            MAX-ACCESS not-accessible
            STATUS current
            DESCRIPTION
                "
                Indicates the configuration of the QoS adjust rule.
                The index of this table is hwCmtsQosAdjustRuleName.
                "
            ::= { hwCmtsQoSAdjustConfigObject 1 }
        
        hwCmtsQosAdjustRuleEntry OBJECT-TYPE
            SYNTAX HwCmtsQosAdjustRuleEntry
            MAX-ACCESS not-accessible
            STATUS current
            DESCRIPTION
                "
                Indicates the configuration of the QoS adjust rule.
                The index of this entry is hwCmtsQosAdjustRuleName.
                "
            INDEX { hwCmtsQosAdjustRuleName }
            ::= { hwCmtsQosAdjustRuleTable 1 }
        
        HwCmtsQosAdjustRuleEntry ::=
            SEQUENCE { 
                hwCmtsQosAdjustRuleName
                    OCTET STRING,
                hwCmtsQosAdjustRuleMonitoringMode
                    INTEGER,
                hwCmtsQosAdjustRuleServiceClassBasic
                    OCTET STRING,
                hwCmtsQosAdjustRuleServiceClassAdjust
                    OCTET STRING,
                hwCmtsQosAdjustRuleDirection
                    INTEGER,
                hwCmtsQosAdjustRuleAdjustPeriod
                    Unsigned32,
                hwCmtsQosAdjustRuleAdjustResetTimeHour
                    Unsigned32,
                hwCmtsQosAdjustRuleAdjustResetTimeMin
                    Unsigned32,
                hwCmtsQosAdjustRuleAdjustResetContinueMonitoring
                    TruthValue,
                hwCmtsQosAdjustRuleActive
                    TruthValue,
                hwCmtsQosAdjustRuleActiveThreshold
                    Unsigned32,
                hwCmtsQosAdjustRuleExceedThresholdAutoAdjust
                    TruthValue,
                hwCmtsQosAdjustRuleNopeakMonitoringWindow
                    Unsigned32,
                hwCmtsQosAdjustRuleNopeakMonitoringAvgRate
                    Unsigned32,
                hwCmtsQosAdjustRuleNopeakMonitoringSamplingInterval
                    Unsigned32,
                hwCmtsQosAdjustRuleNopeakMonitoringAdjustPeriod
                    Unsigned32,
                hwCmtsQosAdjustRuleNopeakMonitoringAdjustAuto
                    TruthValue,
                hwCmtsQosAdjustRuleWeekendNopeakMonitoringEnable
                    TruthValue,
                hwCmtsQosAdjustRuleWeekendNopeakMonitoringWindow
                    Unsigned32,
                hwCmtsQosAdjustRuleWeekendNopeakMonitoringAvgRate
                    Unsigned32,
                hwCmtsQosAdjustRuleWeekendNopeakMonitoringSamplingInterval
                    Unsigned32,
                hwCmtsQosAdjustRuleWeekendNopeakMonitoringAdjustPeriod
                    Unsigned32,
                hwCmtsQosAdjustRuleWeekendNopeakMonitoringAdjustAuto
                    TruthValue,
                hwCmtsQosAdjustRulePeakMonitoringTimeHour1
                    Unsigned32,
                hwCmtsQosAdjustRulePeakMonitoringTimeMin1
                    Unsigned32,
                hwCmtsQosAdjustRulePeakMonitoringWindow1
                    Unsigned32,
                hwCmtsQosAdjustRulePeakMonitoringAvgRate1
                    Unsigned32,
                hwCmtsQosAdjustRulePeakMonitoringTimeHour2
                    Unsigned32,
                hwCmtsQosAdjustRulePeakMonitoringTimeMin2
                    Unsigned32,
                hwCmtsQosAdjustRulePeakMonitoringWindow2
                    Unsigned32,
                hwCmtsQosAdjustRulePeakMonitoringAvgRate2
                    Unsigned32,
                hwCmtsQosAdjustRulePeakMonitoringRemainWindow
                    Unsigned32,
                hwCmtsQosAdjustRulePeakMonitoringRemainAvgRate
                    Unsigned32,
                hwCmtsQosAdjustRulePeakMonitoringSamplingInterval
                    Unsigned32,
                hwCmtsQosAdjustRulePeakMonitoringAdjustPeriod
                    Unsigned32,
                hwCmtsQosAdjustRulePeakMonitoringAdjustAuto
                    TruthValue,
                hwCmtsQosAdjustRuleWeekendPeakMonitoringEnable
                    TruthValue,
                hwCmtsQosAdjustRuleWeekendPeakMonitoringTimeHour1
                    Unsigned32,
                hwCmtsQosAdjustRuleWeekendPeakMonitoringTimeMin1
                    Unsigned32,
                hwCmtsQosAdjustRuleWeekendPeakMonitoringWindow1
                    Unsigned32,
                hwCmtsQosAdjustRuleWeekendPeakMonitoringAvgRate1
                    Unsigned32,
                hwCmtsQosAdjustRuleWeekendPeakMonitoringTimeHour2
                    Unsigned32,
                hwCmtsQosAdjustRuleWeekendPeakMonitoringTimeMin2
                    Unsigned32,
                hwCmtsQosAdjustRuleWeekendPeakMonitoringWindow2
                    Unsigned32,
                hwCmtsQosAdjustRuleWeekendPeakMonitoringAvgRate2
                    Unsigned32,
                hwCmtsQosAdjustRuleWeekendPeakMonitoringRemainWindow
                    Unsigned32,
                hwCmtsQosAdjustRuleWeekendPeakMonitoringRemainAvgRate
                    Unsigned32,
                hwCmtsQosAdjustRuleWeekendPeakMonitoringSamplingInterval
                    Unsigned32,
                hwCmtsQosAdjustRuleWeekendPeakMonitoringAdjustPeriod
                    Unsigned32,
                hwCmtsQosAdjustRuleWeekendPeakMonitoringAdjustAuto
                    TruthValue,
                hwCmtsQosAdjustRuleRowStatus
                    RowStatus
             }

        hwCmtsQosAdjustRuleName OBJECT-TYPE
            SYNTAX OCTET STRING (SIZE (1..15))
            MAX-ACCESS not-accessible
            STATUS current
            DESCRIPTION
                "Indicates the name of the QoS adjust rule.
                 The main input rules of the string are as follows:
                 1. The ASCII value of characters must be between 0x20 and 0x7E.
                 2. The double quotation marks are not supported. 
                 3. The special characters such as ',', ''', '?', ':', ';', and '~', are not supported."
            ::= { hwCmtsQosAdjustRuleEntry 1 }
        
        hwCmtsQosAdjustRuleMonitoringMode OBJECT-TYPE
            SYNTAX INTEGER
                {
                nopeak(1),
                peak(2)
                }
            MAX-ACCESS read-create
            STATUS current
            DESCRIPTION
                "
                 Indicates the monitoring mode of the QoS adjust rule.
                 Options:
                 1. nopeak(1)          -the no-peak monitoring mode
                 2. peak(2)            -the peak monitoring mode
                 Default: nopeak(1)"
            ::= { hwCmtsQosAdjustRuleEntry 2 }
        
        hwCmtsQosAdjustRuleServiceClassBasic OBJECT-TYPE
            SYNTAX OCTET STRING (SIZE (0..15))
            MAX-ACCESS read-create
            STATUS current
            DESCRIPTION
                "Indicates the basic service class name of the QoS adjust rule. The service class can be created by table docsQosServiceClassTable."
            ::= { hwCmtsQosAdjustRuleEntry 3 }
        
        hwCmtsQosAdjustRuleServiceClassAdjust OBJECT-TYPE
            SYNTAX OCTET STRING (SIZE (0..15))
            MAX-ACCESS read-create
            STATUS current
            DESCRIPTION
                "Indicates the adjust service class name of the QoS adjust rule. The service class can be created by table docsQosServiceClassTable."
            ::= { hwCmtsQosAdjustRuleEntry 4 }
        
        hwCmtsQosAdjustRuleDirection OBJECT-TYPE
            SYNTAX INTEGER
                {
                downstream(1),
                upstream(2),
                invalid(255)
                }
            MAX-ACCESS read-create
            STATUS current
            DESCRIPTION
                "Indicates the direction of the QoS adjust rule.
                 Options:
                 1. downstream(1)          -indicates the downstream direction
                 2. upstream(2)            -indicates the upstream direction
                 3. invalid(255)           -indicates the default value or an undo operation 
                 Default: invalid(255)"
            ::= { hwCmtsQosAdjustRuleEntry 5 }
        
        hwCmtsQosAdjustRuleAdjustPeriod OBJECT-TYPE
            SYNTAX Unsigned32 (1..10080)
            UNITS  "minutes"
            MAX-ACCESS read-create
            STATUS current
            DESCRIPTION
                "Indicates the adjust period of the QoS adjust rule.                  
                 Range: 1-10080, 
                 Default: 1440
                "
            ::= { hwCmtsQosAdjustRuleEntry 6 }
        
        hwCmtsQosAdjustRuleAdjustResetTimeHour OBJECT-TYPE
            SYNTAX Unsigned32 (0..23)
            UNITS  "hours"
            MAX-ACCESS read-create
            STATUS current
            DESCRIPTION
                "Indicates the reset time (hour) of the QoS adjust rule.
                 In the set operation, value 0 indicates an undo operation.
                 In the query operation, if it is not set, the value obtained is 0.                  
                 Range: 0-23, 
                 Default: 0
                "
            ::= { hwCmtsQosAdjustRuleEntry 7 }
        
        hwCmtsQosAdjustRuleAdjustResetTimeMin OBJECT-TYPE
            SYNTAX Unsigned32 (0..59)
            UNITS  "minutes"
            MAX-ACCESS read-create
            STATUS current
            DESCRIPTION
                "Indicates the reset time (minute) of the QoS adjust rule.                  
                 In the set operation, value 0 indicates an undo operation.
                 In the query operation, if it is not set, the value obtained is 0.
                 Range: 0-59, 
                 Default: 0
                "
            ::= { hwCmtsQosAdjustRuleEntry 8 }
        
        hwCmtsQosAdjustRuleAdjustResetContinueMonitoring OBJECT-TYPE
            SYNTAX TruthValue
            MAX-ACCESS read-create
            STATUS current
            DESCRIPTION
                "Indicates whether the monitoring is continued after the reset of the QoS adjust rule.
                 Options:
                 1. true(1)          -indicates the monitoring is continued after the reset of the QoS adjust rule
                 2. false(2)         -indicates the monitoring is not continued after the reset of the QoS adjust rule
                 Default: false(2)"
            ::= { hwCmtsQosAdjustRuleEntry 9 }
        
        hwCmtsQosAdjustRuleActive OBJECT-TYPE
            SYNTAX TruthValue
            MAX-ACCESS read-create
            STATUS current
            DESCRIPTION
                "Indicates the status of the QoS adjust rule.
                 Options:
                 1. true(1)          -indicates the status of the QoS adjust rule is active
                 2. false(2)         -indicates the status of the QoS adjust rule is not active
                 Default: false(2)"
            ::= { hwCmtsQosAdjustRuleEntry 10 }
        
        hwCmtsQosAdjustRuleActiveThreshold OBJECT-TYPE
            SYNTAX Unsigned32 (0..4294967)
            UNITS  "KBytes"
            MAX-ACCESS read-create
            STATUS current
            DESCRIPTION
                "
                 Indicates the threshold of the QoS adjust rule.
                 In the set operation, value 0 indicates an undo operation.
                 In the query operation, if it is not set, the value obtained is 0.                  
                 Range: 0-4294967, 
                 Default: 0
                "
            ::= { hwCmtsQosAdjustRuleEntry 11 }
        
        hwCmtsQosAdjustRuleExceedThresholdAutoAdjust OBJECT-TYPE
            SYNTAX TruthValue
            MAX-ACCESS read-create
            STATUS current
            DESCRIPTION
                "Indicates the switch of the automatic adjustment function when the service-flow exceeds the threshold.
                 Options:
                 1. true(1)          -indicates the function is on
                 2. false(2)         -indicates the function is off
                 Default: false(2)"
            ::= { hwCmtsQosAdjustRuleEntry 12 }
        
        hwCmtsQosAdjustRuleNopeakMonitoringWindow OBJECT-TYPE
            SYNTAX Unsigned32 (10..44640)
            UNITS  "minutes"
            MAX-ACCESS read-create
            STATUS current
            DESCRIPTION
                "Indicates the monitoring window size when the monitoring mode of the QoS adjust rule is no-peak.                  
                 Range: 10-44640, 
                 Default: 180
                "
            ::= { hwCmtsQosAdjustRuleEntry 13 }
        
        hwCmtsQosAdjustRuleNopeakMonitoringAvgRate OBJECT-TYPE
            SYNTAX Unsigned32 (0..400000)
            UNITS  "kbps"
            MAX-ACCESS read-create
            STATUS current
            DESCRIPTION
                "Indicates the monitoring average rate when the monitoring mode of the QoS adjust rule is no-peak.
                 In the set operation, value 0 indicates an undo operation.
                 In the query operation, if it is not set, the value obtained is 0.                   
                 Range: 0-400000, 
                 Default: 0
                "
            ::= { hwCmtsQosAdjustRuleEntry 14 }
        
        hwCmtsQosAdjustRuleNopeakMonitoringSamplingInterval OBJECT-TYPE
            SYNTAX Unsigned32 (10..30)
            UNITS  "minutes"
            MAX-ACCESS read-create
            STATUS current
            DESCRIPTION
                "Indicates the monitoring sampling interval when the monitoring mode of the QoS adjust rule is no-peak.                  
                 Range: 10-30, 
                 Default: 20
                "
            ::= { hwCmtsQosAdjustRuleEntry 15 }
        
        hwCmtsQosAdjustRuleNopeakMonitoringAdjustPeriod OBJECT-TYPE
            SYNTAX Unsigned32 (0..10080)
            UNITS  "minutes"
            MAX-ACCESS read-create
            STATUS current
            DESCRIPTION
                "Indicates the adjust period when the monitoring mode of the QoS adjust rule is no-peak. 
                 In the set operation, value 0 indicates an undo operation.
                 In the query operation, if it is not set, the value obtained is 0.
                 0 indicates that use the value of the hwCmtsQosAdjustRuleAdjustPeriod node as the adjust period.
                 Range: 0-10080, 
                 Default: 0
                "
            ::= { hwCmtsQosAdjustRuleEntry 16 }
        
        hwCmtsQosAdjustRuleNopeakMonitoringAdjustAuto OBJECT-TYPE
            SYNTAX TruthValue
            MAX-ACCESS read-create
            STATUS current
            DESCRIPTION
                "Indicates the switch of the automatic adjustment function when the monitoring mode of the QoS adjust rule is no-peak.
                 Options:
                 1. true(1)          -indicates the function is on
                 2. false(2)         -indicates the function is off
                 Default: false(2)"
            ::= { hwCmtsQosAdjustRuleEntry 17 }
        
        hwCmtsQosAdjustRuleWeekendNopeakMonitoringEnable OBJECT-TYPE
            SYNTAX TruthValue
            MAX-ACCESS read-create
            STATUS current
            DESCRIPTION
                 "Indicates the switch of the weekend monitoring function when the monitoring mode of the QoS adjust rule is no-peak.
                 Options:
                 1. true(1)          -indicates the function is on
                 2. false(2)         -indicates the function is off
                 Default: false(2)"
            ::= { hwCmtsQosAdjustRuleEntry 18 }
        
        hwCmtsQosAdjustRuleWeekendNopeakMonitoringWindow OBJECT-TYPE
            SYNTAX Unsigned32 (10..44640)
            UNITS  "minutes"
            MAX-ACCESS read-create
            STATUS current
            DESCRIPTION
                "Indicates the weekend monitoring window size when the monitoring mode of the QoS adjust rule is no-peak.                  
                 Range: 10-44640, 
                 Default: 180
                "
            ::= { hwCmtsQosAdjustRuleEntry 19 }
        
        hwCmtsQosAdjustRuleWeekendNopeakMonitoringAvgRate OBJECT-TYPE
            SYNTAX Unsigned32 (0..400000)
            UNITS  "minutes"
            MAX-ACCESS read-create
            STATUS current
            DESCRIPTION
                "Indicates the weekend monitoring average rate when the monitoring mode of the QoS adjust rule is no-peak.
                 In the set operation, value 0 indicates an undo operation.
                 In the query operation, if it is not set, the value obtained is 0.                   
                 Range: 0-400000, 
                 Default: 0
                "
            ::= { hwCmtsQosAdjustRuleEntry 20 }
        
        hwCmtsQosAdjustRuleWeekendNopeakMonitoringSamplingInterval OBJECT-TYPE
            SYNTAX Unsigned32 (10..30)
            UNITS  "minutes"
            MAX-ACCESS read-create
            STATUS current
            DESCRIPTION
                "Indicates the weekend monitoring sampling interval when the monitoring mode of the QoS adjust rule is no-peak.                  
                 Range: 10-30, 
                 Default: 20
                "
            ::= { hwCmtsQosAdjustRuleEntry 21 }
        
        hwCmtsQosAdjustRuleWeekendNopeakMonitoringAdjustPeriod OBJECT-TYPE
            SYNTAX Unsigned32 (0..10080)
            UNITS  "minutes"
            MAX-ACCESS read-create
            STATUS current
            DESCRIPTION
                "Indicates the weekend adjust period when the monitoring mode of the QoS adjust rule is no-peak. 
                 In the set operation, value 0 indicates an undo operation.
                 In the query operation, if it is not set, the value obtained is 0.
                 0 indicates that use the value of the hwCmtsQosAdjustRuleAdjustPeriod node as the adjust period.
                 Range: 0-10080, 
                 Default: 0
                "
            ::= { hwCmtsQosAdjustRuleEntry 22 }
        
        hwCmtsQosAdjustRuleWeekendNopeakMonitoringAdjustAuto OBJECT-TYPE
            SYNTAX TruthValue
            MAX-ACCESS read-create
            STATUS current
            DESCRIPTION
                "Indicates the switch of the weekend automatic adjustment function when the monitoring mode of the QoS adjust rule is no-peak.
                 Options:
                 1. true(1)          -indicates the function is on
                 2. false(2)         -indicates the function is off
                 Default: false(2)"
            ::= { hwCmtsQosAdjustRuleEntry 23 }
        
        hwCmtsQosAdjustRulePeakMonitoringTimeHour1 OBJECT-TYPE
            SYNTAX Unsigned32 (0..23)
            UNITS  "hours"
            MAX-ACCESS read-create
            STATUS current
            DESCRIPTION
                "Indicates the monitoring time (hour) of the first peak when the monitoring mode of the QoS adjust rule is peak.                  
                 In the set operation, value 0 indicates an undo operation.
                 In the query operation, if it is not set, the value obtained is 0.
                 Range: 0-23, 
                 Default: 0
                "
            ::= { hwCmtsQosAdjustRuleEntry 24 }
        
        hwCmtsQosAdjustRulePeakMonitoringTimeMin1 OBJECT-TYPE
            SYNTAX Unsigned32 (0..59)
            UNITS  "minutes"
            MAX-ACCESS read-create
            STATUS current
            DESCRIPTION
                "Indicates the monitoring time (minute) of the first peak when the monitoring mode of the QoS adjust rule is peak. 
                 In the set operation, value 0 indicates an undo operation.
                 In the query operation, if it is not set, the value obtained is 0.
                 Range: 0-59, 
                 Default: 0
                "
            ::= { hwCmtsQosAdjustRuleEntry 25 }
        
        hwCmtsQosAdjustRulePeakMonitoringWindow1 OBJECT-TYPE
            SYNTAX Unsigned32 (0 | 60..1440)
            UNITS  "minutes"
            MAX-ACCESS read-create
            STATUS current
            DESCRIPTION
                "Indicates the monitoring window size of the first peak when the monitoring mode of the QoS adjust rule is peak.                  
                 In the set operation, value 0 indicates an undo operation.
                 In the query operation, if it is not set, the value obtained is 0.
                 Range: 0 | 60..1440, 
                 Default: 0
                "
            ::= { hwCmtsQosAdjustRuleEntry 26 }
        
        hwCmtsQosAdjustRulePeakMonitoringAvgRate1 OBJECT-TYPE
            SYNTAX Unsigned32 (0..400000)
            UNITS  "kbps"
            MAX-ACCESS read-create
            STATUS current
            DESCRIPTION
                "Indicates the monitoring average rate of the first peak when the monitoring mode of the QoS adjust rule is peak.
                 In the set operation, value 0 indicates an undo operation.
                 In the query operation, if it is not set, the value obtained is 0.                   
                 Range: 0-400000, 
                 Default: 0
                "
            ::= { hwCmtsQosAdjustRuleEntry 27 }
        
        hwCmtsQosAdjustRulePeakMonitoringTimeHour2 OBJECT-TYPE
            SYNTAX Unsigned32 (0..23)
            UNITS  "hours"
            MAX-ACCESS read-create
            STATUS current
            DESCRIPTION
                "Indicates the monitoring time (hour) of the second peak when the monitoring mode of the QoS adjust rule is peak.                  
                 In the set operation, value 0 indicates an undo operation.
                 In the query operation, if it is not set, the value obtained is 0.
                 Range: 0-23, 
                 Default: 0
                "
            ::= { hwCmtsQosAdjustRuleEntry 28 }
        
        hwCmtsQosAdjustRulePeakMonitoringTimeMin2 OBJECT-TYPE
            SYNTAX Unsigned32 (0..59)
            UNITS  "minutes"
            MAX-ACCESS read-create
            STATUS current
            DESCRIPTION
                "Indicates the monitoring time (minute) of the second peak when the monitoring mode of the QoS adjust rule is peak. 
                 In the set operation, value 0 indicates an undo operation.
                 In the query operation, if it is not set, the value obtained is 0.
                 Range: 0-59, 
                 Default: 0
                "
            ::= { hwCmtsQosAdjustRuleEntry 29 }
        
        hwCmtsQosAdjustRulePeakMonitoringWindow2 OBJECT-TYPE
            SYNTAX Unsigned32 (0 | 60..1440)
            UNITS  "minutes"
            MAX-ACCESS read-create
            STATUS current
            DESCRIPTION
                "Indicates the monitoring window size of the second peak when the monitoring mode of the QoS adjust rule is peak.                  
                 In the set operation, value 0 indicates an undo operation.
                 In the query operation, if it is not set, the value obtained is 0.
                 Range: 60-1440, 
                 Default: 0
                "
            ::= { hwCmtsQosAdjustRuleEntry 30 }
        
        hwCmtsQosAdjustRulePeakMonitoringAvgRate2 OBJECT-TYPE
            SYNTAX Unsigned32 (0..400000)
            UNITS  "kbps"
            MAX-ACCESS read-create
            STATUS current
            DESCRIPTION
                "Indicates the monitoring average rate of the second peak when the monitoring mode of the QoS adjust rule is peak.
                 In the set operation, value 0 indicates an undo operation.
                 In the query operation, if it is not set, the value obtained is 0.                   
                 Range: 0-400000, 
                 Default: 0
                "
            ::= { hwCmtsQosAdjustRuleEntry 31 }
        
        hwCmtsQosAdjustRulePeakMonitoringRemainWindow OBJECT-TYPE
            SYNTAX Unsigned32 (0 | 60..1440)
            UNITS  "minutes"
            MAX-ACCESS read-create
            STATUS current
            DESCRIPTION
                "Indicates the remain monitoring window size when the monitoring mode of the QoS adjust rule is peak.                  
                 In the set operation, value 0 indicates an undo operation.
                 In the query operation, if it is not set, the value obtained is 0.
                 Range: 60-1440, 
                 Default: 0
                "
            ::= { hwCmtsQosAdjustRuleEntry 32 }
        
        hwCmtsQosAdjustRulePeakMonitoringRemainAvgRate OBJECT-TYPE
            SYNTAX Unsigned32 (0..400000)
            UNITS  "kbps"
            MAX-ACCESS read-create
            STATUS current
            DESCRIPTION
                "Indicates the remain monitoring average rate when the monitoring mode of the QoS adjust rule is peak.
                 In the set operation, value 0 indicates an undo operation.
                 In the query operation, if it is not set, the value obtained is 0.                   
                 Range: 0-400000, 
                 Default: 0
                "
            ::= { hwCmtsQosAdjustRuleEntry 33 }
        
        hwCmtsQosAdjustRulePeakMonitoringSamplingInterval OBJECT-TYPE
            SYNTAX Unsigned32 (10..30)
            UNITS  "minutes"
            MAX-ACCESS read-create
            STATUS current
            DESCRIPTION
                "Indicates the monitoring sampling interval when the monitoring mode of the QoS adjust rule is peak.                  
                 Range: 10-30, 
                 Default: 20
                "
            ::= { hwCmtsQosAdjustRuleEntry 34 }
        
        hwCmtsQosAdjustRulePeakMonitoringAdjustPeriod OBJECT-TYPE
            SYNTAX Unsigned32 (0..10080)
            UNITS  "minutes"
            MAX-ACCESS read-create
            STATUS current
            DESCRIPTION
                "Indicates the adjust period when the monitoring mode of the QoS adjust rule is peak. 
                 In the set operation, value 0 indicates an undo operation.
                 In the query operation, if it is not set, the value obtained is 0.
                 0 indicates that use the value of the hwCmtsQosAdjustRuleAdjustPeriod node as the adjust period.
                 Range: 0-10080, 
                 Default: 0
                "
            ::= { hwCmtsQosAdjustRuleEntry 35 }
        
        hwCmtsQosAdjustRulePeakMonitoringAdjustAuto OBJECT-TYPE
            SYNTAX TruthValue
            MAX-ACCESS read-create
            STATUS current
            DESCRIPTION
                "Indicates the switch of the automatic adjustment function when the monitoring mode of the QoS adjust rule is peak.
                 Options:
                 1. true(1)          -indicates the function is on
                 2. false(2)         -indicates the function is off
                 Default: false(2)"
            ::= { hwCmtsQosAdjustRuleEntry 36 }
        
        hwCmtsQosAdjustRuleWeekendPeakMonitoringEnable OBJECT-TYPE
            SYNTAX TruthValue
            MAX-ACCESS read-create
            STATUS current
            DESCRIPTION
                 "Indicates the switch of the weekend monitoring function when the monitoring mode of the QoS adjust rule is peak.
                 Options:
                 1. true(1)          -indicates the function is on
                 2. false(2)         -indicates the function is off
                 Default: false(2)"
            ::= { hwCmtsQosAdjustRuleEntry 37 }
        
        hwCmtsQosAdjustRuleWeekendPeakMonitoringTimeHour1 OBJECT-TYPE
            SYNTAX Unsigned32 (0..23)
            UNITS  "hours"
            MAX-ACCESS read-create
            STATUS current
            DESCRIPTION
                "Indicates the monitoring time (hour) of the first weekend peak when the monitoring mode of the QoS adjust rule is peak.                  
                 In the set operation, value 0 indicates an undo operation.
                 In the query operation, if it is not set, the value obtained is 0.
                 Range: 0-23, 
                 Default: 0
                "
            ::= { hwCmtsQosAdjustRuleEntry 38 }
 
        hwCmtsQosAdjustRuleWeekendPeakMonitoringTimeMin1 OBJECT-TYPE
            SYNTAX Unsigned32 (0..59)
            UNITS  "minutes"
            MAX-ACCESS read-create
            STATUS current
            DESCRIPTION
                "Indicates the monitoring time (minute) of the first weekend peak when the monitoring mode of the QoS adjust rule is peak. 
                 In the set operation, value 0 indicates an undo operation.
                 In the query operation, if it is not set, the value obtained is 0.
                 Range: 0-59, 
                 Default: 0
                "
            ::= { hwCmtsQosAdjustRuleEntry 39 }
        
                   
        hwCmtsQosAdjustRuleWeekendPeakMonitoringWindow1 OBJECT-TYPE
            SYNTAX Unsigned32 (0 | 60..1440)
            UNITS  "minutes"
            MAX-ACCESS read-create
            STATUS current
            DESCRIPTION
                "Indicates the monitoring window size of the first weekend peak when the monitoring mode of the QoS adjust rule is peak.                  
                 In the set operation, value 0 indicates an undo operation.
                 In the query operation, if it is not set, the value obtained is 0.
                 Range: 0 | 60..1440, 
                 Default: 0
                "
            ::= { hwCmtsQosAdjustRuleEntry 40 }
        
        hwCmtsQosAdjustRuleWeekendPeakMonitoringAvgRate1 OBJECT-TYPE
            SYNTAX Unsigned32 (0..400000)
            UNITS  "kbps"
            MAX-ACCESS read-create
            STATUS current
            DESCRIPTION
                "Indicates the monitoring average rate of the first weekend peak when the monitoring mode of the QoS adjust rule is peak.
                 In the set operation, value 0 indicates an undo operation.
                 In the query operation, if it is not set, the value obtained is 0.                   
                 Range: 0-400000, 
                 Default: 0
                "
            ::= { hwCmtsQosAdjustRuleEntry 41 }
        
        hwCmtsQosAdjustRuleWeekendPeakMonitoringTimeHour2 OBJECT-TYPE
            SYNTAX Unsigned32 (0..23)
            UNITS  "hours"
            MAX-ACCESS read-create
            STATUS current
            DESCRIPTION
                "Indicates the monitoring time (hour) of the second weekend peak when the monitoring mode of the QoS adjust rule is peak.                  
                 In the set operation, value 0 indicates an undo operation.
                 In the query operation, if it is not set, the value obtained is 0.
                 Range: 0-23, 
                 Default: 0
                "
            ::= { hwCmtsQosAdjustRuleEntry 42 }
        
        hwCmtsQosAdjustRuleWeekendPeakMonitoringTimeMin2 OBJECT-TYPE
            SYNTAX Unsigned32 (0..59)
            UNITS  "minutes"
            MAX-ACCESS read-create
            STATUS current
            DESCRIPTION
                "Indicates the monitoring time (minute) of the second weekend peak when the monitoring mode of the QoS adjust rule is peak. 
                 In the set operation, value 0 indicates an undo operation.
                 In the query operation, if it is not set, the value obtained is 0.
                 Range: 0-59, 
                 Default: 0
                "
            ::= { hwCmtsQosAdjustRuleEntry 43 }
        
        hwCmtsQosAdjustRuleWeekendPeakMonitoringWindow2 OBJECT-TYPE
            SYNTAX Unsigned32 (0 | 60..1440)
            UNITS  "minutes"
            MAX-ACCESS read-create
            STATUS current
            DESCRIPTION
                "Indicates the monitoring window size of the second weekend peak when the monitoring mode of the QoS adjust rule is peak.                  
                 In the set operation, value 0 indicates an undo operation.
                 In the query operation, if it is not set, the value obtained is 0.
                 Range: 60-1440, 
                 Default: 0
                "
            ::= { hwCmtsQosAdjustRuleEntry 44 }
        
        hwCmtsQosAdjustRuleWeekendPeakMonitoringAvgRate2 OBJECT-TYPE
            SYNTAX Unsigned32 (0..400000)
            UNITS  "kbps"
            MAX-ACCESS read-create
            STATUS current
            DESCRIPTION
                "Indicates the monitoring average rate of the second weekend peak when the monitoring mode of the QoS adjust rule is peak.
                 In the set operation, value 0 indicates an undo operation.
                 In the query operation, if it is not set, the value obtained is 0.                   
                 Range: 0-400000, 
                 Default: 0
                "
            ::= { hwCmtsQosAdjustRuleEntry 45 }
        
        hwCmtsQosAdjustRuleWeekendPeakMonitoringRemainWindow OBJECT-TYPE
            SYNTAX Unsigned32 (0 | 60..1440)
            UNITS  "minutes"
            MAX-ACCESS read-create
            STATUS current
            DESCRIPTION
                "Indicates the weekend remain monitoring window size when the monitoring mode of the QoS adjust rule is peak.                  
                 In the set operation, value 0 indicates an undo operation.
                 In the query operation, if it is not set, the value obtained is 0.
                 Range: 60-1440, 
                 Default: 0
                "
            ::= { hwCmtsQosAdjustRuleEntry 46 }
        
        hwCmtsQosAdjustRuleWeekendPeakMonitoringRemainAvgRate OBJECT-TYPE
            SYNTAX Unsigned32 (0..400000)
            UNITS  "kbps"
            MAX-ACCESS read-create
            STATUS current
            DESCRIPTION
                "Indicates the weekend remain monitoring average rate when the monitoring mode of the QoS adjust rule is peak.
                 In the set operation, value 0 indicates an undo operation.
                 In the query operation, if it is not set, the value obtained is 0.                   
                 Range: 0-400000, 
                 Default: 0
                "
            ::= { hwCmtsQosAdjustRuleEntry 47 }
        
        hwCmtsQosAdjustRuleWeekendPeakMonitoringSamplingInterval OBJECT-TYPE
            SYNTAX Unsigned32 (10..30)
            UNITS  "minutes"
            MAX-ACCESS read-create
            STATUS current
            DESCRIPTION
                "Indicates the weekend monitoring sampling interval when the monitoring mode of the QoS adjust rule is peak.                  
                 Range: 10-30, 
                 Default: 20
                "
            ::= { hwCmtsQosAdjustRuleEntry 48 }
        
        hwCmtsQosAdjustRuleWeekendPeakMonitoringAdjustPeriod OBJECT-TYPE
            SYNTAX Unsigned32 (0..10080)
            UNITS  "minutes"
            MAX-ACCESS read-create
            STATUS current
            DESCRIPTION
                "Indicates the weekend adjust period when the monitoring mode of the QoS adjust rule is peak. 
                 In the set operation, value 0 indicates an undo operation.
                 In the query operation, if it is not set, the value obtained is 0.
                 0 indicates that use the value of the hwCmtsQosAdjustRuleAdjustPeriod node as the adjust period.
                 Range: 0-10080, 
                 Default: 0
                "
            ::= { hwCmtsQosAdjustRuleEntry 49 }
        
        hwCmtsQosAdjustRuleWeekendPeakMonitoringAdjustAuto OBJECT-TYPE
            SYNTAX TruthValue
            MAX-ACCESS read-create
            STATUS current
            DESCRIPTION
                "Indicates the switch of the weekend automatic adjustment function when the monitoring mode of the QoS adjust rule is peak.
                 Options:
                 1. true(1)          -indicates the function is on
                 2. false(2)         -indicates the function is off
                 Default: false(2)"
            ::= { hwCmtsQosAdjustRuleEntry 50 }
        
        hwCmtsQosAdjustRuleRowStatus OBJECT-TYPE
            SYNTAX RowStatus
            MAX-ACCESS read-create
            STATUS current
            DESCRIPTION
                "
                This object is used to create a new row or to modify or delete an existing row in this table.
                Options:
                1. active(1)          -the status of the row is active
                2. notInService(2)    -the status of the row is notInService
                3. notReady(3)        -the status of the row is notReady
                4. createAndGo(4)     -the status of the row is createAndGo
                5. createAndWait(5)   -the status of the row is createAndWait
                6. destroy(6)         -the status of the row is destroy
                Active(1) and notInService(2) are states, these values may be read or written.
                NotReady(3) is a state, this value may be read, but not written.
                CreateAndGo(4), createAndWait(5) and destroy(6) are actions, these values may
                be written, but are never read.
                "
            ::= { hwCmtsQosAdjustRuleEntry 255 }
        
        hwCmtsQosAdjustInfoTable OBJECT-TYPE
            SYNTAX SEQUENCE OF HwCmtsQosAdjustInfoEntry
            MAX-ACCESS not-accessible
            STATUS current
            DESCRIPTION
                "Indicates the information of QoS adjusting.
                 The indexes of this table are ifIndex and hwCmtsQosAdjustInfoServiceFlowId."
            ::= { hwCmtsQoSAdjustConfigObject 2 }
        
        hwCmtsQosAdjustInfoEntry OBJECT-TYPE
            SYNTAX HwCmtsQosAdjustInfoEntry
            MAX-ACCESS not-accessible
            STATUS current
            DESCRIPTION
                "Indicates the information of QoS adjusting.
                 The indexes of this entry are ifIndex and hwCmtsQosAdjustInfoServiceFlowId."
            INDEX { ifIndex, hwCmtsQosAdjustInfoServiceFlowId }
            ::= { hwCmtsQosAdjustInfoTable 1 }
        
        HwCmtsQosAdjustInfoEntry ::=
            SEQUENCE { 
                hwCmtsQosAdjustInfoServiceFlowId
                    Unsigned32,
                hwCmtsQosAdjustInfoSfCmMacAddress
                    MacAddress,
                hwCmtsQosAdjustInfoSfRuleName
                    OCTET STRING,
                hwCmtsQosAdjustInfoSfLastExceedAvgRate
                    Unsigned32,
                hwCmtsQosAdjustInfoSfLastAdjustStartTime
                    DateAndTime,
                hwCmtsQosAdjustInfoSfLastAdjustEndTime
                    DateAndTime,
                hwCmtsQosAdjustInfoSfAdjusting
                    TruthValue
             }

        hwCmtsQosAdjustInfoServiceFlowId OBJECT-TYPE
            SYNTAX Unsigned32
            MAX-ACCESS not-accessible
            STATUS current
            DESCRIPTION
                "Indicates an identifier assigned to a Service Flow by CMTS within a MAC Domain.
                 see node docsQosServiceFlowId (1.3.6.1.4.1.4491.2.1.21.1.3.1.1)."
            ::= { hwCmtsQosAdjustInfoEntry 1 }
        
        hwCmtsQosAdjustInfoSfCmMacAddress OBJECT-TYPE
            SYNTAX MacAddress
            MAX-ACCESS read-only
            STATUS current
            DESCRIPTION
                "Indicates the MAC address of the Service Flow by CMTS within a MAC Domain.
                 Default: NULL ASCII string"
            ::= { hwCmtsQosAdjustInfoEntry 2 }
        
        hwCmtsQosAdjustInfoSfRuleName OBJECT-TYPE
            SYNTAX OCTET STRING (SIZE (1..15))
            MAX-ACCESS read-only
            STATUS current
            DESCRIPTION
                "Indicates the QoS adjust rule name of the Service Flow by CMTS within a MAC Domain.
                 Default: NULL ASCII string"
            ::= { hwCmtsQosAdjustInfoEntry 3 }
        
        hwCmtsQosAdjustInfoSfLastExceedAvgRate OBJECT-TYPE
            SYNTAX Unsigned32 (0..4294967)
            UNITS  "kbps"
            MAX-ACCESS read-only
            STATUS current
            DESCRIPTION
                "Indicates the last average rate when the Service Flow exceeds the threshold.                  
                 Range: 0-4294967, 
                 Default: 0
                 "
            ::= { hwCmtsQosAdjustInfoEntry 4 }
        
        hwCmtsQosAdjustInfoSfLastAdjustStartTime OBJECT-TYPE
            SYNTAX DateAndTime
            MAX-ACCESS read-only
            STATUS current
            DESCRIPTION
                "Indicates the start time of the Service Flow's last adjusting.
                 Default: 1970-1-1,0:0:0.0,+0:0"
            ::= { hwCmtsQosAdjustInfoEntry 5 }
        
        hwCmtsQosAdjustInfoSfLastAdjustEndTime OBJECT-TYPE
            SYNTAX DateAndTime
            MAX-ACCESS read-only
            STATUS current
            DESCRIPTION
                "Indicates the end time of the Service Flow's last adjusting.
                 Default: 1970-1-1,0:0:0.0,+0:0"
            ::= { hwCmtsQosAdjustInfoEntry 6 }
        
        hwCmtsQosAdjustInfoSfAdjusting OBJECT-TYPE
            SYNTAX TruthValue
            MAX-ACCESS read-only
            STATUS current
            DESCRIPTION
                "Indicates whether the Service Flow is being adjusted by the QoS adjust rule.
                 Options:
                 1. true(1)          -indicates the Service Flow is being adjusted by the QoS adjust rule
                 2. false(2)         -indicates the Service Flow is not being adjusted by the QoS adjust rule
                 Default: false(2)"
            ::= { hwCmtsQosAdjustInfoEntry 7 }
        
        hwCmtsQosAdjustCancelTable OBJECT-TYPE
            SYNTAX SEQUENCE OF HwCmtsQosAdjustCancelEntry
            MAX-ACCESS not-accessible
            STATUS current
            DESCRIPTION
                "Cancels the adjusting of the CM(Cable Modem).
                 The index of this table is docsIf3CmtsCmRegStatusId."
            ::= { hwCmtsQoSAdjustConfigObject 3 }
        
        hwCmtsQosAdjustCancelEntry OBJECT-TYPE
            SYNTAX HwCmtsQosAdjustCancelEntry
            MAX-ACCESS not-accessible
            STATUS current
            DESCRIPTION                
                "Cancels the adjusting of the CM(Cable Modem).
                 The index of this entry is docsIf3CmtsCmRegStatusId."
            INDEX { docsIf3CmtsCmRegStatusId }
            ::= { hwCmtsQosAdjustCancelTable 1 }
        
        HwCmtsQosAdjustCancelEntry ::=
            SEQUENCE { 
                hwCmtsQosAdjustCancel
                    INTEGER
             }

        hwCmtsQosAdjustCancel OBJECT-TYPE
             SYNTAX  INTEGER 
              {
                 cancel(1)
              }
            MAX-ACCESS read-write
            STATUS current
            DESCRIPTION
                "Indicates cancel the adjusting of the CM(Cable Modem).
                 Options:
                 1. cancel(1)          -indicates cancel the adjusting of the CM(Cable Modem)
                "
            ::= { hwCmtsQosAdjustCancelEntry 1 }
            
        hwCmtsCmServiceFlowTable OBJECT-TYPE
            SYNTAX SEQUENCE OF HwCmtsCmServiceFlowEntry
            MAX-ACCESS not-accessible
            STATUS current
            DESCRIPTION
                "Indicates the Service Flow information of the CM(Cable Modem).
                 The index of this table is docsIf3CmtsCmRegStatusId."
            ::= { hwCmtsQoSAdjustConfigObject 4 }
        
        hwCmtsCmServiceFlowEntry OBJECT-TYPE
            SYNTAX HwCmtsCmServiceFlowEntry
            MAX-ACCESS not-accessible
            STATUS current
            DESCRIPTION
                "Indicates the Service Flow information of the CM(Cable Modem).
                 The index of this entry is docsIf3CmtsCmRegStatusId."
            INDEX { docsIf3CmtsCmRegStatusId }
            ::= { hwCmtsCmServiceFlowTable 1 }
        
        HwCmtsCmServiceFlowEntry ::=
            SEQUENCE { 
                hwCmtsCmServiceFlowIfIndex 
                    InterfaceIndexOrZero,
                hwCmtCmServiceFlowUpstreamList
                    OCTET STRING,
                hwCmtCmServiceFlowDownstreamList
                    OCTET STRING
             }

        hwCmtsCmServiceFlowIfIndex  OBJECT-TYPE
            SYNTAX     InterfaceIndexOrZero
            MAX-ACCESS   read-only
            STATUS      current
            DESCRIPTION
                "
                The ifIndex is an ifType of docsCableMaclayer(127).
                "
            ::= { hwCmtsCmServiceFlowEntry 1 }
            
        hwCmtCmServiceFlowUpstreamList OBJECT-TYPE
            SYNTAX OCTET STRING (SIZE (32))
            MAX-ACCESS read-only
            STATUS current
            DESCRIPTION
                "Indicates the upstream Service Flow index list of the CM(Cable Modem).
                 Every 4 octets represent a Service Flow index(for
                 example, the hexadecimal value 010101010202020203030303000000000000000000 means that 
                 there are three Service Flow indexes: 0x01010101, 0x02020202, and 0x03030303.                   
                 All these gateway addresses must be sorted according to the lexicographical."
            ::= { hwCmtsCmServiceFlowEntry 2 }
            
        hwCmtCmServiceFlowDownstreamList OBJECT-TYPE
            SYNTAX OCTET STRING (SIZE (32))
            MAX-ACCESS read-only
            STATUS current
            DESCRIPTION
                "Indicates the downstream Service Flow list of the CM(Cable Modem).
                 Every 4 octets represent a Service Flow index(for
                 example, the hexadecimal value 010101010202020203030303000000000000000000 means that 
                 there are three Service Flow indexes: 0x01010101, 0x02020202, and 0x03030303.                   
                 All these gateway addresses must be sorted according to the lexicographical."
            ::= { hwCmtsCmServiceFlowEntry 3 }
                
    --Table hwCmtsCmTrafficTable begin
        
    hwCmtsCmTrafficTable OBJECT-TYPE
        SYNTAX     SEQUENCE OF HwCmtsCmTrafficEntry
        MAX-ACCESS not-accessible
        STATUS     current
        DESCRIPTION
            "Indicates the information of cm traffic.
            The index of this table is docsIf3CmtsCmRegStatusId."
        ::= { hwCmtsServiceObject 4 }

    hwCmtsCmTrafficEntry OBJECT-TYPE
        SYNTAX     HwCmtsCmTrafficEntry
        MAX-ACCESS not-accessible
        STATUS     current
        DESCRIPTION
            "Indicates the information of cm traffic.
            The index of this entry is docsIf3CmtsCmRegStatusId."
        INDEX       { docsIf3CmtsCmRegStatusId }
        ::= { hwCmtsCmTrafficTable 1 }

    HwCmtsCmTrafficEntry ::=
        SEQUENCE {
            hwCmtsCmTrafficUpStreamCir               Unsigned32,   
            hwCmtsCmTrafficUpStreamCbs               Unsigned32,
            hwCmtsCmTrafficUpStreamPir               Unsigned32,
            hwCmtsCmTrafficUpStreamPbs               Unsigned32,
            hwCmtsCmTrafficDownStreamCir             Unsigned32,
            hwCmtsCmTrafficDownStreamCbs             Unsigned32,
            hwCmtsCmTrafficDownStreamPir             Unsigned32,
            hwCmtsCmTrafficDownStreamPbs             Unsigned32,
            hwCmtsCmTrafficUpStream                  Unsigned32,
            hwCmtsCmTrafficDownStream                Unsigned32,
            hwCmtsCmTrafficUpStreamMax               Unsigned32,
            hwCmtsCmTrafficDownStreamMax             Unsigned32
        }

    hwCmtsCmTrafficUpStreamCir  OBJECT-TYPE
        SYNTAX     Unsigned32
        UNITS      "kbps"
        MAX-ACCESS read-only
        STATUS     current
        DESCRIPTION
            "This object indicats the cm traffic of upstream CIR.
             When the value is default value, it indicates that the leaf is not configured.
             Default: 4294967295
            "
        ::= { hwCmtsCmTrafficEntry 1 }

    hwCmtsCmTrafficUpStreamCbs  OBJECT-TYPE
        SYNTAX     Unsigned32
        UNITS      "Bytes"
        MAX-ACCESS read-only
        STATUS     current
        DESCRIPTION
            "This object indicats the cm traffic of upstream CBS.
             When the value is default value, it indicates that the leaf is not configured.
             Default: 4294967295
            "
        ::= { hwCmtsCmTrafficEntry 2 }

    hwCmtsCmTrafficUpStreamPir  OBJECT-TYPE
        SYNTAX     Unsigned32
        UNITS      "kbps"
        MAX-ACCESS read-only
        STATUS     current
        DESCRIPTION
            "This object indicats the cm traffic of upstream PIR.
             When the value is default value, it indicates that the leaf is not configured.
             Default: 4294967295
            "
        ::= { hwCmtsCmTrafficEntry 3 }

    hwCmtsCmTrafficUpStreamPbs  OBJECT-TYPE
        SYNTAX     Unsigned32
        UNITS      "Bytes"
        MAX-ACCESS read-only
        STATUS     current
        DESCRIPTION
            "This object indicats the max cm traffic of upstream PBS.
             When the value is default value, it indicates that the leaf is not configured.
             Default: 4294967295
            "
        ::= { hwCmtsCmTrafficEntry 4 }
        
    hwCmtsCmTrafficDownStreamCir  OBJECT-TYPE
        SYNTAX     Unsigned32
        UNITS      "kbps"
        MAX-ACCESS read-only
        STATUS     current
        DESCRIPTION
            "This object indicats the cm traffic of downstream CIR.
             When the value is default value, it indicates that the leaf is not configured.
             Default: 4294967295
            "
        ::= { hwCmtsCmTrafficEntry 5 }

    hwCmtsCmTrafficDownStreamCbs  OBJECT-TYPE
        SYNTAX     Unsigned32
        UNITS      "Bytes"
        MAX-ACCESS read-only
        STATUS     current
        DESCRIPTION
            "This object indicats the cm traffic of downstream CBS.
             When the value is default value, it indicates that the leaf is not configured.
             Default: 4294967295
            "
        ::= { hwCmtsCmTrafficEntry 6 }

    hwCmtsCmTrafficDownStreamPir  OBJECT-TYPE
        SYNTAX     Unsigned32
        UNITS      "kbps"
        MAX-ACCESS read-only
        STATUS     current
        DESCRIPTION
            "This object indicats the cm traffic of downstream PIR.
             When the value is default value, it indicates that the leaf is not configured.
             Default: 4294967295
            "
        ::= { hwCmtsCmTrafficEntry 7 }

    hwCmtsCmTrafficDownStreamPbs  OBJECT-TYPE
        SYNTAX     Unsigned32
        UNITS      "Bytes"
        MAX-ACCESS read-only
        STATUS     current
        DESCRIPTION
            "This object indicats the cm traffic of downstream PBS.
             When the value is default value, it indicates that the leaf is not configured.
             Default: 4294967295
            "
        ::= { hwCmtsCmTrafficEntry 8 }
        
     hwCmtsCmTrafficUpStream  OBJECT-TYPE
        SYNTAX     Unsigned32
        UNITS      "bps"
        MAX-ACCESS read-only
        STATUS     current
        DESCRIPTION
            "This object indicats the cm traffic of upstream.
            "
        ::= { hwCmtsCmTrafficEntry 9 }

    hwCmtsCmTrafficDownStream  OBJECT-TYPE
        SYNTAX     Unsigned32
        UNITS      "bps"
        MAX-ACCESS read-only
        STATUS     current
        DESCRIPTION
            "This object indicats the cm traffic of downstream.
            "
        ::= { hwCmtsCmTrafficEntry 10 }

    hwCmtsCmTrafficUpStreamMax  OBJECT-TYPE
        SYNTAX     Unsigned32
        UNITS      "bps"
        MAX-ACCESS read-only
        STATUS     current
        DESCRIPTION
            "This object indicats the max cm traffic of upstream.
             When the value is default value, it indicates that the leaf is not configured.
             Default: 4294967295
            "
        ::= { hwCmtsCmTrafficEntry 11 }

    hwCmtsCmTrafficDownStreamMax  OBJECT-TYPE
        SYNTAX     Unsigned32
        UNITS      "bps"
        MAX-ACCESS read-only
        STATUS     current
        DESCRIPTION
            "This object indicats the max cm traffic of downstream.
             When the value is default value, it indicates that the leaf is not configured.
             Default: 4294967295
            "
        ::= { hwCmtsCmTrafficEntry 12 }

    --Table hwCmtsCmTrafficTable end

    hwCmtsServiceDomainConfigObject OBJECT IDENTIFIER ::= { hwCmtsServiceObject 5 }

    --Table hwCmtsServiceDomainTable begin
    hwCmtsServiceDomainTable OBJECT-TYPE
        SYNTAX SEQUENCE OF HwCmtsServiceDomainEntry
        MAX-ACCESS not-accessible
        STATUS current
        DESCRIPTION
            "
            Indicates the configuration of the cable service domain.
            The index of this table is hwCmtsServiceDomainName.
            "
        ::= { hwCmtsServiceDomainConfigObject 1 }
    
    hwCmtsServiceDomainEntry OBJECT-TYPE
        SYNTAX HwCmtsServiceDomainEntry
        MAX-ACCESS not-accessible
        STATUS current
        DESCRIPTION
            "
            Indicates the configuration of the cable service domain.
            The index of this entry is hwCmtsServiceDomainName.
            "
        INDEX { hwCmtsServiceDomainName }
        ::= { hwCmtsServiceDomainTable 1 }
    
    HwCmtsServiceDomainEntry ::=
        SEQUENCE { 
            hwCmtsServiceDomainName
                OCTET STRING,
            hwCmtsServiceDomainDefault
                TruthValue,
            hwCmtsServiceDomainRowStatus
                RowStatus
         }

    hwCmtsServiceDomainName OBJECT-TYPE
        SYNTAX OCTET STRING (SIZE (1..15))
        MAX-ACCESS not-accessible
        STATUS current
        DESCRIPTION
            "
            Indicates the name of the cable service domain.
            The main input rules of the string are as follows:
            1. The ASCII value of characters must be between 0x20 and 0x7E.
            2. The special character '?' is not supported.
            "
        ::= { hwCmtsServiceDomainEntry 1 }
    
    hwCmtsServiceDomainDefault OBJECT-TYPE
        SYNTAX TruthValue
        MAX-ACCESS read-create
        STATUS current
        DESCRIPTION
            "
            Indicates if the cable service domain is default.
            Options:
            1. true(1)  -default
            2. false(2) -not default
            Default: false(2)
            "
        ::= { hwCmtsServiceDomainEntry 2 }
    
    hwCmtsServiceDomainRowStatus OBJECT-TYPE
        SYNTAX RowStatus
        MAX-ACCESS read-create
        STATUS current
        DESCRIPTION
            "Indicates the row status to create or delete a cable service domain."
        ::= { hwCmtsServiceDomainEntry 3 }
    
    --Table hwCmtsServiceDomainTable end
    
    --Table hwCmtsServiceDomainMappingTable begin
    hwCmtsServiceDomainMappingTable OBJECT-TYPE
        SYNTAX SEQUENCE OF HwCmtsServiceDomainMappingEntry
        MAX-ACCESS not-accessible
        STATUS current
        DESCRIPTION
            "
            Indicates the configuration of the cable service domain mapping.
            The indexes of this table are hwCmtsServiceDomainName and hwCmtsServiceDomainMappingID.
            "
        ::= { hwCmtsServiceDomainConfigObject 2 }
    
    hwCmtsServiceDomainMappingEntry OBJECT-TYPE
        SYNTAX HwCmtsServiceDomainMappingEntry
        MAX-ACCESS not-accessible
        STATUS current
        DESCRIPTION
            "
            Indicates the configuration of the cable service domain mapping.
            The indexes of this entry are hwCmtsServiceDomainName and hwCmtsServiceDomainMappingID.
            "
        INDEX { hwCmtsServiceDomainName, hwCmtsServiceDomainMappingID }
        ::= { hwCmtsServiceDomainMappingTable 1 }
    
    HwCmtsServiceDomainMappingEntry ::=
        SEQUENCE { 
            hwCmtsServiceDomainMappingID
                Unsigned32,
            hwCmtsServiceDomainMappingPriority
                Unsigned32,
            hwCmtsServiceDomainMappingOuterVlan
                Unsigned32,
            hwCmtsServiceDomainMappingTagtransform
                INTEGER,
            hwCmtsServiceDomainMappingOuterVlanPriority
                INTEGER,
            hwCmtsServiceDomainMappingMatchType
                INTEGER,
            hwCmtsServiceDomainMappingSIpAddressType
                InetAddressType,
            hwCmtsServiceDomainMappingSIpAddress
                InetAddress,
            hwCmtsServiceDomainMappingSIpAddressPrefixLen
                InetAddressPrefixLength,
            hwCmtsServiceDomainMappingUserVlanType
                INTEGER,
            hwCmtsServiceDomainMappingUserVlan
                Unsigned32,
            hwCmtsServiceDomainMappingVlan8021p
                Unsigned32,
            hwCmtsServiceDomainMappingUserEncap
                INTEGER,
            hwCmtsServiceDomainMappingDhcpOption60MatchType
                INTEGER,
            hwCmtsServiceDomainMappingDhcpOption60
                OCTET STRING,
            hwCmtsServiceDomainMappingOuterVlanMode
                INTEGER,
            hwCmtsServiceDomainMappingVpnID
                DocsL2vpnIdentifier,
            hwCmtsServiceDomainMappingRowStatus
                RowStatus
         }

    hwCmtsServiceDomainMappingID OBJECT-TYPE
        SYNTAX Unsigned32
        MAX-ACCESS not-accessible
        STATUS current
        DESCRIPTION
            "
            Indicates the mapping ID in the cable service domain.
            4294967295 indicates that an index will be allocated automatically for the mapping.
            Range: 1..32 | 4294967295
            "
        ::= { hwCmtsServiceDomainMappingEntry 1 }
    
    hwCmtsServiceDomainMappingPriority OBJECT-TYPE
        SYNTAX Unsigned32 (0..255)
        MAX-ACCESS read-create
        STATUS current
        DESCRIPTION
            "
            Indicates the priority of the mapping.
            Default value:128
            "
        ::= { hwCmtsServiceDomainMappingEntry 2 }
    
    hwCmtsServiceDomainMappingOuterVlan OBJECT-TYPE
        SYNTAX Unsigned32 (0..4093)
        MAX-ACCESS read-create
        STATUS current
        DESCRIPTION
            "
            Indicates the outer VLAN of the mapping.
            0 indicates an invalid value.
            "
        ::= { hwCmtsServiceDomainMappingEntry 3 }
    
    hwCmtsServiceDomainMappingTagtransform OBJECT-TYPE
        SYNTAX INTEGER
            {
            add(1),
            translate(2),
            invalid(255)
            }
        MAX-ACCESS read-create
        STATUS current
        DESCRIPTION
            "
            Indicates the tag transform of the mapping.
            Options:
            1. add(1)          -indicates that a VLAN tag is added to the traffic in the upstream direction
            2. translate(2)    -indicates retaining the VLAN tag of the traffic in the upstream direction
            3. invalid(255)    -invalid value
            "
        ::= { hwCmtsServiceDomainMappingEntry 4 }
    
    hwCmtsServiceDomainMappingOuterVlanPriority OBJECT-TYPE
        SYNTAX INTEGER
            {
            default(1),
            usercos(2),
            invalid(255)
            }
        MAX-ACCESS read-create
        STATUS current
        DESCRIPTION
            "
            Indicates the policy of priority remarking.
            Options:
            1. default(1)      -indicates the default value. The user priority is used
            2. usercos(2)      -indicates that the user CoS priority is copied
            3. invalid(255)    -invalid value
            "
        ::= { hwCmtsServiceDomainMappingEntry 5 }
    
    hwCmtsServiceDomainMappingMatchType OBJECT-TYPE
        SYNTAX INTEGER
            {
            srcIpPrefix(1),
            userVlan(2),
            user8021pVlan(3),
            userEncap(4),
            dhcpOption60(5),
            any(6),
            invalid(255)
            }
        MAX-ACCESS read-create
        STATUS current
        DESCRIPTION
            "
            Indicates the match type of the mapping.
            Options:
            1. srcIpPrefix(1)     -indicates prefix matching of source IP address
            2. userVlan(2)        -indicates user vlan matching
            3. user8021pVlan(3)   -indicates user 802.1p matching
            4. userEncap(4)       -indicates user encapsulation type matching
            5. dhcpOption60(5)    -indicates DHCP option60 matching
            6. any(6)             -indicates that the system matches any packets
            7. invalid(255)       -invalid value
            "
        ::= { hwCmtsServiceDomainMappingEntry 6 }
    
    hwCmtsServiceDomainMappingSIpAddressType OBJECT-TYPE
        SYNTAX InetAddressType
        MAX-ACCESS read-create
        STATUS current
        DESCRIPTION
            "
            Indicates the IP address type of the mapping.
            Options:
            1. unknown(0)   -invalid value
            2. ipv4(1)      -indicates that the IP address type is ipv4
            3. ipv6(2)      -indicates that the IP address type is ipv6
            "
        ::= { hwCmtsServiceDomainMappingEntry 7 }
    
    hwCmtsServiceDomainMappingSIpAddress OBJECT-TYPE
        SYNTAX InetAddress
        MAX-ACCESS read-create
        STATUS current
        DESCRIPTION
            "
            Indicates the IP address of the mapping rule.
            00.00.00.00(hex) indicates an invalid value.
            "
        ::= { hwCmtsServiceDomainMappingEntry 8 }
    
    hwCmtsServiceDomainMappingSIpAddressPrefixLen OBJECT-TYPE
        SYNTAX InetAddressPrefixLength
        MAX-ACCESS read-create
        STATUS current
        DESCRIPTION
            "
            Indicates the IP address's prefix length in the mapping rule.
            4294967295 indicates an invalid value.
            "
        ::= { hwCmtsServiceDomainMappingEntry 9 }
    
    hwCmtsServiceDomainMappingUserVlanType OBJECT-TYPE
        SYNTAX INTEGER
            {
            untag(1),
            userVlan(2),
            invalid(255)
            }
        MAX-ACCESS read-create
        STATUS current
        DESCRIPTION
            "
            Indicates the user VLAN type.
            Options:
            1. untag(1)     -untagged
            2. userVlan(2)  -the user-side VLAN
            3. invalid(255) -invalid value
            "
        ::= { hwCmtsServiceDomainMappingEntry 10 }
    
    hwCmtsServiceDomainMappingUserVlan OBJECT-TYPE
        SYNTAX Unsigned32 (0..4095)
        MAX-ACCESS read-create
        STATUS current
        DESCRIPTION
            "
            Indicates the user VLAN ID.
            0 indicates an invalid value.
            "
        ::= { hwCmtsServiceDomainMappingEntry 11 }
    
    hwCmtsServiceDomainMappingVlan8021p OBJECT-TYPE
        SYNTAX Unsigned32 (0..7|255)
        MAX-ACCESS read-create
        STATUS current
        DESCRIPTION
            "
            Indicates the value of user 802.1p.
            255 indicates an invalid value.
            "
        ::= { hwCmtsServiceDomainMappingEntry 12 }
    
    hwCmtsServiceDomainMappingUserEncap OBJECT-TYPE
        SYNTAX INTEGER
            {
            pppoe(1),
            invalid(255)
            }
        MAX-ACCESS read-create
        STATUS current
        DESCRIPTION
            "
            Indicates the user encapsulation type.
            Options:
            1. pppoe(1)       -indicates the PPPoE encapsulation type
            2. invalid(255)   -invalid value
            "
        ::= { hwCmtsServiceDomainMappingEntry 13 }
    
    hwCmtsServiceDomainMappingDhcpOption60MatchType OBJECT-TYPE
        SYNTAX INTEGER
            {
            any(1),
            value(2),
            invalid(255)
            }
        MAX-ACCESS read-create
        STATUS current
        DESCRIPTION
            "
            Indicates the DHCP option60 type.
            Options:
            1. any(1)       -indicates any DHCP option60
            2. value(2)     -indicates value of DHCP option60
            3. invalid(255) -invalid value
            "
        ::= { hwCmtsServiceDomainMappingEntry 14 }
    
    hwCmtsServiceDomainMappingDhcpOption60 OBJECT-TYPE
        SYNTAX OCTET STRING (SIZE (0..15))
        MAX-ACCESS read-create
        STATUS current
        DESCRIPTION
            "
            Indicates the string value of DHCP option60.
            "
        ::= { hwCmtsServiceDomainMappingEntry 15 }

  hwCmtsServiceDomainMappingOuterVlanMode OBJECT-TYPE
        SYNTAX INTEGER
            {
            static(1),
            autosense(2)
            }
        MAX-ACCESS read-create
        STATUS current
        DESCRIPTION
            "
            Indicates the outer VLAN mode of the mapping.
            Options:
            1. static(1)        -indicates VLAN is static
            2. autosense(2)     -indicates VLAN is autosense by config file on CM.
            Default: static(1)
            "
        ::= { hwCmtsServiceDomainMappingEntry 16 }

  hwCmtsServiceDomainMappingVpnID OBJECT-TYPE
        SYNTAX DocsL2vpnIdentifier
        MAX-ACCESS read-create
        STATUS current
        DESCRIPTION
            "
            Indicates the VPN ID.
            00(hex) indicates an invalid value when the outer VLAN mode is static.
            "
        ::= { hwCmtsServiceDomainMappingEntry 17 }

  hwCmtsServiceDomainMappingRowStatus OBJECT-TYPE
        SYNTAX RowStatus
        MAX-ACCESS read-create
        STATUS current
        DESCRIPTION
            "Indicates the row status to create or delete a cable service domain mapping."
        ::= { hwCmtsServiceDomainMappingEntry 255 }
 
    --Table hwCmtsServiceDomainMappingTable end
    
    --Table hwCmtsServiceDomainMemberTable begin
    hwCmtsServiceDomainMemberTable OBJECT-TYPE
        SYNTAX SEQUENCE OF HwCmtsServiceDomainMemberEntry
        MAX-ACCESS not-accessible
        STATUS current
        DESCRIPTION
            "
            Indicates the configuration of the cable service domain member.
            The indexes of this table are hwCmtsServiceDomainName and hwCmtsServiceDomainMemberID.
            "
        ::= { hwCmtsServiceDomainConfigObject 3 }
    
    hwCmtsServiceDomainMemberEntry OBJECT-TYPE
        SYNTAX HwCmtsServiceDomainMemberEntry
        MAX-ACCESS not-accessible
        STATUS current
        DESCRIPTION
            "
            Indicates the configuration of the cable service domain member.
            The indexes of this entry are hwCmtsServiceDomainName and hwCmtsServiceDomainMemberID.
            "
        INDEX { hwCmtsServiceDomainName, hwCmtsServiceDomainMemberID }
        ::= { hwCmtsServiceDomainMemberTable 1 }
    
    HwCmtsServiceDomainMemberEntry ::=
        SEQUENCE { 
            hwCmtsServiceDomainMemberID
                Unsigned32,
            hwCmtsServiceDomainMemberType
                INTEGER,
            hwCmtsServiceDomainMemberAddressType
                InetAddressType,
            hwCmtsServiceDomainMemberAddress
                InetAddress,
            hwCmtsServiceDomainMemberAddressPrefixLen
                InetAddressPrefixLength,
            hwCmtsServiceDomainMemberFrameID
                Unsigned32,
            hwCmtsServiceDomainMemberSlotID
                Unsigned32,
            hwCmtsServiceDomainMemberIfindex
                Unsigned32,
            hwCmtsServiceDomainMemberRowStatus
                RowStatus
         }

    hwCmtsServiceDomainMemberID OBJECT-TYPE
        SYNTAX Unsigned32
        MAX-ACCESS not-accessible
        STATUS current
        DESCRIPTION
            "
            Indicates the member ID in the cable service domain.
            4294967295 indicates that an index will be allocated automatically for the member.
            Range: 1..64 | 4294967295
            "
        ::= { hwCmtsServiceDomainMemberEntry 1 }
    
    hwCmtsServiceDomainMemberType OBJECT-TYPE
        SYNTAX INTEGER
            {
            cmIpPrefix(1),
            port(2),
            board(3),
            invalid(255)
            }
        MAX-ACCESS read-create
        STATUS current
        DESCRIPTION
            "
            Indicates the member type.
            Options:
            1. cmIpPrefix(1)      -CM IP address prefix
            2. port(2)            -indicates the member type is port
            3. board(3)           -indicates the member type is board
            4. invalid(255)       -invalid value
            "
        ::= { hwCmtsServiceDomainMemberEntry 2 }
    
    hwCmtsServiceDomainMemberAddressType OBJECT-TYPE
        SYNTAX InetAddressType
        MAX-ACCESS read-create
        STATUS current
        DESCRIPTION
            "
            Indicates the IP address type of the member.
            Options:
            1. unknown(0)   -invalid value            
            2. ipv4(1)      -indicates that the IP address type is ipv4
            3. ipv6(2)      -indicates that the IP address type is ipv6
            "
        ::= { hwCmtsServiceDomainMemberEntry 3 }
    
    hwCmtsServiceDomainMemberAddress OBJECT-TYPE
        SYNTAX InetAddress
        MAX-ACCESS read-create
        STATUS current
        DESCRIPTION
            "
            Indicates the IP address of the member.
            00.00.00.00(hex) indicates an invalid value.
            "
        ::= { hwCmtsServiceDomainMemberEntry 4 }
    
    hwCmtsServiceDomainMemberAddressPrefixLen OBJECT-TYPE
        SYNTAX InetAddressPrefixLength
        MAX-ACCESS read-create
        STATUS current
        DESCRIPTION
            "
            Indicates the IP address's prefix length in the member configuration.
            4294967295 indicates an invalid value.
            "
        ::= { hwCmtsServiceDomainMemberEntry 5 }

    hwCmtsServiceDomainMemberFrameID OBJECT-TYPE
        SYNTAX Unsigned32
        MAX-ACCESS read-create
        STATUS current
        DESCRIPTION
            "
            Indicates the frame ID of a board member.
            4294967295 indicates an invalid value.
            "
        ::= { hwCmtsServiceDomainMemberEntry 6 }
    
    hwCmtsServiceDomainMemberSlotID OBJECT-TYPE
        SYNTAX Unsigned32
        MAX-ACCESS read-create
        STATUS current
        DESCRIPTION
            "
            Indicates the slot ID of a board member.
            4294967295 indicates an invalid value.
            "
        ::= { hwCmtsServiceDomainMemberEntry 7 }
    
    hwCmtsServiceDomainMemberIfindex OBJECT-TYPE
        SYNTAX Unsigned32
        MAX-ACCESS read-create
        STATUS current
        DESCRIPTION
            "
            Indicates the index of a port member.
            4294967295 indicates an invalid value.
            "
        ::= { hwCmtsServiceDomainMemberEntry 8 }
    
    hwCmtsServiceDomainMemberRowStatus OBJECT-TYPE
        SYNTAX RowStatus
        MAX-ACCESS read-create
        STATUS current
        DESCRIPTION
            "Indicates the row status to create or delete a cable service domain member."
            ::= { hwCmtsServiceDomainMemberEntry 255 }
    
    --Table hwCmtsServiceDomainMemberTable end 
    
    --Table hwCmtsCmServiceDomainMappingTable begin
    hwCmtsCmServiceDomainMappingTable OBJECT-TYPE
        SYNTAX SEQUENCE OF HwCmtsCmServiceDomainMappingEntry
        MAX-ACCESS not-accessible
        STATUS current
        DESCRIPTION
            "
            Indicates the cable service domain mapping rules taking effect for the CM.
            The index of this table is docsIfCmtsCmStatusIndex.
            "
        ::= { hwCmtsServiceDomainConfigObject 4 }
    
    hwCmtsCmServiceDomainMappingEntry OBJECT-TYPE
        SYNTAX HwCmtsCmServiceDomainMappingEntry
        MAX-ACCESS not-accessible
        STATUS current
        DESCRIPTION
            "
            Indicates the cable service domain mapping rules taking effect for the CM.
            The index of this entry is docsIfCmtsCmStatusIndex.
            "
        INDEX { docsIfCmtsCmStatusIndex }
        ::= { hwCmtsCmServiceDomainMappingTable 1 }
    
    HwCmtsCmServiceDomainMappingEntry ::=
        SEQUENCE { 
            hwCmtsCmServiceDomainName
                OCTET STRING,
            hwCmtsCmServiceDomainRunningMappingID
                OCTET STRING,
            hwCmtsCmServiceDomainRunningVlanInfo
                OCTET STRING
         }

    hwCmtsCmServiceDomainName OBJECT-TYPE
        SYNTAX OCTET STRING (SIZE (0..15))
        MAX-ACCESS read-only
        STATUS current
        DESCRIPTION
            "
            Indicates the name of the cable service domain for the CM.
            The main input rules of the string are as follows:
            1. The ASCII value of characters must be between 0x20 and 0x7E.
            2. The special character '?' is not supported.
            "
        ::= { hwCmtsCmServiceDomainMappingEntry 1 }
    
    hwCmtsCmServiceDomainRunningMappingID OBJECT-TYPE
        SYNTAX OCTET STRING  (SIZE (0..256))
        MAX-ACCESS read-only
        STATUS current
        DESCRIPTION
            "
            Indicates the ID of the mapping rule taking effect for the CM.
            Format: 1.3.4.31
            Each number represents a mapping ID.
            "
        ::= { hwCmtsCmServiceDomainMappingEntry 2 }
    
    hwCmtsCmServiceDomainRunningVlanInfo OBJECT-TYPE
        SYNTAX OCTET STRING   (SIZE (0..1024))
        MAX-ACCESS read-only
        STATUS current
        DESCRIPTION
            "
            Indicates the vlan information of the mapping rule taking effect for the CM.
            The information includes the tag transform mode, inner vlan, and outer vlan. 
            Format: 1.100.0.4.300.400  
            Each three numbers correspond to a mapping rule. 
            First number: indicates the tag translation mode. 1 indicates add, 2 indicates translate, 3 indicates tranlsate-and-add, 4 indicates add-double, and 255 indicates invalid.
            Second number: indicates the service outer vlan ID. 0 indicates an invalid ID. The range is from 1 to 4093. 
            Third number: indicates the service inner vlan ID. 0 indicates an invalid ID. The range is from 1 to 4095.
            "
        ::= { hwCmtsCmServiceDomainMappingEntry 3 }   
     
    --Table hwCmtsCmServiceDomainMappingTable end    

    hwCmtsUpstreamExtTable OBJECT-TYPE
        SYNTAX SEQUENCE OF HwCmtsUpstreamExtEntry
        MAX-ACCESS not-accessible
        STATUS current
        DESCRIPTION
            "Indicates the extended information associated with upstream service flows.
             The indexes of this table are ifIndex and docsQosSID.
            "
        ::= { hwCmtsServiceObject 6 }

    hwCmtsUpstreamExtEntry OBJECT-TYPE
        SYNTAX HwCmtsUpstreamExtEntry
        MAX-ACCESS not-accessible
        STATUS current
        DESCRIPTION
            "Indicates the extended information associated with upstream service flows.
             The indexes of this entry are ifIndex and docsQosSID.
            "        
        INDEX { ifIndex, docsQosSID }
        ::= { hwCmtsUpstreamExtTable  1 }

    HwCmtsUpstreamExtEntry ::= SEQUENCE {
        hwCmtsUpstreamExtMacAddress         MacAddress,
        hwCmtsUpstreamExtSIDHCSErrors       Counter64,
        hwCmtsUpstreamExtSIDCRCErrors       Counter64
        }

    hwCmtsUpstreamExtMacAddress OBJECT-TYPE
        SYNTAX MacAddress
        MAX-ACCESS read-only
        STATUS current
        DESCRIPTION 
            "The MAC address of the CM associated with the service flow."
        ::= { hwCmtsUpstreamExtEntry 1 }
        
    hwCmtsUpstreamExtSIDHCSErrors OBJECT-TYPE
        SYNTAX  Counter64
        MAX-ACCESS      read-only
        STATUS  current
        DESCRIPTION 
            "The number of MAC HCS errors on this service flow."
        ::= { hwCmtsUpstreamExtEntry 2 }

    hwCmtsUpstreamExtSIDCRCErrors OBJECT-TYPE
        SYNTAX  Counter64
        MAX-ACCESS      read-only
        STATUS  current
        DESCRIPTION 
            "The number of MAC CRC errors on this service flow."
        ::= { hwCmtsUpstreamExtEntry 3 }
  
    --Table hwCmtsServiceVlanTable begin
        
    hwCmtsServiceVlanTable OBJECT-TYPE
        SYNTAX     SEQUENCE OF HwCmtsServiceVlanEntry
        MAX-ACCESS not-accessible
        STATUS     current
        DESCRIPTION
            "
            Indicates the service VLAN information of the CM.
            The index of this table is hwCmtsServiceVlanMacAddr.
            "
        ::= { hwCmtsServiceObject 7  }

    hwCmtsServiceVlanEntry OBJECT-TYPE
        SYNTAX     HwCmtsServiceVlanEntry
        MAX-ACCESS not-accessible
        STATUS     current
        DESCRIPTION
            "
            Indicates the service VLAN information of the CM.
            The index of this entry is hwCmtsServiceVlanMacAddr.
            "
        INDEX       { hwCmtsServiceVlanMacAddr }
        ::= { hwCmtsServiceVlanTable 1 }

    HwCmtsServiceVlanEntry ::=
        SEQUENCE {
                 hwCmtsServiceVlanMacAddr        MacAddress,
                 hwCmtsServiceVlan               OCTET STRING   
        }
        
    hwCmtsServiceVlanMacAddr OBJECT-TYPE
            SYNTAX MacAddress
            MAX-ACCESS not-accessible
            STATUS current
            DESCRIPTION
                "Indicates the MAC address of the CM.           
                "
         ::= { hwCmtsServiceVlanEntry 1 }
   
    hwCmtsServiceVlan OBJECT-TYPE
            SYNTAX OCTET STRING (SIZE (0..1024))    
            MAX-ACCESS read-only
            STATUS current
            DESCRIPTION
                "Indicates the service VLAN information of the CM.
        The strings are as follows, 0.100.200: 
        '0' indicates the type of the service-port is not l2vpn.
        '100' indicates the outer service VLAN of the service-port,
        '200' indicates the inner service VLAN of the service-port(65535 means invalid).        
                "
         ::= { hwCmtsServiceVlanEntry 2 }
        
    hwL2vpnCmMplsNsiTable OBJECT-TYPE
        SYNTAX SEQUENCE OF HwL2vpnCmMplsNsiEntry
        MAX-ACCESS not-accessible
        STATUS current
        DESCRIPTION
            "Indicates the L2VPN configurations with MPLS encapsulation for CMs.
             The indexes of this table are docsL2vpnIdx and docsIfCmtsCmStatusIndex.
            "
        ::= { hwCmtsServiceObject 8 }

    hwL2vpnCmMplsNsiEntry OBJECT-TYPE
        SYNTAX HwL2vpnCmMplsNsiEntry
        MAX-ACCESS not-accessible
        STATUS current
        DESCRIPTION
            "Indicates the L2VPN configurations with MPLS encapsulation for CMs.
             The indexes of this entry are docsL2vpnIdx and docsIfCmtsCmStatusIndex.
            "        
        INDEX { docsL2vpnIdx, docsIfCmtsCmStatusIndex }
        ::= { hwL2vpnCmMplsNsiTable  1 }

    HwL2vpnCmMplsNsiEntry ::= 
        SEQUENCE {
            hwL2vpnCmMplsNsiEncapPWID                    Unsigned32,
            hwL2vpnCmMplsNsiEncapPeerIPAddressType       InetAddressType,
            hwL2vpnCmMplsNsiEncapPeerIPAddress           InetAddress,
            hwL2vpnCmMplsNsiEncapPWType                  INTEGER,
            hwL2vpnCmMplsNsiEncapBackupPWID              Unsigned32,
            hwL2vpnCmMplsNsiEncapBackupPeerIPAddressType InetAddressType,
            hwL2vpnCmMplsNsiEncapBackupPeerIPAddress     InetAddress
        }

    hwL2vpnCmMplsNsiEncapPWID OBJECT-TYPE
        SYNTAX Unsigned32 (0..4294967295)
        MAX-ACCESS read-only
        STATUS current
        DESCRIPTION 
            "Indicates the primary MPLS PW identifier.
             0 indicates an invalid value.
            "
        ::= { hwL2vpnCmMplsNsiEntry 1 }
        
    hwL2vpnCmMplsNsiEncapPeerIPAddressType OBJECT-TYPE
        SYNTAX  InetAddressType
        MAX-ACCESS      read-only
        STATUS  current
        DESCRIPTION 
            "Indicates the MPLS peer IP address type of the primary MPLS PW."
        ::= { hwL2vpnCmMplsNsiEntry 2 }

    hwL2vpnCmMplsNsiEncapPeerIPAddress OBJECT-TYPE
        SYNTAX  InetAddress
        MAX-ACCESS      read-only
        STATUS  current
        DESCRIPTION 
            "Indicates the PW Peer IP address of the primary MPLS PW."
        ::= { hwL2vpnCmMplsNsiEntry 3 }
  
    hwL2vpnCmMplsNsiEncapPWType OBJECT-TYPE
        SYNTAX  INTEGER
            {
                ethernetTaggedMode(4),
                ethernetRawMode(5),
                vpls(19)
            }
        MAX-ACCESS      read-only
        STATUS  current
        DESCRIPTION 
            "Indicates the pseudowire type.
             Options:
             1. ethernetTaggedMode(4)   -indicates the pseudowire type is ethernet tagged mode.
             2. ethernetRawMode(5)      -indicates the pseudowire type is ethernet raw mode.
             3. vpls(19)                -indicates the pseudowire type is VPLS.
            "

        ::= { hwL2vpnCmMplsNsiEntry 4 }
      
    hwL2vpnCmMplsNsiEncapBackupPWID OBJECT-TYPE
        SYNTAX Unsigned32 (0..4294967295)
        MAX-ACCESS read-only
        STATUS current
        DESCRIPTION 
            "Indicates the backup MPLS PW identifier.
             0 indicates an invalid value.
            "
        ::= { hwL2vpnCmMplsNsiEntry 5 }
        
    hwL2vpnCmMplsNsiEncapBackupPeerIPAddressType OBJECT-TYPE
        SYNTAX  InetAddressType
        MAX-ACCESS      read-only
        STATUS  current
        DESCRIPTION 
            "Indicates the MPLS peer IP address type of the backup MPLS PW."
        ::= { hwL2vpnCmMplsNsiEntry 6 }

    hwL2vpnCmMplsNsiEncapBackupPeerIPAddress OBJECT-TYPE
        SYNTAX  InetAddress
        MAX-ACCESS      read-only
        STATUS  current
        DESCRIPTION 
            "Indicates the PW Peer IP address of the backup MPLS PW."
        ::= { hwL2vpnCmMplsNsiEntry 7 }                        

    hwCmtsL2vpnFloodingModeConfigObject OBJECT IDENTIFIER ::= { hwCmtsServiceObject  9}

    hwCmtsL2vpnDot1qFloodingMode OBJECT-TYPE
        SYNTAX  INTEGER
            {
            unicast(1),
            broadcast(2)
            }
        MAX-ACCESS read-write
        STATUS     current
        DESCRIPTION
             "Indicates the flooding mode of 802.1Q L2VPN.
              Options:
              1. unicast(1)     -Sends VPN broadcast packets (including unknown broadcast and unknown unicast packets) to CMs in unicast mode.
              2. broadcast(2)   -Sends VPN broadcast packets (including unknown broadcast and unknown unicast packets) to CMs in broadcast mode.
              Default: unicast(1)           
             "
        ::= { hwCmtsL2vpnFloodingModeConfigObject 1 }


    hwIpReturnConnectObject OBJECT IDENTIFIER ::= { hwCmtsServiceObject 10 }


    --Table hwCmtsBundleReservedVlanList begin
    
    hwCmtsBundleReservedVlanList OBJECT-TYPE
           SYNTAX OCTET STRING (SIZE (512))  
           MAX-ACCESS read-write
           STATUS current
           DESCRIPTION
               "Indicates the vlan used by cable bundle.
                From left to right, 1 bit indicates a VLAN.
                Length: 512
               "
           ::= { hwCmtsObject 23 }

    --Table hwCmtsBundleReservedVlanList end
    
    --Table hwCmtsBundleTable begin
        
    hwCmtsBundleTable OBJECT-TYPE
        SYNTAX     SEQUENCE OF HwCmtsBundleEntry
        MAX-ACCESS not-accessible
        STATUS     current
        DESCRIPTION
            "
            Indicates the basic property cable bundle.
            The index of this table is hwCmtsBundleName.
            "
        ::= { hwCmtsObject 24 }
        
        
    hwCmtsBundleEntry OBJECT-TYPE
        SYNTAX     HwCmtsBundleEntry
        MAX-ACCESS not-accessible
        STATUS     current
        DESCRIPTION
           "
           Indicates the basic property cable bundle.
           The index of this entry is hwCmtsBundleName.
           "
       INDEX       { hwCmtsBundleName }
       ::= { hwCmtsBundleTable 1 }

   HwCmtsBundleEntry ::=
       SEQUENCE {
           hwCmtsBundleName
             OCTET STRING,
           hwCmtsBundleIfindex
             InterfaceIndexOrZero,
           hwCmtsBundleServiceProfile
             OCTET STRING,           
           hwCmtsBundleMemberList
             OCTET STRING, 
           hwCmtsBundleRowStatus
             RowStatus             
       }
       
   hwCmtsBundleName OBJECT-TYPE
       SYNTAX OCTET STRING (SIZE (1..32))
       MAX-ACCESS not-accessible 
       STATUS current
       DESCRIPTION
           "Indicates the name of the cable bundle.
            Range: a string of 1-32 characters
            The input index consists of the name of a cable bundle and
            the length of the name.
            The input name must be ASCII codes.
            Assume that you need to create a huawei cable bundle.
            Because the ASCII value of huawei is 104.117.97.119.101.105 and
            the length of huawei is 6, the index is 6.104.117.97.119.101.105.
           "
       ::= { hwCmtsBundleEntry 1 } 
       
    hwCmtsBundleIfindex OBJECT-TYPE                                               
       SYNTAX InterfaceIndexOrZero                                                        
       MAX-ACCESS read-create                                                  
       STATUS current                                                          
       DESCRIPTION                                                             
           "Indicates the index of a VLAN interface, which maps a VLAN ID.  
            The VLAN which the interface based on must be super VLAN.
            It indicates the interface is not configured, if the value is 0.
            Default: 0                                      
           "                                                                   
       ::= { hwCmtsBundleEntry 2 }            
       
    hwCmtsBundleServiceProfile OBJECT-TYPE                                                            
       SYNTAX OCTET STRING  (SIZE (0..32))                                          
       MAX-ACCESS read-create                                                             
       STATUS current                                                                        
       DESCRIPTION                                                                           
           "Describes the attributes of a VLAN service profile, used for refering  
            a VLAN service profile.
            Default: NULL ASCII string                                                                                              
           "                                                                                 
       ::= { hwCmtsBundleEntry 3 }
       
    hwCmtsBundleMemberList OBJECT-TYPE                                                            
       SYNTAX OCTET STRING  (SIZE (1024))                                            
       MAX-ACCESS read-create                                                             
       STATUS current                                                                        
       DESCRIPTION                                                                           
           "Describes the cable bundle member, used for adding or deleting a member of  
            a cable bundle. It uses 4 bytes to describe a member; the first 2 bytes of
            data indicates the frame, and the next 2 bytes of data is slot.                                                                                          
           "                                                                                 
       ::= { hwCmtsBundleEntry 4 }                                                          
                              
    hwCmtsBundleRowStatus OBJECT-TYPE
          SYNTAX RowStatus
          MAX-ACCESS read-create
          STATUS current
          DESCRIPTION
              "RowStatus.
               1. active(1)      -indicates the query operation.
               2. createAndGo(4) -indicates creating a CMTS bundle group.
               3. destroy(6)     -indicates deleting a CMTS bundle group. 
              "
       ::= { hwCmtsBundleEntry 5 }                                                                          
        
    --Table hwCmtsBundleTable end
    
    --Table hwCmtsBundleMemberTable begin
        
    hwCmtsBundleMemberTable OBJECT-TYPE
        SYNTAX     SEQUENCE OF HwCmtsBundleMemberEntry
        MAX-ACCESS not-accessible
        STATUS     current
        DESCRIPTION
            "
            Indicates the member of cable bundle.
            The index of this table is hwFrameIndex, hwSlotIndex and hwCmtsBundleName.
            "
        ::= { hwCmtsObject 25 }

    hwCmtsBundleMemberEntry OBJECT-TYPE
        SYNTAX     HwCmtsBundleMemberEntry
        MAX-ACCESS not-accessible
        STATUS     current
        DESCRIPTION
            "
            Indicates the member of cable bundle.
            The index of this entry is hwFrameIndex, hwSlotIndex and hwCmtsBundleName.
            "
        INDEX       { hwFrameIndex,
                      hwSlotIndex, 
                      hwCmtsBundleName }
        ::= { hwCmtsBundleMemberTable 1 }

    HwCmtsBundleMemberEntry ::=
        SEQUENCE {
                 hwCmtsBundleMemberRowStatus RowStatus
        }
        
    hwCmtsBundleMemberRowStatus OBJECT-TYPE
            SYNTAX RowStatus
            MAX-ACCESS read-create
            STATUS current
            DESCRIPTION
                "RowStatus.
                 1. active(1)      -indicates the query operation.
                 2. createAndGo(4) -indicates adding a member to cable bundle.
                 3. destroy(6)     -indicates deleting a member from cable bundle.
                 Default: active(1)
                "
         ::= { hwCmtsBundleMemberEntry 1 }
        
    --Table hwCmtsBundleMemberTable end
    
    --Table hwServiceFlowExtTable begin
        
    hwServiceFlowExtTable OBJECT-TYPE
        SYNTAX     SEQUENCE OF HwServiceFlowExtEntry
        MAX-ACCESS not-accessible
        STATUS     current
        DESCRIPTION
            "
            Indicates the extended information of the service flow.
            The indexes of this table are ifIndex and docsQosServiceFlowId.
            "
        ::= { hwCmtsObject 26 }

    hwServiceFlowExtEntry OBJECT-TYPE
        SYNTAX     HwServiceFlowExtEntry
        MAX-ACCESS not-accessible
        STATUS     current
        DESCRIPTION
            "
            Indicates the extended information of the service flow.
            The indexes of this entry are ifIndex and docsQosServiceFlowId.
            "
        INDEX       { ifIndex,
                      docsQosServiceFlowId }
        ::= { hwServiceFlowExtTable 1 }

    HwServiceFlowExtEntry ::=
        SEQUENCE {
                 hwServiceFlowExtThroughputPps Counter32,
                 hwServiceFlowExtThroughputBps Counter32,
                 hwServiceFlowExtGateId Counter32
        }
        
    hwServiceFlowExtThroughputPps OBJECT-TYPE
            SYNTAX Counter32
            UNITS "pps"
            MAX-ACCESS read-only
            STATUS current
            DESCRIPTION
                "Indicates the throughput of the service flow.             
                "
         ::= { hwServiceFlowExtEntry 1 }
   
    hwServiceFlowExtThroughputBps OBJECT-TYPE
            SYNTAX Counter32
            UNITS "bps"
            MAX-ACCESS read-only
            STATUS current
            DESCRIPTION
                "Indicates the throughput of the service flow.              
                "
         ::= { hwServiceFlowExtEntry 2 }
     
    hwServiceFlowExtGateId OBJECT-TYPE
            SYNTAX Counter32
            MAX-ACCESS read-only
            STATUS current
            DESCRIPTION
                "Indicates the identifier of the PacketCable gate for the service flow.
                 Default: 4294967295
                 The value 4294967295 indicates that the PacketCable gate is invalid.
                "
         ::= { hwServiceFlowExtEntry 3 }
     
    --Table hwServiceFlowExtTable end
    
    hwDocsIf31AccessObject OBJECT IDENTIFIER ::= { hwCmtsObject  27 }
    
    --Table hwDocsIf31CmtsUsOfdmaChanTable begin
        
    hwDocsIf31CmtsUsOfdmaChanTable OBJECT-TYPE
        SYNTAX     SEQUENCE OF HwDocsIf31CmtsUsOfdmaChanEntry
        MAX-ACCESS not-accessible
        STATUS     current
        DESCRIPTION
            "
            Indicates the upstream channel status parameters.
            The index of this table is ifIndex.
            "
        ::= { hwDocsIf31AccessObject 1 }

    hwDocsIf31CmtsUsOfdmaChanEntry OBJECT-TYPE
        SYNTAX     HwDocsIf31CmtsUsOfdmaChanEntry
        MAX-ACCESS not-accessible
        STATUS     current
        DESCRIPTION
            "
            Indicates the upstream channel status parameters.
            The index of this entry is ifIndex.
            "
        INDEX       { ifIndex }
        ::= { hwDocsIf31CmtsUsOfdmaChanTable 1 }

    HwDocsIf31CmtsUsOfdmaChanEntry ::=
        SEQUENCE {
                 hwDocsIf31CmtsUsOfdmaChanEfficiency Integer32,
                 hwDocsIf31CmtsUsOfdmaChanMinRxMer   Integer32,
                 hwDocsIf31CmtsUsOfdmaChanMaxRxMer   Integer32,
                 hwDocsIf31CmtsUsOfdmaChanMdUsSgId   Unsigned32,
                 hwDocsIf31CmtsUsOfdmaChanPer        Integer32,
                 hwDocsIf31CmtsUsOfdmaChanRealTimeDataRate Integer32,
                 hwDocsIf31CmtsUsOfdmaChanMaxDataRate Integer32
        }
        
    hwDocsIf31CmtsUsOfdmaChanEfficiency OBJECT-TYPE
            SYNTAX Integer32 (0..100)
            UNITS "%"
            MAX-ACCESS read-only
            STATUS current
            DESCRIPTION
                "Indicates the upstream channel modulation efficiency.
                 0 represents invalid value.               
                "
         ::= { hwDocsIf31CmtsUsOfdmaChanEntry 1 }
         
  hwDocsIf31CmtsUsOfdmaChanMinRxMer OBJECT-TYPE
            SYNTAX Integer32
            UNITS "TenthdB"
            MAX-ACCESS read-only
            STATUS current 
            DESCRIPTION
                "This attribute represents the minimum RxMER of the upstream OFDMA channel. 
                -1(0xffffffff) represents invalid value.            
                "
         ::= { hwDocsIf31CmtsUsOfdmaChanEntry 2 }
         
  hwDocsIf31CmtsUsOfdmaChanMaxRxMer OBJECT-TYPE
            SYNTAX Integer32
            UNITS "TenthdB"
            MAX-ACCESS read-only
            STATUS current
            DESCRIPTION
                "This attribute represents the maximum RxMER of the upstream OFDMA channel. 
                -1(0xffffffff) represents invalid value.           
                "
         ::= { hwDocsIf31CmtsUsOfdmaChanEntry 3 }

   hwDocsIf31CmtsUsOfdmaChanMdUsSgId OBJECT-TYPE
           SYNTAX Unsigned32
           MAX-ACCESS read-only
           STATUS current
           DESCRIPTION
               "This object indicates MAC domain upstream service group ID of this channel."

        ::= { hwDocsIf31CmtsUsOfdmaChanEntry 4 }

   hwDocsIf31CmtsUsOfdmaChanPer OBJECT-TYPE
            SYNTAX Integer32
            UNITS "0.00001"
            MAX-ACCESS read-only
            STATUS current
            DESCRIPTION
                "The rate of package error received on the up channels.
                 -1 represents invalid value.             
                "
         ::= { hwDocsIf31CmtsUsOfdmaChanEntry 5 }

   hwDocsIf31CmtsUsOfdmaChanRealTimeDataRate OBJECT-TYPE
            SYNTAX Integer32
            UNITS "kbps"
            MAX-ACCESS read-only
            STATUS current
            DESCRIPTION
                "The real time data rate.
                 -1 represents invalid value.                            
                "
         ::= { hwDocsIf31CmtsUsOfdmaChanEntry 6 }  
         
         hwDocsIf31CmtsUsOfdmaChanMaxDataRate OBJECT-TYPE
            SYNTAX Integer32
            UNITS "kbps"
            MAX-ACCESS read-only
            STATUS current
            DESCRIPTION
                "The max data rate.
                 -1 represents invalid value.                            
                "
         ::= { hwDocsIf31CmtsUsOfdmaChanEntry 7 }  
                              
    --Table hwDocsIf31CmtsUsOfdmaChanTable end
    
    --Table hwDocsIf31CmtsDsOfdmChanTable begin
        
    hwDocsIf31CmtsDsOfdmChanTable OBJECT-TYPE
        SYNTAX     SEQUENCE OF HwDocsIf31CmtsDsOfdmChanEntry
        MAX-ACCESS not-accessible
        STATUS     current
        DESCRIPTION
            "
            Indicates the downstream channel status parameters.
            The index of this table is ifIndex.
            "
        ::= { hwDocsIf31AccessObject 2 }

    hwDocsIf31CmtsDsOfdmChanEntry OBJECT-TYPE
        SYNTAX     HwDocsIf31CmtsDsOfdmChanEntry
        MAX-ACCESS not-accessible
        STATUS     current
        DESCRIPTION
            "
            Indicates the downstream channel status parameters.
            The index of this entry is ifIndex.
            "
        INDEX       { ifIndex }
        ::= { hwDocsIf31CmtsDsOfdmChanTable 1 }

    HwDocsIf31CmtsDsOfdmChanEntry ::=
        SEQUENCE {
                 hwDocsIf31CmtsDsOfdmChanEfficiency Integer32, 
                 hwDocsIf31CmtsDsOfdmChanTxPower    Integer32,
                 hwDocsIf31CmtsDsOfdmChanRealTimeDataRate Integer32,
                 hwDocsIf31CmtsDsOfdmChanMaxDataRate Integer32
        }
        
    hwDocsIf31CmtsDsOfdmChanEfficiency OBJECT-TYPE
            SYNTAX Integer32 (0..100)
            UNITS "%"
            MAX-ACCESS read-only
            STATUS current
            DESCRIPTION
                "Indicates the modulation efficiency of the OFDM downstream channel.
                 0 represents invalid value.               
                "
         ::= { hwDocsIf31CmtsDsOfdmChanEntry 1 }
         
  hwDocsIf31CmtsDsOfdmChanTxPower OBJECT-TYPE
            SYNTAX Integer32
            UNITS "TenthdBmV"
            MAX-ACCESS read-only
            STATUS current
            DESCRIPTION
                "This attribute represents the Tx power of the OFDM downstream channel based on 6 MHz frequency bandwidth.
                -2147483647 represents invalid value.           
                "
         ::= { hwDocsIf31CmtsDsOfdmChanEntry 2 }
         
   hwDocsIf31CmtsDsOfdmChanRealTimeDataRate OBJECT-TYPE
            SYNTAX Integer32
            UNITS "kbps"
            MAX-ACCESS read-only
            STATUS current
            DESCRIPTION
                "The real time data rate.
                 -1 represents invalid value.                               
                "     
         ::= { hwDocsIf31CmtsDsOfdmChanEntry 3 }
         
         hwDocsIf31CmtsDsOfdmChanMaxDataRate OBJECT-TYPE
            SYNTAX Integer32
            UNITS "kbps"
            MAX-ACCESS read-only
            STATUS current
            DESCRIPTION
                "The max data rate.
                 -1 represents invalid value.                               
                "     
         ::= { hwDocsIf31CmtsDsOfdmChanEntry 4 }

    --Table hwDocsIf31CmtsDsOfdmChanTable end
    
    --Table hwDocsIf31CmtsCmRegStatusTable begin
        
    hwDocsIf31CmtsCmRegStatusTable OBJECT-TYPE
        SYNTAX     SEQUENCE OF HwDocsIf31CmtsCmRegStatusEntry
        MAX-ACCESS not-accessible
        STATUS     current
        DESCRIPTION
            "
            Indicates the IUC type of the upstream channel modulation profile and 
            the downstream channel modulation profile used by the CM.
            The index of this table is docsIf3CmtsCmRegStatusId.
            "
        ::= { hwDocsIf31AccessObject 3 }

    hwDocsIf31CmtsCmRegStatusEntry OBJECT-TYPE
        SYNTAX     HwDocsIf31CmtsCmRegStatusEntry
        MAX-ACCESS not-accessible
        STATUS     current
        DESCRIPTION
            "
            Indicates the IUC type of the upstream channel modulation profile and 
            the downstream channel modulation profile used by the CM.
            The index of this entry is docsIf3CmtsCmRegStatusId.
            "
        INDEX       { docsIf3CmtsCmRegStatusId  }
        ::= { hwDocsIf31CmtsCmRegStatusTable 1 }
    
    HwDocsIf31CmtsCmRegStatusEntry ::=
        SEQUENCE {
                 hwDocsIf31CmtsCmRegStatusDsProfileId   OCTET STRING,
                 hwDocsIf31CmtsCmRegStatusUsProfileIuc  OCTET STRING,
                 hwDocsIf31CmtsCmRegStatusPrimaryUsTimingOffset  Integer32
                 }
        
    hwDocsIf31CmtsCmRegStatusDsProfileId OBJECT-TYPE
            SYNTAX OCTET STRING (SIZE (0..32))
            MAX-ACCESS read-only
            STATUS current
            DESCRIPTION
                "Indicates the downstream channel modulation profile used by the CM.
                For example, if a CM uses profile0 on channel 97 and profile1 on 
                channel 98, the parameter value is 0x61006201.
                Return a zero-length OCTET STRING to indicate the invalid value.
                0xFF indicates the invalid profile ID.                
                "
         ::= { hwDocsIf31CmtsCmRegStatusEntry 1 }

    hwDocsIf31CmtsCmRegStatusUsProfileIuc OBJECT-TYPE
            SYNTAX OCTET STRING (SIZE (0..32))
            MAX-ACCESS read-only
            STATUS current
            DESCRIPTION
                "Indicates the IUC type of the upstream channel modulation profile 
                used by the CM. For example, if a CM uses IUC5 on channel 17 and IUC6 
                on channel 18, the parameter value is 0x11051206.
                Return a zero-length OCTET STRING to indicate the invalid value.
                0xFF indicates the invalid IUC type.              
                "
         ::= { hwDocsIf31CmtsCmRegStatusEntry 2 } 

    hwDocsIf31CmtsCmRegStatusPrimaryUsTimingOffset OBJECT-TYPE
            SYNTAX      Integer32
            UNITS       "time tick/(64*256)"
            MAX-ACCESS  read-only
            STATUS      current
            DESCRIPTION
                "This attribute represents the current measured round trip time on this 
                 CM's primary upstream channel in units of (6.25 microseconds/(64*256)). 
                 This attribute returns zero if the value is unknown.              
                "
         ::= { hwDocsIf31CmtsCmRegStatusEntry 3 }
              
    --Table hwDocsIf31CmtsCmRegStatusTable end
    
    --Table hwDocsPnmCmtsUsOfdmaRxMerTable begin
        
    hwDocsPnmCmtsUsOfdmaRxMerTable OBJECT-TYPE
        SYNTAX     SEQUENCE OF HwDocsPnmCmtsUsOfdmaRxMerEntry
        MAX-ACCESS not-accessible
        STATUS     current
        DESCRIPTION
            "
            Indicates to start the collection of OFDMA upstream channel subcarrier RxMER 
            data for DOCSIS 3.1 CMs.
            The indexes of this table are ifindex and hwDocsPnmCmtsUsOfdmaRxMerMacAddress.
            "
        ::= { hwDocsIf31AccessObject 4 }

    hwDocsPnmCmtsUsOfdmaRxMerEntry OBJECT-TYPE
        SYNTAX     HwDocsPnmCmtsUsOfdmaRxMerEntry
        MAX-ACCESS not-accessible
        STATUS     current
        DESCRIPTION
            "
            Indicates to start the collection of OFDMA upstream channel subcarrier RxMER 
            data for DOCSIS 3.1 CMs.
            The indexes of this entry are ifindex and hwDocsPnmCmtsUsOfdmaRxMerMacAddress.
            "
        INDEX       { ifIndex, hwDocsPnmCmtsUsOfdmaRxMerMacAddress }
        ::= { hwDocsPnmCmtsUsOfdmaRxMerTable 1 }

    HwDocsPnmCmtsUsOfdmaRxMerEntry ::=
        SEQUENCE {
                 hwDocsPnmCmtsUsOfdmaRxMerMacAddress   MacAddress,
                 hwDocsPnmCmtsUsOfdmaRxMerRowStatus    RowStatus,
                 hwDocsPnmCmtsUsOfdmaRxMerPreEq        TruthValue,
                 hwDocsPnmCmtsUsOfdmaRxMerNumAvgs      Unsigned32,
                 hwDocsPnmCmtsUsOfdmaRxMerMeasStatus   MeasStatusType
        }
        
    hwDocsPnmCmtsUsOfdmaRxMerMacAddress OBJECT-TYPE
          SYNTAX  MacAddress
          MAX-ACCESS  not-accessible
          STATUS  current
          DESCRIPTION
                "This attribute represents the MAC address of the CM."
          ::= { hwDocsPnmCmtsUsOfdmaRxMerEntry 1 }
        
    hwDocsPnmCmtsUsOfdmaRxMerRowStatus OBJECT-TYPE
            SYNTAX RowStatus
            MAX-ACCESS read-create
            STATUS current
            DESCRIPTION
                "Indicates the row status to create or 
                 delete a RxMER data collection task."
         ::= { hwDocsPnmCmtsUsOfdmaRxMerEntry 2 }
    
    hwDocsPnmCmtsUsOfdmaRxMerPreEq OBJECT-TYPE
            SYNTAX TruthValue
            MAX-ACCESS read-write
            STATUS current
            DESCRIPTION
                "This attribute is used by the CMTS to enable or disable Pre 
                Equalization of the probe. The Pre Equalization is controlled 
                by a bit in the Probe Information Element sent in a MAP to the 
                CM. This object cannot be changed while a capture is in progress. 
                1. true(1)  - enable the Pre Equalization of the probe
                2. false(2) - disable the Pre Equalization of the probe
                Default: false(2)                
                "
         ::= { hwDocsPnmCmtsUsOfdmaRxMerEntry 3 }
    
    hwDocsPnmCmtsUsOfdmaRxMerNumAvgs OBJECT-TYPE
            SYNTAX Unsigned32 (0..255)
            MAX-ACCESS read-write
            STATUS current
            DESCRIPTION
                "This attribute controls the number of probes the CMTS will use to 
                calculate the RxMER per subcarrier. The average will be computed using 
                the 'leaky integrator' method, where reported RxMER per subcarrier 
                value = alpha*accumulated values + (1-alpha)*current value. Alpha is 
                one minus the reciprocal of the number of averages. For example, if N=25, 
                then alpha = 0.96. A value of 1 indicates no averaging. Re-writing the 
                number of averages will restart the averaging process.  If there are no 
                accumulated values, the accumulators are made equal to the first measured 
                bin amplitudes. This object cannot be changed while a capture is in progress. 
                Default value: 5              
                "
         ::= { hwDocsPnmCmtsUsOfdmaRxMerEntry 4 }
         
    hwDocsPnmCmtsUsOfdmaRxMerMeasStatus OBJECT-TYPE
            SYNTAX MeasStatusType
            MAX-ACCESS read-only
            STATUS current
            DESCRIPTION
                "This attribute is used to determine the status of the measurement. 
                The PNM server will query this value to determine when the file is 
                ready for transfer.          
                "
         ::= { hwDocsPnmCmtsUsOfdmaRxMerEntry 5 }          
    
    --Table hwDocsPnmCmtsUsOfdmaRxMerTable end
    
    --Table hwDocsPnmCmtsUsOfdmaRxMerReportTable begin
        
    hwDocsPnmCmtsUsOfdmaRxMerReportTable OBJECT-TYPE
        SYNTAX     SEQUENCE OF HwDocsPnmCmtsUsOfdmaRxMerReportEntry
        MAX-ACCESS not-accessible
        STATUS     current
        DESCRIPTION
            "
            Indicates to query the collection result of OFDMA upstream channel subcarrier 
            RxMER data for DOCSIS 3.1 CMs.
            The indexes of this table are ifindex and hwDocsPnmCmtsUsOfdmaRxMerReportMacAddress.
            "
        ::= { hwDocsIf31AccessObject 5 }

    hwDocsPnmCmtsUsOfdmaRxMerReportEntry OBJECT-TYPE
        SYNTAX     HwDocsPnmCmtsUsOfdmaRxMerReportEntry
        MAX-ACCESS not-accessible
        STATUS     current
        DESCRIPTION
            "
            Indicates to query the collection result of OFDMA upstream channel subcarrier 
            RxMER data for DOCSIS 3.1 CMs.
            The indexes of this entry are ifindex and hwDocsPnmCmtsUsOfdmaRxMerReportMacAddress.
            "
        INDEX       { ifIndex, hwDocsPnmCmtsUsOfdmaRxMerReportMacAddress  }
        ::= { hwDocsPnmCmtsUsOfdmaRxMerReportTable 1 }

    HwDocsPnmCmtsUsOfdmaRxMerReportEntry ::=
        SEQUENCE {
                 hwDocsPnmCmtsUsOfdmaRxMerReportMacAddress             MacAddress,
                 hwDocsPnmCmtsUsOfdmaRxMerLength                       Integer32,
                 hwDocsPnmCmtsUsOfdmaRxMerZeroFreq                     Integer32,
                 hwDocsPnmCmtsUsOfdmaRxMerFirstActiveSubcarrierNum     Integer32,
                 hwDocsPnmCmtsUsOfdmaRxMerSubCarrierSpacing            SubcarrierSpacingType,
                 hwDocsPnmCmtsUsOfdmaRxMerData                         OCTET STRING
        }
        
    hwDocsPnmCmtsUsOfdmaRxMerReportMacAddress OBJECT-TYPE
          SYNTAX  MacAddress
          MAX-ACCESS  not-accessible
          STATUS  current
          DESCRIPTION
                "This attribute represents the MAC address of the CM."
          ::= { hwDocsPnmCmtsUsOfdmaRxMerReportEntry 1 }
        
    hwDocsPnmCmtsUsOfdmaRxMerLength OBJECT-TYPE
            SYNTAX Integer32 
            MAX-ACCESS read-only
            STATUS current
            DESCRIPTION
                "Indicates the RxMER data length.
                0 represents invalid value.                
                "
         ::= { hwDocsPnmCmtsUsOfdmaRxMerReportEntry 2 }

    hwDocsPnmCmtsUsOfdmaRxMerZeroFreq OBJECT-TYPE
            SYNTAX Integer32
            UNITS  "Hz"
            MAX-ACCESS read-only
            STATUS current
            DESCRIPTION
                "Indicates the frequency of subcarrier 0.
                0 represents invalid value.           
                "
         ::= { hwDocsPnmCmtsUsOfdmaRxMerReportEntry 3 }         
    
    hwDocsPnmCmtsUsOfdmaRxMerFirstActiveSubcarrierNum OBJECT-TYPE
            SYNTAX Integer32
            MAX-ACCESS read-only
            STATUS current
            DESCRIPTION
                "Indicates the index of the first valid subcarrier.
                0 represents invalid value.              
                "
         ::= { hwDocsPnmCmtsUsOfdmaRxMerReportEntry 4 }
    
    hwDocsPnmCmtsUsOfdmaRxMerSubCarrierSpacing OBJECT-TYPE
            SYNTAX SubcarrierSpacingType
            UNITS       "kHz"
            MAX-ACCESS read-only
            STATUS current
            DESCRIPTION
                "This attribute defines the subcarrier spacing associated with
                a particular FFT mode configured on the OFDM downstream 
                channel. If it is 4K mode, then the subcarrier spacing is 
                50kHz. If it is 8K mode, then the subcarrier spacing is 
                25kHz.
                "
         ::= { hwDocsPnmCmtsUsOfdmaRxMerReportEntry 5 }
    
    hwDocsPnmCmtsUsOfdmaRxMerData OBJECT-TYPE
            SYNTAX OCTET STRING
            UNITS  "1/4 dB"
            MAX-ACCESS read-only
            STATUS current
            DESCRIPTION
                "Indicates the RxMER data content.Each subcarrier uses one byte to 
                indicate the RxMER data in hexadecimal format in the unit of 1/4 dB.
                Return a zero-length OCTET STRING to indicate that the data is not achieved.           
                "
         ::= { hwDocsPnmCmtsUsOfdmaRxMerReportEntry 6 }
    
    --Table hwDocsPnmCmtsUsOfdmaRxMerReportTable end    
    
    --Table hwDocsIf31CmtsCmUsOfdmaChannelStatusTable begin
    hwDocsIf31CmtsCmUsOfdmaChannelStatusTable OBJECT-TYPE
        SYNTAX     SEQUENCE OF HwDocsIf31CmtsCmUsOfdmaChannelStatusEntry
        MAX-ACCESS not-accessible
        STATUS     current
        DESCRIPTION
            "
            Indicates to query the collection result of OFDMA upstream channel words data
            for DOCSIS 3.1 CMs.
            The indexes of this table are docsIf3CmtsCmRegStatusId and ifIndex.
            "
        ::= { hwDocsIf31AccessObject 6 }       
        
     hwDocsIf31CmtsCmUsOfdmaChannelStatusEntry OBJECT-TYPE
        SYNTAX     HwDocsIf31CmtsCmUsOfdmaChannelStatusEntry
        MAX-ACCESS not-accessible
        STATUS     current
        DESCRIPTION
            "
            Indicates to query the collection result of OFDMA upstream channel words data
            for DOCSIS 3.1 CMs.
            The indexes of this entry are docsIf3CmtsCmRegStatusId and ifIndex.
            "
        INDEX       { docsIf3CmtsCmRegStatusId, ifIndex  }
        ::= { hwDocsIf31CmtsCmUsOfdmaChannelStatusTable 1 }  
        
    HwDocsIf31CmtsCmUsOfdmaChannelStatusEntry ::=
        SEQUENCE {
                 hwDocsIf31CmtsCmUsOfdmaChannelUncorrectedErrorCodewords         Counter64,
                 hwDocsIf31CmtsCmUsOfdmaChannelCorrectedErrorCodewords           Counter64,
                 hwDocsIf31CmtsCmUsOfdmaChannelGoodCodewords                     Counter64,
                 hwDocsIf31CmtsCmUsOfdmaChannelUtilization                       Unsigned32 (0..100),
                 hwDocsIf31CmtsCmUsOfdmaChannelMinMeanRxMer                      Unsigned32,
                 hwDocsIf31CmtsCmUsOfdmaChannelMaxMeanRxMer                      Unsigned32,
                 hwDocsIf31CmtsCmUsOfdmaChannelTxPower                           Integer32,
                 hwDocsIf31CmtsCmUsOfdmaChannelMaxTxPower                        Integer32,
                 hwDocsIf31CmtsCmUsOfdmaChannelMinTxPower                        Integer32,
                 hwDocsIf31CmtsCmUsOfdmaChannelT3Timeouts                        Integer32,
                 hwDocsIf31CmtsCmUsOfdmaChannelT4Timeouts                        Integer32
        }
    
    hwDocsIf31CmtsCmUsOfdmaChannelUncorrectedErrorCodewords OBJECT-TYPE
          SYNTAX  Counter64
          MAX-ACCESS  read-only
          STATUS  current
          DESCRIPTION
              "
              This attribute represents the codewords received with uncorrectable errors 
              from the CM on this ofdma upstream channel.
              18446744073709551615(0xFFFFFFFFFFFFFFFF) represents invalid value.
              "
          ::= { hwDocsIf31CmtsCmUsOfdmaChannelStatusEntry 1 }

    hwDocsIf31CmtsCmUsOfdmaChannelCorrectedErrorCodewords OBJECT-TYPE
          SYNTAX Counter64 
          MAX-ACCESS read-only
          STATUS current
          DESCRIPTION
              "
              This attribute represents the codewords received with correctable errors from
              the CM on this ofdma upstream channel.
              18446744073709551615(0xFFFFFFFFFFFFFFFF) represents invalid value.                
              "
         ::= { hwDocsIf31CmtsCmUsOfdmaChannelStatusEntry 2 }
    
    hwDocsIf31CmtsCmUsOfdmaChannelGoodCodewords OBJECT-TYPE
        SYNTAX Counter64 
        MAX-ACCESS read-only
        STATUS current
        DESCRIPTION
            "
            This attribute represents the codewords received without error from the CM 
            on this ofdma upstream channel.
            18446744073709551615(0xFFFFFFFFFFFFFFFF) represents invalid value.                
            "
     ::= { hwDocsIf31CmtsCmUsOfdmaChannelStatusEntry 3 }  
     
  hwDocsIf31CmtsCmUsOfdmaChannelUtilization OBJECT-TYPE
        SYNTAX Unsigned32 (0..100) 
        MAX-ACCESS read-only
        STATUS current
        DESCRIPTION
            "
            This attribute represents OFDMA upstream channel utilization rate of the CM.
            Default value: 0                  
            "
     ::= { hwDocsIf31CmtsCmUsOfdmaChannelStatusEntry 4 }
     
  hwDocsIf31CmtsCmUsOfdmaChannelMinMeanRxMer OBJECT-TYPE
          SYNTAX  Unsigned32
          UNITS  "HundredthdB"
          MAX-ACCESS  read-only
          STATUS  current
          DESCRIPTION
              "
              This attribute represents the minimum RxMER of a CM using the upstream OFDMA channel.
              4294967295 represents invalid value.
              "
          ::= { hwDocsIf31CmtsCmUsOfdmaChannelStatusEntry 5 }
          
  hwDocsIf31CmtsCmUsOfdmaChannelMaxMeanRxMer OBJECT-TYPE
          SYNTAX  Unsigned32
          UNITS  "HundredthdB"
          MAX-ACCESS  read-only
          STATUS  current
          DESCRIPTION
              "
              This attribute represents the maximum RxMER of a CM using the upstream OFDMA channel. 
              4294967295 represents invalid value.
              "
          ::= { hwDocsIf31CmtsCmUsOfdmaChannelStatusEntry 6 }
          
  hwDocsIf31CmtsCmUsOfdmaChannelTxPower OBJECT-TYPE
          SYNTAX  Integer32
          UNITS  "TenthdBmV"
          MAX-ACCESS  read-only
          STATUS  current
          DESCRIPTION
              "
              This attribute represents Rx power of a CM using the upstream OFDMA channel. 
              -2147483647 represents invalid value.
              "
          ::= { hwDocsIf31CmtsCmUsOfdmaChannelStatusEntry 7 }
          
  hwDocsIf31CmtsCmUsOfdmaChannelMaxTxPower OBJECT-TYPE
          SYNTAX  Integer32
          UNITS  "TenthdBmV"
          MAX-ACCESS  read-only
          STATUS  current
          DESCRIPTION
              "
              This attribute represents the maximum Tx power of a CM using the upstream OFDMA channel. 
              -2147483647 represents invalid value.
              "
          ::= { hwDocsIf31CmtsCmUsOfdmaChannelStatusEntry 8 }
          
  hwDocsIf31CmtsCmUsOfdmaChannelMinTxPower OBJECT-TYPE
          SYNTAX  Integer32
          UNITS  "TenthdBmV"
          MAX-ACCESS  read-only
          STATUS  current
          DESCRIPTION
              "
              This attribute represents the minimum Tx power of a CM using the upstream OFDMA channel. 
              -2147483647 represents invalid value.
              "
          ::= { hwDocsIf31CmtsCmUsOfdmaChannelStatusEntry 9 }

  hwDocsIf31CmtsCmUsOfdmaChannelT3Timeouts OBJECT-TYPE
          SYNTAX  Integer32
          UNITS  "timeouts"
          MAX-ACCESS  read-only
          STATUS  current
          DESCRIPTION
              "
              Number of times counter T3 expired in the CM.
              T3 represents waiting for ranging response.
              -1 represents invalid value.
              "
          ::= { hwDocsIf31CmtsCmUsOfdmaChannelStatusEntry 10 }
          
  hwDocsIf31CmtsCmUsOfdmaChannelT4Timeouts OBJECT-TYPE
          SYNTAX  Integer32
          UNITS  "timeouts"
          MAX-ACCESS  read-only
          STATUS  current
          DESCRIPTION
              "
             Number of times counter T4 expired in the CM.
             T4 represents waiting for unicast ranging opportunity.
             -1 represents invalid value.
              "
          ::= { hwDocsIf31CmtsCmUsOfdmaChannelStatusEntry 11 }
                        
    --Table hwDocsIf31CmtsCmUsOfdmaChannelStatusTable end      
    
    --Table hwDocsIf31CmtsCmDsOfdmChannelStatusTable begin
        hwDocsIf31CmtsCmDsOfdmChannelStatusTable OBJECT-TYPE
        SYNTAX     SEQUENCE OF HwDocsIf31CmtsCmDsOfdmChannelStatusEntry
        MAX-ACCESS not-accessible
        STATUS     current
        DESCRIPTION
            "
            Indicates to query the collection result of OFDM downstream channel words data
            for DOCSIS 3.1 CMs.
            The indexes of this table are docsIf3CmtsCmRegStatusId and ifIndex.
            "
        ::= { hwDocsIf31AccessObject 7 }       
        
     hwDocsIf31CmtsCmDsOfdmChannelStatusEntry OBJECT-TYPE
        SYNTAX     HwDocsIf31CmtsCmDsOfdmChannelStatusEntry
        MAX-ACCESS not-accessible
        STATUS     current
        DESCRIPTION
            "
            Indicates to query the collection result of OFDM downstream channel words data
            for DOCSIS 3.1 CMs.
            The indexes of this entry are docsIf3CmtsCmRegStatusId and ifIndex.
            "
        INDEX       { docsIf3CmtsCmRegStatusId, ifIndex  }
        ::= { hwDocsIf31CmtsCmDsOfdmChannelStatusTable 1 }  
        
    HwDocsIf31CmtsCmDsOfdmChannelStatusEntry ::=
        SEQUENCE {
                 hwDocsIf31CmtsCmDsOfdmChannelUncorrectedErrorCode         Counter64,
                 hwDocsIf31CmtsCmDsOfdmChannelCorrectedErrorCode           Counter64,
                 hwDocsIf31CmtsCmDsOfdmChannelGoodCode                     Counter64,
                 hwDocsIf31CmtsCmDsOfdmChannelUtilization                  Unsigned32 (0..100),
                 hwDocsIf31CmtsCmDsOfdmChannelMeanRxMER                    Unsigned32,
                 hwDocsIf31CmtsCmDsOfdmChannelMinMeanRxMER                 Unsigned32,
                 hwDocsIf31CmtsCmDsOfdmChannelMaxMeanRxMER                 Unsigned32,
                 hwDocsIf31CmtsCmDsOfdmChannelRxPower                      Integer32,
                 hwDocsIf31CmtsCmDsOfdmChannelMinRxPower                   Integer32,
                 hwDocsIf31CmtsCmDsOfdmChannelMaxRxPower                   Integer32,
                 hwDocsIf31CmtsCmDsOfdmChannelTxPower                      Integer32
        }
    
    hwDocsIf31CmtsCmDsOfdmChannelUncorrectedErrorCode OBJECT-TYPE
          SYNTAX  Counter64
          MAX-ACCESS  read-only
          STATUS  current
          DESCRIPTION
              "
              This attribute represents the codewords received with uncorrectable errors from 
              the CM on this ofdm downstream channel.
              18446744073709551615(0xFFFFFFFFFFFFFFFF) represents invalid value.
              "
          ::= { hwDocsIf31CmtsCmDsOfdmChannelStatusEntry 1 }

    hwDocsIf31CmtsCmDsOfdmChannelCorrectedErrorCode OBJECT-TYPE
          SYNTAX Counter64 
          MAX-ACCESS read-only
          STATUS current
          DESCRIPTION
              "
              This attribute represents the codewords received with correctable errors from 
              the CM on this ofdm downstream channel.
              18446744073709551615(0xFFFFFFFFFFFFFFFF) represents invalid value.represents invalid value.                
              "
         ::= { hwDocsIf31CmtsCmDsOfdmChannelStatusEntry 2 }
    
    hwDocsIf31CmtsCmDsOfdmChannelGoodCode OBJECT-TYPE
        SYNTAX Counter64 
        MAX-ACCESS read-only
        STATUS current
        DESCRIPTION
            "
            This attribute represents the codewords received without error from the CM on this
            ofdm downstream channel.
            18446744073709551615(0xFFFFFFFFFFFFFFFF) represents invalid value.                
            "
      ::= { hwDocsIf31CmtsCmDsOfdmChannelStatusEntry 3 }
     
  hwDocsIf31CmtsCmDsOfdmChannelUtilization OBJECT-TYPE
        SYNTAX Unsigned32 (0..100) 
        MAX-ACCESS read-only
        STATUS current
        DESCRIPTION
            "
            This attribute represents OFDM downstream channel utilization rate of the CM.
            Default value: 0                  
            "
      ::= { hwDocsIf31CmtsCmDsOfdmChannelStatusEntry 4 }
      
    hwDocsIf31CmtsCmDsOfdmChannelMeanRxMER OBJECT-TYPE
        SYNTAX Unsigned32
        UNITS "HundredthdB" 
        MAX-ACCESS read-only
        STATUS current
        DESCRIPTION
            "
            This attribute represents the average RxMER of a CM using the downstream OFDM channel. 
            4294967295 represents invalid value.            
            "
      ::= { hwDocsIf31CmtsCmDsOfdmChannelStatusEntry 5 }
      
  hwDocsIf31CmtsCmDsOfdmChannelMinMeanRxMER OBJECT-TYPE
        SYNTAX Unsigned32
        UNITS "HundredthdB" 
        MAX-ACCESS read-only
        STATUS current
        DESCRIPTION
            "
            This attribute represents the minimum average RxMER of a CM using the downstream OFDM channel.
            4294967295 represents invalid value.                   
            "
      ::= { hwDocsIf31CmtsCmDsOfdmChannelStatusEntry 6 }
      
  hwDocsIf31CmtsCmDsOfdmChannelMaxMeanRxMER OBJECT-TYPE
        SYNTAX Unsigned32
        UNITS "HundredthdB" 
        MAX-ACCESS read-only
        STATUS current
        DESCRIPTION
            "
            This attribute represents the maximum average RxMER of a CM using the downstream OFDM channel. 
            4294967295 represents invalid value.                
            "
      ::= { hwDocsIf31CmtsCmDsOfdmChannelStatusEntry 7 }
      
  hwDocsIf31CmtsCmDsOfdmChannelRxPower OBJECT-TYPE
        SYNTAX Integer32
        UNITS "TenthdBmV" 
        MAX-ACCESS read-only
        STATUS current
        DESCRIPTION
            "
            This attribute represents Rx power of a CM using the downstream OFDM channel.
            -2147483647 represents invalid value.             
            "
      ::= { hwDocsIf31CmtsCmDsOfdmChannelStatusEntry 8 }
      
  hwDocsIf31CmtsCmDsOfdmChannelMinRxPower OBJECT-TYPE
        SYNTAX Integer32
        UNITS "TenthdBmV"
        MAX-ACCESS read-only
        STATUS current
        DESCRIPTION
            "
            This attribute represents the minimum Rx power of a CM using the downstream OFDM channel.
            -2147483647 represents invalid value.               
            "
      ::= { hwDocsIf31CmtsCmDsOfdmChannelStatusEntry 9 }   
      
  hwDocsIf31CmtsCmDsOfdmChannelMaxRxPower OBJECT-TYPE
        SYNTAX Integer32
        UNITS "TenthdBmV"
        MAX-ACCESS read-only
        STATUS current
        DESCRIPTION
            "
            This attribute represents the minimum Rx power of a CM using the downstream OFDM channel. 
            -2147483647 represents invalid value.                
            "
      ::= { hwDocsIf31CmtsCmDsOfdmChannelStatusEntry 10 }
      
  hwDocsIf31CmtsCmDsOfdmChannelTxPower OBJECT-TYPE
        SYNTAX Integer32
        UNITS "TenthdBmV" 
        MAX-ACCESS read-only
        STATUS current
        DESCRIPTION
            "
            This attribute represents Tx power of a CM using the downstream OFDM channel. 
            -2147483647 represents invalid value.               
            "
      ::= { hwDocsIf31CmtsCmDsOfdmChannelStatusEntry 11 }

    --Table hwDocsIf31CmtsCmDsOfdmChannelStatusTable end  
END
