-- =============================================================================================================
-- Copyright (C) 2016 by  HUAWEI TECHNOLOGIES. All rights reserved.
-- Description: This MIB module defines Huawei's Policy Information Transfer Protocol (PITP) MIB objects.
--              PITP is a member of the Huawei Group Management Protocol (HGMP) family, and provides the Broadband
--              Remote Access Server (BRAS) with the information about the port of access users. PITP binds user
--              accounts to the access ports together to prevent theft and roaming of user accounts.
-- Reference:
-- Version:   V1.53
-- ==============================================================================================================

    HUAWEI-DSLAM-PITP-MIB DEFINITIONS ::= BEGIN

        IMPORTS
            huaweiUtility
                FROM HUAWEI-MIB
            ifIndex
                FROM IF-MIB
            Unsigned32, OBJECT-TYPE, MODULE-IDENTITY,Integer32
                FROM SNMPv2-SMI
            TruthValue, RowStatus, DisplayString
                FROM SNMPv2-TC;

        hwPITP MODULE-IDENTITY
            LAST-UPDATED "201601200000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION
                "This MIB module defines Huawei's Policy Information Transfer Protocol (PITP) MIB objects.
                 PITP is a member of the Huawei Group Management Protocol (HGMP) family, and provides the Broadband
                 Remote Access Server (BRAS) with the information about the port of access users. PITP binds user
                 accounts to the access ports together to prevent theft and roaming of user accounts."

            --  Revision history
            REVISION     "201601200000Z"
            DESCRIPTION  "V1.53, added hwDslamRaioSuboptionFastReport.
                         "

            REVISION     "201506010000Z"
            DESCRIPTION  "V1.52, added radiusNasPortId(5) to hwDslamRAIOObject.
                          Added hwDslamRadiusNasPortIdRAIOMode and hwDslamRaioProfileRadiusNasPortIdRaioMode.
                         "

            REVISION     "201503110000Z"
            DESCRIPTION  "V1.51, deleted the table of hwDslamPITPPmodePortPvcTable."

            REVISION     "201502020000Z"
            DESCRIPTION  "V1.50, modified the description of hwDslamRaioProtocolTypeIndex.
                         "

            REVISION     "201412270000Z"
            DESCRIPTION  "V1.49, added hwDslamRaioSuboptionActualDataRateType."

            REVISION     "201409010000Z"
            DESCRIPTION  "V1.48, modified the revision log of version 1.47.
                         "

            REVISION     "201408150000Z"
            DESCRIPTION  "V1.47, modified the attributes of hwDslamPppoeFlowStatisticsRowStatus.
                         "

            REVISION     "201406100000Z"
            DESCRIPTION  "V1.46, modified the enumerate of hwDslamPITPTransparentUserVlanType,
                                 modified hwDslamPITP to hwPITP.
                         "

            REVISION     "201401170000Z"
            DESCRIPTION  "V1.45, added true(17) to hwDslamRaioProfilePitpRaioMode, hwDslamRaioProfileDhcpOption82RaioMode,
                          hwDslamRaioProfileAncpRaioMode and hwDslamRaioProfileDhcpv6OptionRaioMode.
                         "

            REVISION     "201401100000Z"
            DESCRIPTION  "V1.44, added hwDslamPITPTransparentUserVlanType and hwDslamPITPTransparentSingleUserVlanList."

            REVISION     "201312200000Z"
            DESCRIPTION  "V1.43, modified the description of hwDslamRAIOAncpAggCidFormatString."

            REVISION     "201310230000Z"
            DESCRIPTION  "V1.42, added true(17) to hwDslamPITPRAIOMode, hwDslamDHCPOPTION82RAIOMode, hwDslamRAIOMode, hwDslamAncpRAIOMode, hwDslamDHCPv6OPTIONRAIOMode."

            REVISION     "201309110000Z"
            DESCRIPTION  "V1.41, added hwDslamRaioDHCPv6Option17CableLabsSubSuboptionTable."

            REVISION     "201307300000Z"
            DESCRIPTION  "V1.40, added hwDslamRAIOAncpAggCidFormatString."

            REVISION     "201305130000Z"
            DESCRIPTION  "V1.39, added hwDslamRaioCableLabsSuboptionTable."

            REVISION     "201301100000Z"
            DESCRIPTION  "V1.38, The number of dashes used form comments was changed to two."

            REVISION     "201211070000Z"
            DESCRIPTION  "V1.37, modified description of hwDslamRAIORowStatus."

            REVISION     "201205120000Z"
            DESCRIPTION  "V1.36, added docsis(5) to hwDslamRAIOIfType."

            REVISION     "201203140000Z"
            DESCRIPTION  "V1.35, modified the value range of hwDslamPppoeFlowStatisticsIndex."

            REVISION     "201112290000Z"
            DESCRIPTION  "V1.34, added hwDslamPppoeReverse."

            REVISION     "201109270000Z"
            DESCRIPTION  "V1.33, added vnpt(16) to hwDslamDHCPv6OPTIONRAIOMode,hwDslamRaioProfilePitpRaioMode,
                          hwDslamRaioProfileDhcpOption82RaioMode,hwDslamRaioProfileAncpRaioMode,hwDslamRaioProfileDhcpv6OptionRaioMode.
                         "

            REVISION     "201108120000Z"
            DESCRIPTION  "V1.32, added vnpt(16) to hwDslamPITPRAIOMode,hwDslamDHCPOPTION82RAIOMode,hwDslamAncpRAIOMode and hwDslamRAIOMode.
                          Modified the indication of hwDslamDHCPOPTION82RAIOMode,hwDslamAncpRAIOMode,hwDslamRaioProfileDhcpOption82RaioMode,
                          hwDslamRaioProfileAncpRaioMode and hwDslamRaioProfileDhcpv6OptionRaioMode.
                         "

            REVISION     "201107290000Z"
            DESCRIPTION  "V1.31, modified the description."

            REVISION     "201102130000Z"
            DESCRIPTION  "V1.30, added hwDslamPppoeFlowStatisticsTable.
                         "

            REVISION     "201101250000Z"
            DESCRIPTION  "V1.29, changed hwDslamRaioProfileAccessNodeIp to hwDslamRaioProfileAccessNodeIpIfType
                          and hwDslamRaioProfileAccessNodeIpIfNumber. Moved hwDslamRaioProfileAccessNodeId to a
                          new position.
                         "

            REVISION     "201012150000Z"
            DESCRIPTION  "V1.28, added hwDslamRaioProfileTable, hwDslamRaioProfileSuboptionTable
                          and hwDslamRaioProfileFormatTable.
                         "

            REVISION     "201011260000Z"
            DESCRIPTION  "V1.27, added dhcpv6Option(4) to hwDslamRAIOObject.
                          Added hwDslamDHCPv6OPTIONRAIOMode and hwDslamRAIODhcpv6Option37EnterpriseNumber.
                         "

            REVISION     "201011170000Z"
            DESCRIPTION  "V1.26, modified description of all leaves. Modified the value range of hwDslamRAIOIfType."

            REVISION     "201011110000Z"
            DESCRIPTION  "V1.25, added bbf(15) to hwDslamPITPRAIOMode,hwDslamDHCPOPTION82RAIOMode,hwDslamAncpRAIOMode and hwDslamRAIOMode.
                          Added forwardPmode(4) and rebuildPmode(5) to hwDslamPITPStatus.
                         "

            REVISION     "201011090000Z"
            DESCRIPTION  "V1.24, modified the description."

            REVISION     "201010110000Z"
            DESCRIPTION  "V1.23, modified the description."

            REVISION     "201007100000Z"
            DESCRIPTION  "V1.22, modified the description of hwDslamAccessNodeId and hwDslamAccessNodeIp.
                          Modified the description of all enumerate values.
                         "

            REVISION     "201004250000Z"
            DESCRIPTION  "V1.21, modified description of all leaves."

            REVISION     "201003110000Z"
            DESCRIPTION  "V1.20, modified enumeration format."

            REVISION     "200910280000Z"
            DESCRIPTION  "V1.16, added tm(14) to hwDslamPITPRAIOMode,hwDslamDHCPOPTION82RAIOMode and hwDslamRAIOMode."

            REVISION     "200909100000Z"
            DESCRIPTION  "V1.15, added cntelXpon to hwDslamPITPRAIOMode."

            REVISION     "200407280900Z"
            DESCRIPTION  "V1.00, initial version."

            ::= { huaweiUtility 42 }

        hwDslamPITPStatus OBJECT-TYPE
            SYNTAX INTEGER
                {
                disable(1),
                enableVmode(2),
                enablePmode(3),
                forwardPmode(4),
                rebuildPmode(5)
                }
            MAX-ACCESS read-write
            STATUS current
            DESCRIPTION
                "Indicates the status of the global PITP switch.
                 Options:
                 1. disable(1)      -indicates the global PITP switch is off
                 2. enableVmode(2)  -indicates the global PITP switch is V mode
                 3. enablePmode(3)  -indicates the global PITP switch is P mode
                 4. forwardPmode(4) -indicates not processing the vendor tag of the packet, but transparent it transmitted. Only for P mode
                 5. rebuildPmode(5) -indicates rebuild the vendor tag from the ONU device, to meet the TR-156 needs, only for P mode
                 Default: disable(1)
                "
            ::= { hwPITP 1 }

        hwDslamPITPVmodeEtherType OBJECT-TYPE
            SYNTAX Unsigned32 (1536..65535)
            MAX-ACCESS read-write
            STATUS current
            DESCRIPTION
                "Indicates the Ethernet protocol type of the PITP VBAS.
                 Range: 1536-65535, that is, 0x600-0xFFFF
                 Default: 33280(0x8200)
                 Restrictions: If the value set to a protocol type is the same as any of other protocol types in the system,
                 the setting fails.
                "
            ::= { hwPITP 2 }

        hwDslamPITPXdslPortRateInfoSwitch OBJECT-TYPE
            SYNTAX INTEGER
                {
                disable(1),
                enable(2)
                }
            MAX-ACCESS   read-write
            STATUS       current
            DESCRIPTION
                "Xdsl port rate information switch, current support Adsl only.
                 Options:
                 1. disable(1) -indicates the Xdsl port rate information switch is off
                 2. enable(2)  -indicates Xdsl port rate information switch is on
                 Default: disable(1)
                "
            ::= { hwPITP 3}

        hwDslamPITPCNTelSwitch OBJECT-TYPE
            SYNTAX INTEGER
                {
                disable(1),
                enable(2)
                }
            MAX-ACCESS   read-write
            STATUS       current
            DESCRIPTION
                "Xdsl add BRAS information switch.
                 Options:
                 1. disable(1) -indicates the Xdsl add BRAS information switch is off
                 2. enable(2)  -indicates Xdsl add BRAS information switch is on
                 Default: disable(1)
                "
            ::= { hwPITP 4}

        hwDslamPITPTITagSwitch OBJECT-TYPE
            SYNTAX INTEGER
                {
                disable(1),
                enable(2)
                }
            MAX-ACCESS   read-write
            STATUS       current
            DESCRIPTION
                "TI Add Dhcp && PITP Tag information switch
                 Options:
                 1. disable(1) -indicates the TI Add Dhcp && PITP Tag information switch is off
                 2. enable(2)  -indicates the TI Add Dhcp && PITP Tag information switch is on
                 Default: disable(1)
                "
            ::= { hwPITP 5}

        hwDslamPITPRAIOMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS   read-write
            STATUS       current
            DESCRIPTION
                "Indicates the RAIO mode of PPPoE plus/VBAS.
                 Options:
                 1. common(1)               -indicates the RAIO mode of PPPoE plus/VBAS is common
                 2. xdslPortRate(2)         -indicates the RAIO mode of PPPoE plus/VBAS is Xdsl port rate
                 3. cntel(3)                -indicates the RAIO mode of PPPoE plus/VBAS is Xdsl add BRAS
                 4. ti(4)                   -indicates the RAIO mode of PPPoE plus/VBAS is TI Add Dhcp && PITP Tag
                 5. neuf(5)                 -indicates the RAIO mode of PPPoE plus/VBAS is neuf
                 6. portUserLabel(6)        -indicates the RAIO mode of PPPoE plus/VBAS is portUserLabel
                 7. bt(7)                   -indicates the RAIO mode of PPPoE plus/VBAS is bt
                 8. servicePortUserLabel(8) -indicates the RAIO mode of PPPoE plus/VBAS is servicePortUserLabel
                 9. dslForumDefault(9)      -indicates the RAIO mode of PPPoE plus/VBAS is dslForumDefault
                 10. brt(10)                -indicates the RAIO mode of PPPoE plus/VBAS is brt
                 11. userDefined(11)        -indicates the RAIO mode of PPPoE plus/VBAS is user defined
                 12. ft(12)                 -indicates the RAIO mode of PPPoE plus/VBAS is ft
                 13. cntelXpon(13)          -indicates the RAIO mode of PPPoE plus/VBAS is Xpon add BRAS
                 14. tm(14)                 -indicates the RAIO mode of PPPoE plus/VBAS is tm
                 15. bbf(15)                -indicates the RAIO mode of PPPoE plus is bbf
                 16. vnpt(16)               -indicates the RAIO mode of PPPoE plus is vnpt
                 17. true(17)               -indicates the RAIO mode of PPPoE plus is true
                 Default: common(1)
                 Restrictions:
                 bt(7) is not supported.
                 The VBAS supports only common(1), cntel(3), and userDefined(11).
                 When this leaf is set to userDefined(11), the specific RAIO format must be configured through hwDslamRAIOFormatTable.
                "
            ::= { hwPITP 6}

        hwDslamPITPPMODERAIOMode OBJECT-TYPE
            SYNTAX INTEGER
                {
                common(1),
                xdslPortRate(2),
                cntel(3),
                ti(4),
                neuf(5),
                portUserLabel(6),
                bt(7),
                bbf(15)
                }
            MAX-ACCESS   read-write
            STATUS       current
            DESCRIPTION
                "RAIO(Relay agent info Option) mode of PITP pmode.
                 Options:
                 1. common(1)               -indicates the RAIO mode of PPPoE plus/VBAS is common
                 2. xdslPortRate(2)         -indicates the RAIO mode of PPPoE plus/VBAS is Xdsl port rate
                 3. cntel(3)                -indicates the RAIO mode of PPPoE plus/VBAS is Xdsl add BRAS
                 4. ti(4)                   -indicates the RAIO mode of PPPoE plus/VBAS is TI Add Dhcp && PITP Tag
                 5. neuf(5)                 -indicates the RAIO mode of PPPoE plus/VBAS is neuf
                 6. portUserLabel(6)        -indicates the RAIO mode of PPPoE plus/VBAS is portUserLabel
                 7. bt(7)                   -indicates the RAIO mode of PPPoE plus/VBAS is bt
                 8. bbf(15)                 -indicates the RAIO mode of PPPoE plus is bbf
                 Default: common(1)
                "
            ::= { hwPITP 7}

        hwDslamPITPVMODERAIOMode OBJECT-TYPE
            SYNTAX INTEGER
                {
                common(1),
                cntel(3)
                }
            MAX-ACCESS   read-write
            STATUS       current
            DESCRIPTION
                "RAIO(Relay agent info Option) mode of PITP vmode.
                 Options:
                 1. common(1)               -indicates the RAIO mode of PPPoE plus/VBAS is common
                 2. cntel(3)                -indicates the RAIO mode of PPPoE plus/VBAS is Xdsl add BRAS
                 Default: common(1)
                "
            ::= { hwPITP 8}

        hwDslamDHCPOPTION82RAIOMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS   read-write
            STATUS       current
            DESCRIPTION
                "Indicates the RAIO mode of DHCP Option82.
                 Options:
                 1. common(1)               -indicates the RAIO mode of DHCP Option82 is common
                 2. xdslPortRate(2)         -indicates the RAIO mode of DHCP Option82 is Xdsl port rate
                 3. cntel(3)                -indicates the RAIO mode of DHCP Option82 is Xdsl add BRAS
                 4. ti(4)                   -indicates the RAIO mode of DHCP Option82 is TI Add Dhcp && PITP Tag
                 5. neuf(5)                 -indicates the RAIO mode of DHCP Option82 is neuf
                 6. portUserLabel(6)        -indicates the RAIO mode of DHCP Option82 is portUserLabel
                 7. bt(7)                   -indicates the RAIO mode of DHCP Option82 is bt
                 8. servicePortUserLabel(8) -indicates the RAIO mode of DHCP Option82 is servicePortUserLabel
                 9. dslForumDefault(9)      -indicates the RAIO mode of DHCP Option82 is dslForumDefault
                 10. brt(10)                -indicates the RAIO mode of DHCP Option82 is brt
                 11. userDefined(11)        -indicates the RAIO mode of DHCP Option82 is user defined
                 12. ft(12)                 -indicates the RAIO mode of DHCP Option82 is ft
                 13. cntelXpon(13)          -indicates the RAIO mode of DHCP Option82 is Xpon add BRAS
                 14. tm(14)                 -indicates the RAIO mode of DHCP Option82 is tm
                 15. bbf(15)                -indicates the RAIO mode of DHCP Option82 is bbf
                 16. vnpt(16)               -indicates the RAIO mode of DHCP Option82 is vnpt
                 17. true(17)               -indicates the RAIO mode of DHCP Option82 is true
                 Default: common(1)
                 Restrictions:
                 bt(7) is not supported.
                 When this leaf is set to userDefined(11), the specific RAIO format must be configured through hwDslamRAIOFormatTable.
                "
            ::= { hwPITP 9}

        hwDslamRAIOFormatTable OBJECT-TYPE
            SYNTAX SEQUENCE OF HwDslamRAIOFormatEntry
            MAX-ACCESS not-accessible
            STATUS current
            DESCRIPTION
                "Used for querying the RAIO format; supports the setting of only the user-defined mode.
                 The indexes of this table are hwDslamRAIOObject, hwDslamRAIOIdPara, hwDslamRAIOMode and hwDslamRAIOIfType.
                "
            ::= { hwPITP 10 }

        hwDslamRAIOFormatEntry OBJECT-TYPE
            SYNTAX HwDslamRAIOFormatEntry
            MAX-ACCESS not-accessible
            STATUS current
            DESCRIPTION
                "Used for querying the RAIO format; supports the setting of only the user-defined mode.
                 The indexes of this entry are hwDslamRAIOObject, hwDslamRAIOIdPara, hwDslamRAIOMode and hwDslamRAIOIfType.
                "
            INDEX { hwDslamRAIOObject, hwDslamRAIOIdPara, hwDslamRAIOMode, hwDslamRAIOIfType }
            ::= { hwDslamRAIOFormatTable 1 }

        HwDslamRAIOFormatEntry ::=
            SEQUENCE {
                hwDslamRAIOObject                  INTEGER,
                hwDslamRAIOIdPara                  INTEGER,
                hwDslamRAIOMode                    INTEGER,
                hwDslamRAIOIfType                  INTEGER,
                hwDslamRAIOFormatString            OCTET STRING,
                hwDslamRAIORowStatus               RowStatus
                }

        hwDslamRAIOObject OBJECT-TYPE
            SYNTAX INTEGER
                {
                pitp(1),
                dhcpOption82(2),
                ancp(3),
                dhcpv6Option(4),
                radiusNasPortId(5)
                }
            MAX-ACCESS not-accessible
            STATUS current
            DESCRIPTION
                "Indicates the RAIO object. This leaf is an index.
                 Options:
                 1. pitp(1)            -indicates the RAIO object is pitp
                 2. dhcpOption82(2)    -indicates the RAIO object is dhcpOption82
                 3. ancp(3)            -indicates the RAIO object is ancp
                 4. dhcpv6Option(4)    -indicates the RAIO object is dhcpv6Option
                 5. radiusNasPortId(5) -indicates the RAIO object is radiusNasPortId
                "
            ::= { hwDslamRAIOFormatEntry 1 }

        hwDslamRAIOIdPara OBJECT-TYPE
            SYNTAX INTEGER
                {
                cid(1),
                rid(2),
                info(3)
                }
            MAX-ACCESS not-accessible
            STATUS current
            DESCRIPTION
                "Indicates the RAIO ID parameter. This leaf is an index.
                 Options:
                 1. cid(1)  -indicates the RAIO object is cid
                 2. rid(2)  -indicates the RAIO object is rid
                 3. info(3) -indicates the RAIO object is info
                "
            ::= { hwDslamRAIOFormatEntry 2 }


        hwDslamRAIOMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS not-accessible
            STATUS current
            DESCRIPTION
                "Indicates the RAIO mode. This leaf is an index.
                 Options:
                 1. common(1)               -indicates the RAIO mode is common
                 2. xdslPortRate(2)         -indicates the RAIO mode is Xdsl port rate
                 3. cntel(3)                -indicates the RAIO mode is Xdsl add BRAS
                 4. ti(4)                   -indicates the RAIO mode is TI Add Dhcp && PITP Tag
                 5. neuf(5)                 -indicates the RAIO mode is neuf
                 6. portUserLabel(6)        -indicates the RAIO mode is portUserLabel
                 7. bt(7)                   -indicates the RAIO mode is bt
                 8. servicePortUserLabel(8) -indicates the RAIO mode is servicePortUserLabel
                 9. dslForumDefault(9)      -indicates the RAIO mode is dslForumDefault
                 10. brt(10)                -indicates the RAIO mode is brt
                 11. userDefined(11)        -indicates the RAIO mode is user defined
                 12. ft(12)                 -indicates the RAIO mode is ft
                 13. cntelXpon(13)          -indicates the RAIO mode is Xpon add BRAS
                 14. tm(14)                 -indicates the RAIO mode is tm
                 15. bbf(15)                -indicates the RAIO mode is bbf
                 16. vnpt(16)               -indicates the RAIO mode is vnpt
                 17. true(17)               -indicates the RAIO mode is true
                 Default: common(1)
                 Restrictions:
                 bt(7) is not supported.
                 The VBAS supports only common(1), cntel(3), and userDefined(11).
                "
            ::= { hwDslamRAIOFormatEntry 3 }

        hwDslamRAIOIfType OBJECT-TYPE
            SYNTAX INTEGER
                {
                atm(1),
                eth(2),
                xpon(3),
                eoc(4),
                docsis(5)
                }
            MAX-ACCESS not-accessible
            STATUS current
            DESCRIPTION
                "Indicates the interface type.
                 Options:
                 1. atm(1)    -atm interface type
                 2. eth(2)    -eth interface type
                 3. xpon(3)   -xpon interface type
                 4. eoc(4)    -eoc interface type
                 5. docsis(5) -docsis interface type
                 For the ATM access mode (the ATM mode of xDSL boards),
                 the value of this leaf is atm(1); for the Ethernet access mode
                 (the PTM mode of the OPFA board and xDSL boards), the value of
                 this leaf is eth(2); for the xPON access mode, the value of this leaf is xpon(3);
                 for the EOC access mode, the value of this leaf is eoc(4);
                 for the docsis access mode, the value of this leaf is docsis(5).
                "
            ::= { hwDslamRAIOFormatEntry 4 }

        hwDslamRAIOFormatString OBJECT-TYPE
            SYNTAX OCTET STRING  (SIZE (0..255))
            MAX-ACCESS read-write
            STATUS current
            DESCRIPTION
                "Indicates the character string of the RAIO format.
                 Range: a string of 0-255 characters.
                "
            ::= { hwDslamRAIOFormatEntry 5 }

        hwDslamRAIORowStatus OBJECT-TYPE
            SYNTAX       RowStatus
            MAX-ACCESS   read-create
            STATUS       current
            DESCRIPTION
                "Indicates the row status, used for deleting the RAIO format.
                 Options active(1), createAndGo(4) and destroy(6) are supported. Currently,
                 this leaf does not support the create and query operations.
                 To modify the RAIO format, you need not bind the row status.
                 To delete the RAIO format, you must input hwDslamRAIORowStatus.
                "
            DEFVAL { active }
            ::= { hwDslamRAIOFormatEntry 6}

        hwDslamPITPPmodePortTable OBJECT-TYPE
            SYNTAX SEQUENCE OF HwDslamPITPPmodePortEntry
            MAX-ACCESS not-accessible
            STATUS current
            DESCRIPTION
                "PITP pmode of port management table.
                 The index of this table is ifIndex.
                "
            ::= { hwPITP 12 }

        hwDslamPITPPmodePortEntry OBJECT-TYPE
            SYNTAX HwDslamPITPPmodePortEntry
            MAX-ACCESS not-accessible
            STATUS current
            DESCRIPTION
                "PITP pmode of port management table.
                 The index of this entry is ifIndex.
                "
            INDEX { ifIndex }
            ::= { hwDslamPITPPmodePortTable 1 }

        HwDslamPITPPmodePortEntry ::=
            SEQUENCE {
                hwDslamPITPPmodePortAdminStatus
                    TruthValue,
                hwDslamPITPPmodePortUplinkStatus
                    TruthValue,
                hwDslamPITPPmodePortRowStatus
                    RowStatus
             }

        hwDslamPITPPmodePortAdminStatus OBJECT-TYPE
            SYNTAX TruthValue
            MAX-ACCESS read-write
            STATUS current
            DESCRIPTION
                "PITP pmode of port administer state.
                 Options: true(enable), false(disable)
                 Default: false
                "
            DEFVAL { false }
            ::= { hwDslamPITPPmodePortEntry 1 }

        hwDslamPITPPmodePortUplinkStatus OBJECT-TYPE
            SYNTAX TruthValue
            MAX-ACCESS read-write
            STATUS current
            DESCRIPTION
                "Up-link administer state. Only a port on main board can be an up-link.
                 Options: true(yes), false(no),
                 Default: true
                "
            ::= { hwDslamPITPPmodePortEntry 2 }

        hwDslamPITPPmodePortRowStatus OBJECT-TYPE
            SYNTAX RowStatus
            MAX-ACCESS read-create
            STATUS current
            DESCRIPTION
                "Row status.
                 Add or delete a table item.
                "
            ::= { hwDslamPITPPmodePortEntry 3 }

        hwDslamPITPPmodeSuboption90Status OBJECT-TYPE
            SYNTAX TruthValue
            MAX-ACCESS read-write
            STATUS current
            DESCRIPTION
                "Indicates PPPoE plus Suboption90.
                 Options:
                 1. true(1)  -indicates PPPoE plus Suboption90 is enable
                 2. false(2) -indicates PPPoE plus Suboption90 is disable
                 Default: false(2)
                 Restrictions:
                 The operation on this leaf takes effect in the PPPoE plus mode only.
                "
            ::= { hwPITP 13 }

        hwDslamPITPPmodeSuboptionTable OBJECT-TYPE
            SYNTAX SEQUENCE OF HwDslamPITPPmodeSuboptionEntry
            MAX-ACCESS not-accessible
            STATUS current
            DESCRIPTION
                "PITP pmode suboption table.
                 The index of this table is hwDslamPITPPmodeSuboptionIndex.
                "
            ::= { hwPITP 14 }

        hwDslamPITPPmodeSuboptionEntry OBJECT-TYPE
            SYNTAX HwDslamPITPPmodeSuboptionEntry
            MAX-ACCESS not-accessible
            STATUS current
            DESCRIPTION
                "PITP pmode suboption table.
                 The index of this entry is hwDslamPITPPmodeSuboptionIndex.
                "
            INDEX { hwDslamPITPPmodeSuboptionIndex }
            ::= { hwDslamPITPPmodeSuboptionTable 1 }

        HwDslamPITPPmodeSuboptionEntry ::=
            SEQUENCE {
                hwDslamPITPPmodeSuboptionIndex
                    Integer32,
                hwDslamPITPPmodeSuboptionStatus
                    TruthValue
                }

        hwDslamPITPPmodeSuboptionIndex OBJECT-TYPE
            SYNTAX Integer32 (1..15)
            MAX-ACCESS read-only
            STATUS current
            DESCRIPTION
                "the index of PITP pmode suboption:
                    -index 1 stand for suboption 0x81;
                    -index 2 stand for suboption 0x82;
                    -index 3 stand for suboption 0x83;
                    -index 4 stand for suboption 0x84;
                    -index 5 stand for suboption 0x85;
                    -index 6 stand for suboption 0x86;
                    -index 7 stand for suboption 0x87;
                    -index 8 stand for suboption 0x88;
                    -index 9 stand for suboption 0x89;
                    -index 10 stand for suboption 0x8a;
                    -index 11 stand for suboption 0x8b;
                    -index 12 stand for suboption 0x8c;
                    -index 13 stand for suboption 0x8d;
                    -index 14 stand for suboption 0x8e;
                    -index 15 stand for suboption 0x90;
                DEFVAL { 1 }
                "
            ::= { hwDslamPITPPmodeSuboptionEntry 1 }

        hwDslamPITPPmodeSuboptionStatus OBJECT-TYPE
            SYNTAX TruthValue
            MAX-ACCESS read-write
            STATUS current
            DESCRIPTION
                "Configuration of PITP pmode suboption.
                 Options: true(enable), false(disable)
                 Default: false
                "
                DEFVAL { 2 }
            ::= { hwDslamPITPPmodeSuboptionEntry 2 }

        hwDslamRaioSuboptionTable OBJECT-TYPE
            SYNTAX SEQUENCE OF HwDslamRaioSuboptionEntry
            MAX-ACCESS not-accessible
            STATUS current
            DESCRIPTION
                "Used for setting and querying RAIO suboptions.
                 The indexes of this table are hwDslamRaioProtocolTypeIndex and hwDslamRaioSuboptionIndex.
                "
            ::= { hwPITP 15 }

        hwDslamRaioSuboptionEntry OBJECT-TYPE
            SYNTAX HwDslamRaioSuboptionEntry
            MAX-ACCESS not-accessible
            STATUS current
            DESCRIPTION
                "Used for setting and querying RAIO suboptions.
                 The indexes of this entry are hwDslamRaioProtocolTypeIndex and hwDslamRaioSuboptionIndex.
                "
            INDEX { hwDslamRaioProtocolTypeIndex, hwDslamRaioSuboptionIndex }
            ::= { hwDslamRaioSuboptionTable 1 }

        HwDslamRaioSuboptionEntry ::=
            SEQUENCE {
                hwDslamRaioProtocolTypeIndex
                    Integer32,
                hwDslamRaioSuboptionIndex
                    Integer32,
                hwDslamRaioSuboptionStatus
                    INTEGER
             }

        hwDslamRaioProtocolTypeIndex OBJECT-TYPE
            SYNTAX Integer32 (1..255)
            MAX-ACCESS not-accessible
            STATUS current
            DESCRIPTION
                "Indicates the protocol type supporting RAIO suboptions. This leaf is an index.
                 Range: 1-255
                 The value 1 indicates DHCP Option82, 2 indicates PPPoE plus, 3 indicates DHCPv6 Option17, and 4-255 are reserved.
                "
            ::= { hwDslamRaioSuboptionEntry 1 }

        hwDslamRaioSuboptionIndex OBJECT-TYPE
            SYNTAX Integer32 (1..255)
            MAX-ACCESS not-accessible
            STATUS current
            DESCRIPTION
                "Indicates the RAIO suboption. This leaf is an index.
                 Range: 1-255
                 1-17 correspond to suboptions 0x81-0x91.
                "
            ::= { hwDslamRaioSuboptionEntry 2 }

        hwDslamRaioSuboptionStatus OBJECT-TYPE
            SYNTAX INTEGER {
                enable(1),
                disable(2)
                }
            MAX-ACCESS read-write
            STATUS current
            DESCRIPTION
                "Indicates the status of the RAIO suboption.
                 Options:
                 1. enable(1)  -indicates the RAIO suboption is enable
                 2. disable(2) -indicates the RAIO suboption is disable
                 Default: disable(2)
                "
            ::= { hwDslamRaioSuboptionEntry 3 }

        hwDslamAccessNodeId OBJECT-TYPE
            SYNTAX OCTET STRING (SIZE (0..50))
            MAX-ACCESS read-write
            STATUS current
            DESCRIPTION
                "Indicates the ANID.
                 Range: a string of 0-50 characters
                 Restrictions:
                 This leaf does not support the create operation, and supports only the modify and query operations.
                 To cancel the settings of the ANID, you can directly perform the set operation without inputting a leaf value.
                "
            ::= { hwPITP 16 }

        hwDslamAccessNodeIp OBJECT-TYPE
            SYNTAX      Integer32
            MAX-ACCESS read-write
            STATUS current
            DESCRIPTION
                "Indicates the L3 interface in the ANIP field. Currently, the device management IP address is used as the device identifier.
                 The value of the device management IP address is obtained through the VLAN L3 interface specified by hwDslamAccessNodeIp.
                 Range: 0-4294967295
                 Restrictions:
                 This leaf does not support the create operation, and supports only the modify and query operations.
                 To cancel the settings of the ANIP, input leaf value 4294967295 (equaling 0xFFFFFFFF) and perform the set operation.
                "
            ::= { hwPITP 17 }

--
-- ANCP RAIO mode
--
        hwDslamAncpRAIOMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS   read-write
            STATUS       current
            DESCRIPTION
                "RAIO(Relay agent info Option) mode of ANCP.
                 Options:
                 1. common(1)               -indicates the RAIO mode of ANCP is common
                 2. xdslPortRate(2)         -indicates the RAIO mode of ANCP is Xdsl port rate
                 3. cntel(3)                -indicates the RAIO mode of ANCP is Xdsl add BRAS
                 4. ti(4)                   -indicates the RAIO mode of ANCP is TI Add Dhcp && PITP Tag
                 5. neuf(5)                 -indicates the RAIO mode of ANCP is neuf
                 6. portUserLabel(6)        -indicates the RAIO mode of ANCP is portUserLabel
                 7. bt(7)                   -indicates the RAIO mode of ANCP is bt
                 8. servicePortUserLabel(8) -indicates the RAIO mode of ANCP is servicePortUserLabel
                 9. dslForumDefault(9)      -indicates the RAIO mode of ANCP is dslForumDefault
                 10. brt(10)                -indicates the RAIO mode of ANCP is brt
                 11. userDefined(11)        -indicates the RAIO mode of ANCP is user defined
                 12. ft(12)                 -indicates the RAIO mode of ANCP is ft
                 13. cntelXpon(13)          -indicates the RAIO mode of ANCP is Xpon add BRAS
                 14. tm(14)                 -indicates the RAIO mode of ANCP is tm
                 15. bbf(15)                -indicates the RAIO mode of ANCP is bbf
                 16. vnpt(16)               -indicates the RAIO mode of ANCP is vnpt
                 17. true(17)               -indicates the RAIO mode of ANCP is true
                 Default: dslForumDefault(9)
                "
            ::= { hwPITP 18}

--
-- DHCPv6Option RAIO mode
--
        hwDslamDHCPv6OPTIONRAIOMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS   read-write
            STATUS       current
            DESCRIPTION
                "Indicates the RAIO mode of DHCPv6 Option.
                 Options:
                 1. common(1)               -indicates the RAIO mode of DHCPv6 option is common
                 2. xdslPortRate(2)         -indicates the RAIO mode of DHCPv6 option is Xdsl port rate
                 3. cntel(3)                -indicates the RAIO mode of DHCPv6 option is Xdsl add BRAS
                 4. ti(4)                   -indicates the RAIO mode of DHCPv6 option is TI Add Dhcp && PITP Tag
                 5. neuf(5)                 -indicates the RAIO mode of DHCPv6 option is neuf
                 6. portUserLabel(6)        -indicates the RAIO mode of DHCPv6 option is portUserLabel
                 7. bt(7)                   -indicates the RAIO mode of DHCPv6 option is bt
                 8. servicePortUserLabel(8) -indicates the RAIO mode of DHCPv6 option is servicePortUserLabel
                 9. dslForumDefault(9)      -indicates the RAIO mode of DHCPv6 option is dslForumDefault
                 10. brt(10)                -indicates the RAIO mode of DHCPv6 option is brt
                 11. userDefined(11)        -indicates the RAIO mode of DHCPv6 option is user defined
                 12. ft(12)                 -indicates the RAIO mode of DHCPv6 option is ft
                 13. cntelXpon(13)          -indicates the RAIO mode of DHCPv6 option is Xpon add BRAS
                 14. tm(14)                 -indicates the RAIO mode of DHCPv6 option is tm
                 15. bbf(15)                -indicates the RAIO mode of DHCPv6 option is bbf
                 16. vnpt(16)               -indicates the RAIO mode of DHCPv6 option is vnpt
		 17. true(17)               -indicates the RAIO mode of DHCPv6 option is true
                 Default: common(1)
                 Restrictions:
                 bt(7) is not supported.
                 When this leaf is set to userDefined(11), the specific RAIO format must be configured through hwDslamRAIOFormatTable.
                "
            ::= { hwPITP 19}

--
-- Enterprise number
--

        hwDslamRAIODhcpv6Option37EnterpriseNumber OBJECT-TYPE
            SYNTAX Unsigned32 (0..4294967295)
            MAX-ACCESS read-write
            STATUS current
            DESCRIPTION
                "Indicates the enterprise number which is used in DHCPv6 option 37.
                 Range: 0-4294967295
                 DEFVAL {2011}
                "
            ::= { hwPITP 20}

--
-- RAIO profile
--

        hwDslamRaioProfileTable OBJECT-TYPE
            SYNTAX SEQUENCE OF HwDslamRaioProfileEntry
            MAX-ACCESS not-accessible
            STATUS current
            DESCRIPTION
                "Used for creating, setting and querying RAIO profiles.
                 The index of this table is hwDslamRaioProfileName.
                "
            ::= { hwPITP 21 }

        hwDslamRaioProfileEntry OBJECT-TYPE
            SYNTAX HwDslamRaioProfileEntry
            MAX-ACCESS not-accessible
            STATUS current
            DESCRIPTION
                "Used for creating, setting and querying RAIO profiles.
                 The index of this entry is hwDslamRaioProfileName.
                "
            INDEX { hwDslamRaioProfileName }
            ::= { hwDslamRaioProfileTable 1 }

        HwDslamRaioProfileEntry ::=
            SEQUENCE {
                hwDslamRaioProfileName                              OCTET STRING,
                hwDslamRaioProfileAccessNodeIpIfType                INTEGER,
                hwDslamRaioProfileAccessNodeIpIfNumber              Integer32,
                hwDslamRaioProfilePitpRaioMode                      INTEGER,
                hwDslamRaioProfileDhcpOption82RaioMode              INTEGER,
                hwDslamRaioProfileAncpRaioMode                      INTEGER,
                hwDslamRaioProfileDhcpv6OptionRaioMode              INTEGER,
                hwDslamRaioProfileDhcpv6Option37EnterpriseNumber    Unsigned32,
                hwDslamRaioProfileAccessNodeId                      OCTET STRING,
                hwDslamRaioProfileRowStatus                         RowStatus,
                hwDslamRaioProfileRadiusNasPortIdRaioMode           INTEGER
                }

        hwDslamRaioProfileName OBJECT-TYPE
            SYNTAX OCTET STRING  (SIZE (1..32))
            MAX-ACCESS not-accessible
            STATUS current
            DESCRIPTION
                "RAIO profile name.
                 Range: a string of 1-32 characters
                "
            ::= { hwDslamRaioProfileEntry 1 }

        hwDslamRaioProfileAccessNodeIpIfType OBJECT-TYPE
            SYNTAX INTEGER
                {
                notConfiged(1),
                meth(2),
                loopback(3),
                vlanif(4)
                }
            MAX-ACCESS read-write
            STATUS current
            DESCRIPTION
                "Indicates the interface type.
                 Options:
                 1. notConfiged(1) -indicates that no source interface is configured
                 2. meth(2)        -indicates the MEth interface
                 3. loopback(3)    -indicates the loopback interface
                 4. vlanif(4)      -indicates the VLAN interface
                 When this leaf is set to notConfiged(1), it means that no source
                 interface is configured in the case of the create operation, and
                 that the source interface is deleted in the case of the modify operation.
                "
            ::= { hwDslamRaioProfileEntry 2 }

        hwDslamRaioProfileAccessNodeIpIfNumber OBJECT-TYPE
            SYNTAX Integer32 (0..4093)
            MAX-ACCESS read-write
            STATUS current
            DESCRIPTION
                "Indicates the interface ID.
                 Range: 0-4093
                 Range for the MEth interface: 0
                 Range for the loopback interface: 0-31
                 Range for the VLAN interface: 1-4093
                 The interface ID and interface type together identify an interface.
                "
            ::= { hwDslamRaioProfileEntry 3 }

        hwDslamRaioProfilePitpRaioMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS read-write
            STATUS current
            DESCRIPTION
                "Indicates the RAIO mode. This leaf is an index.
                 Options:
                 1. common(1)               -indicates the RAIO mode of PPPoE plus/VBAS is common
                 2. xdslPortRate(2)         -indicates the RAIO mode of PPPoE plus/VBAS is Xdsl port rate
                 3. cntel(3)                -indicates the RAIO mode of PPPoE plus/VBAS is Xdsl add BRAS
                 4. ti(4)                   -indicates the RAIO mode of PPPoE plus/VBAS is TI Add Dhcp && PITP Tag
                 5. neuf(5)                 -indicates the RAIO mode of PPPoE plus/VBAS is neuf
                 6. portUserLabel(6)        -indicates the RAIO mode of PPPoE plus/VBAS is portUserLabel
                 7. bt(7)                   -indicates the RAIO mode of PPPoE plus/VBAS is bt
                 8. servicePortUserLabel(8) -indicates the RAIO mode of PPPoE plus/VBAS is servicePortUserLabel
                 9. dslForumDefault(9)      -indicates the RAIO mode of PPPoE plus/VBAS is dslForumDefault
                 10. brt(10)                -indicates the RAIO mode of PPPoE plus/VBAS is brt
                 11. userDefined(11)        -indicates the RAIO mode of PPPoE plus/VBAS is user defined
                 12. ft(12)                 -indicates the RAIO mode of PPPoE plus/VBAS is ft
                 13. cntelXpon(13)          -indicates the RAIO mode of PPPoE plus/VBAS is Xpon add BRAS
                 14. tm(14)                 -indicates the RAIO mode of PPPoE plus/VBAS is tm
                 15. bbf(15)                -indicates the RAIO mode of PPPoE plus/VBAS is bbf
                 16. vnpt(16)               -indicates the RAIO mode of PPPoE plus/VBAS is vnpt
                 17. true(17)               -indicates the RAIO mode of PPPoE plus/VBAS is true
                 Default: common(1)
                 Restrictions:
                 bt(7) is not supported.
                 The VBAS supports only common(1), cntel(3), and userDefined(11).
                "
            ::= { hwDslamRaioProfileEntry 4 }

        hwDslamRaioProfileDhcpOption82RaioMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS read-write
            STATUS current
            DESCRIPTION
                "Indicates the RAIO mode. This leaf is an index.
                 Options:
                 1. common(1)               -indicates the RAIO mode of DHCP Option82 is common
                 2. xdslPortRate(2)         -indicates the RAIO mode of DHCP Option82 is Xdsl port rate
                 3. cntel(3)                -indicates the RAIO mode of DHCP Option82 is Xdsl add BRAS
                 4. ti(4)                   -indicates the RAIO mode of DHCP Option82 is TI Add Dhcp && PITP Tag
                 5. neuf(5)                 -indicates the RAIO mode of DHCP Option82 is neuf
                 6. portUserLabel(6)        -indicates the RAIO mode of DHCP Option82 is portUserLabel
                 7. bt(7)                   -indicates the RAIO mode of DHCP Option82 is bt
                 8. servicePortUserLabel(8) -indicates the RAIO mode of DHCP Option82 is servicePortUserLabel
                 9. dslForumDefault(9)      -indicates the RAIO mode of DHCP Option82 is dslForumDefault
                 10. brt(10)                -indicates the RAIO mode of DHCP Option82 is brt
                 11. userDefined(11)        -indicates the RAIO mode of DHCP Option82 is user defined
                 12. ft(12)                 -indicates the RAIO mode of DHCP Option82 is ft
                 13. cntelXpon(13)          -indicates the RAIO mode of DHCP Option82 is Xpon add BRAS
                 14. tm(14)                 -indicates the RAIO mode of DHCP Option82 is tm
                 15. bbf(15)                -indicates the RAIO mode of DHCP Option82 is bbf
                 16. vnpt(16)               -indicates the RAIO mode of DHCP Option82 is vnpt
                 17. true(17)               -indicates the RAIO mode of DHCP Option82 is true
                 Default: common(1)
                 Restrictions:
                 bt(7) is not supported.
                "
            ::= { hwDslamRaioProfileEntry 5 }

        hwDslamRaioProfileAncpRaioMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS read-write
            STATUS current
            DESCRIPTION
                "Indicates the RAIO mode. This leaf is an index.
                 Options:
                 1. common(1)               -indicates the RAIO mode of ANCP is common
                 2. xdslPortRate(2)         -indicates the RAIO mode of ANCP is Xdsl port rate
                 3. cntel(3)                -indicates the RAIO mode of ANCP is Xdsl add BRAS
                 4. ti(4)                   -indicates the RAIO mode of ANCP is TI Add Dhcp && PITP Tag
                 5. neuf(5)                 -indicates the RAIO mode of ANCP is neuf
                 6. portUserLabel(6)        -indicates the RAIO mode of ANCP is portUserLabel
                 7. bt(7)                   -indicates the RAIO mode of ANCP is bt
                 8. servicePortUserLabel(8) -indicates the RAIO mode of ANCP is servicePortUserLabel
                 9. dslForumDefault(9)      -indicates the RAIO mode of ANCP is dslForumDefault
                 10. brt(10)                -indicates the RAIO mode of ANCP is brt
                 11. userDefined(11)        -indicates the RAIO mode of ANCP is user defined
                 12. ft(12)                 -indicates the RAIO mode of ANCP is ft
                 13. cntelXpon(13)          -indicates the RAIO mode of ANCP is Xpon add BRAS
                 14. tm(14)                 -indicates the RAIO mode of ANCP is tm
                 15. bbf(15)                -indicates the RAIO mode of ANCP is bbf
                 16. vnpt(16)               -indicates the RAIO mode of ANCP is vnpt
                 17. true(17)               -indicates the RAIO mode of ANCP is true
                 Default: dslForumDefault(9)
                 Restrictions:
                 bt(7) is not supported.
                "
            ::= { hwDslamRaioProfileEntry 6 }

        hwDslamRaioProfileDhcpv6OptionRaioMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS read-write
            STATUS current
            DESCRIPTION
                "Indicates the RAIO mode. This leaf is an index.
                 Options:
                 1. common(1)               -indicates the RAIO mode of DHCPv6 is common
                 2. xdslPortRate(2)         -indicates the RAIO mode of DHCPv6 is Xdsl port rate
                 3. cntel(3)                -indicates the RAIO mode of DHCPv6 is Xdsl add BRAS
                 4. ti(4)                   -indicates the RAIO mode of DHCPv6 is TI Add Dhcp && PITP Tag
                 5. neuf(5)                 -indicates the RAIO mode of DHCPv6 is neuf
                 6. portUserLabel(6)        -indicates the RAIO mode of DHCPv6 is portUserLabel
                 7. bt(7)                   -indicates the RAIO mode of DHCPv6 is bt
                 8. servicePortUserLabel(8) -indicates the RAIO mode of DHCPv6 is servicePortUserLabel
                 9. dslForumDefault(9)      -indicates the RAIO mode of DHCPv6 is dslForumDefault
                 10. brt(10)                -indicates the RAIO mode of DHCPv6 is brt
                 11. userDefined(11)        -indicates the RAIO mode of DHCPv6 is user defined
                 12. ft(12)                 -indicates the RAIO mode of DHCPv6 is ft
                 13. cntelXpon(13)          -indicates the RAIO mode of DHCPv6 is Xpon add BRAS
                 14. tm(14)                 -indicates the RAIO mode of DHCPv6 is tm
                 15. bbf(15)                -indicates the RAIO mode of DHCPv6 is bbf
                 16. vnpt(16)               -indicates the RAIO mode of DHCPv6 is vnpt
                 17. true(17)               -indicates the RAIO mode of DHCPv6 is true
                 Default: common(1)
                 Restrictions:
                 bt(7) is not supported.
                "
            ::= { hwDslamRaioProfileEntry 7 }

        hwDslamRaioProfileDhcpv6Option37EnterpriseNumber OBJECT-TYPE
            SYNTAX Unsigned32 (0..4294967295)
            MAX-ACCESS read-write
            STATUS current
            DESCRIPTION
                "Indicates the enterprise number which is used in DHCPv6 option 37.
                 Range: 0-4294967295
                "
            DEFVAL { 2011 }
            ::= { hwDslamRaioProfileEntry 8 }

        hwDslamRaioProfileAccessNodeId OBJECT-TYPE
            SYNTAX OCTET STRING  (SIZE (0..50))
            MAX-ACCESS read-write
            STATUS current
            DESCRIPTION
                "Indicates the ANID.
                 Range: a string of 0-50 characters
                 Restrictions:
                "
            ::= { hwDslamRaioProfileEntry 9 }

        hwDslamRaioProfileRowStatus OBJECT-TYPE
            SYNTAX RowStatus
            MAX-ACCESS read-create
            STATUS current
            DESCRIPTION
                "Indicates the row status, used for creating and deleting the RAIO profile.
                 Options createAndGo(4) and destroy(6) are supported. Currently,
                 to modify the RAIO profile, you need not bind the row status.
                 To delete the RAIO profile, you must input hwDslamRaioProfileRowStatus.
                "
            DEFVAL { active }
            ::= { hwDslamRaioProfileEntry 10 }

        hwDslamRaioProfileRadiusNasPortIdRaioMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS read-write
            STATUS current
            DESCRIPTION
                "Indicates the RAIO mode of RADIUS NAS-Port-Id. This leaf is an index.
                 Options:
                 1. common(1)               -indicates the RAIO mode of RADIUS NAS-Port-Id is common
                 2. xdslPortRate(2)         -indicates the RAIO mode of RADIUS NAS-Port-Id is Xdsl port rate
                 3. cntel(3)                -indicates the RAIO mode of RADIUS NAS-Port-Id is Xdsl add BRAS
                 4. ti(4)                   -indicates the RAIO mode of RADIUS NAS-Port-Id is TI Add Dhcp && PITP Tag
                 5. neuf(5)                 -indicates the RAIO mode of RADIUS NAS-Port-Id is neuf
                 6. portUserLabel(6)        -indicates the RAIO mode of RADIUS NAS-Port-Id is portUserLabel
                 7. bt(7)                   -indicates the RAIO mode of RADIUS NAS-Port-Id is bt
                 8. servicePortUserLabel(8) -indicates the RAIO mode of RADIUS NAS-Port-Id is servicePortUserLabel
                 9. dslForumDefault(9)      -indicates the RAIO mode of RADIUS NAS-Port-Id is dslForumDefault
                 10. brt(10)                -indicates the RAIO mode of RADIUS NAS-Port-Id is brt
                 11. userDefined(11)        -indicates the RAIO mode of RADIUS NAS-Port-Id is user defined
                 12. ft(12)                 -indicates the RAIO mode of RADIUS NAS-Port-Id is ft
                 13. cntelXpon(13)          -indicates the RAIO mode of RADIUS NAS-Port-Id is Xpon add BRAS
                 14. tm(14)                 -indicates the RAIO mode of RADIUS NAS-Port-Id is tm
                 15. bbf(15)                -indicates the RAIO mode of RADIUS NAS-Port-Id is bbf
                 16. vnpt(16)               -indicates the RAIO mode of RADIUS NAS-Port-Id is vnpt
                 17. true(17)               -indicates the RAIO mode of RADIUS NAS-Port-Id is true
                 Default: common(1)
                 Restrictions:
                 bt(7) is not supported.
                "
            ::= { hwDslamRaioProfileEntry 11 }

--
-- RAIO profile suboption
--

        hwDslamRaioProfileSuboptionTable OBJECT-TYPE
            SYNTAX SEQUENCE OF HwDslamRaioProfileSuboptionEntry
            MAX-ACCESS not-accessible
            STATUS current
            DESCRIPTION
                "Used for setting and querying the RAIO suboption state of the RAIO profile.
                 The indexes of this table are hwDslamRaioProfileName, hwDslamRaioProtocolTypeIndex
                 and hwDslamRaioSuboptionIndex.
                "
            ::= { hwPITP 22 }

        hwDslamRaioProfileSuboptionEntry OBJECT-TYPE
            SYNTAX HwDslamRaioProfileSuboptionEntry
            MAX-ACCESS not-accessible
            STATUS current
            DESCRIPTION
                "Used for setting and querying the RAIO suboption state of the RAIO profile.
                 The indexes of this entry are hwDslamRaioProfileName, hwDslamRaioProtocolTypeIndex
                 and hwDslamRaioSuboptionIndex.
                "
            INDEX { hwDslamRaioProfileName, hwDslamRaioProtocolTypeIndex, hwDslamRaioSuboptionIndex }
            ::= { hwDslamRaioProfileSuboptionTable 1 }

        HwDslamRaioProfileSuboptionEntry ::=
            SEQUENCE {
                hwDslamRaioProfileSuboptionStatus       INTEGER
                }

        hwDslamRaioProfileSuboptionStatus OBJECT-TYPE
            SYNTAX INTEGER {
                enable(1),
                disable(2)
                }
            MAX-ACCESS read-write
            STATUS current
            DESCRIPTION
                "Indicates the status of the RAIO suboption.
                 Options:
                 1. enable(1)   -indicates the RAIO suboption is enable
                 2. disable(2)  -indicates the RAIO suboption is disable
                 Default: disable(2)
                "
            ::= { hwDslamRaioProfileSuboptionEntry 1 }

--
-- RAIO profile format
--

        hwDslamRaioProfileFormatTable OBJECT-TYPE
            SYNTAX SEQUENCE OF HwDslamRaioProfileFormatEntry
            MAX-ACCESS not-accessible
            STATUS current
            DESCRIPTION
                "Used for querying the RAIO format of the RAIO profile; supports the setting of only the user-defined mode.
                 The indexes of this table are hwDslamRaioProfileName, hwDslamRAIOObject, hwDslamRAIOIdPara,
                 hwDslamRAIOMode, and hwDslamRAIOIfType.
                "
            ::= { hwPITP 23 }

        hwDslamRaioProfileFormatEntry OBJECT-TYPE
            SYNTAX HwDslamRaioProfileFormatEntry
            MAX-ACCESS not-accessible
            STATUS current
            DESCRIPTION
                "Used for querying the RAIO format of the RAIO profile; supports the setting of only the user-defined mode.
                 The indexes of this entry are hwDslamRaioProfileName, hwDslamRAIOObject, hwDslamRAIOIdPara,
                 hwDslamRAIOMode, and hwDslamRAIOIfType.
                "
            INDEX { hwDslamRaioProfileName, hwDslamRAIOObject, hwDslamRAIOIdPara, hwDslamRAIOMode, hwDslamRAIOIfType }
            ::= { hwDslamRaioProfileFormatTable 1 }

        HwDslamRaioProfileFormatEntry ::=
            SEQUENCE {
                hwDslamRaioProfileFormatString      OCTET STRING
                }

        hwDslamRaioProfileFormatString OBJECT-TYPE
            SYNTAX OCTET STRING  (SIZE (0..255))
            MAX-ACCESS read-write
            STATUS current
            DESCRIPTION
                "Indicates the character string of the RAIO format.
                 Range: a string of 0-255 characters.
                "
            ::= { hwDslamRaioProfileFormatEntry 1 }

--
-- PPPOEPLUS statistics service-port
--

        hwDslamPppoeFlowStatisticsTable OBJECT-TYPE
            SYNTAX SEQUENCE OF HwDslamPppoeFlowStatisticsEntry
            MAX-ACCESS not-accessible
            STATUS current
            DESCRIPTION
                "Used for querying and resetting the pppoeplus statistics on flow.
                 The index of this table is hwDslamPppoeFlowStatisticsIndex.
                 Statistics for a maximum of 64 service ports are supported.
                "
            ::= { hwPITP 24 }

        hwDslamPppoeFlowStatisticsEntry OBJECT-TYPE
            SYNTAX HwDslamPppoeFlowStatisticsEntry
            MAX-ACCESS not-accessible
            STATUS current
            DESCRIPTION
                "Used for querying and resetting the pppoeplus statistics on flow.
                 The index of this entry is hwDslamPppoeFlowStatisticsIndex.
                 Statistics for a maximum of 64 service ports are supported.
                "
            INDEX { hwDslamPppoeFlowStatisticsIndex }
            ::= { hwDslamPppoeFlowStatisticsTable 1 }

        HwDslamPppoeFlowStatisticsEntry ::=
            SEQUENCE {
                hwDslamPppoeFlowStatisticsIndex                 Unsigned32,
                hwDslamPppoeFlowStatisticsRowStatus             RowStatus,
                hwDslamPppoeFlowStatisticsOperMode              INTEGER,
                hwDslamPppoeFlowStatisticsReceivePadi           Unsigned32,
                hwDslamPppoeFlowStatisticsReceivePado           Unsigned32,
                hwDslamPppoeFlowStatisticsReceivePadr           Unsigned32,
                hwDslamPppoeFlowStatisticsReceivePads           Unsigned32,
                hwDslamPppoeFlowStatisticsReceivePadt           Unsigned32,
                hwDslamPppoeFlowStatisticsSendPadi              Unsigned32,
                hwDslamPppoeFlowStatisticsSendPado              Unsigned32,
                hwDslamPppoeFlowStatisticsSendPadr              Unsigned32,
                hwDslamPppoeFlowStatisticsSendPads              Unsigned32,
                hwDslamPppoeFlowStatisticsSendPadt              Unsigned32,
                hwDslamPppoeFlowStatisticsTagTooLong            Unsigned32,
                hwDslamPppoeFlowStatisticsFrameTooLong          Unsigned32,
                hwDslamPppoeFlowStatisticsReceiveUntrusted      Unsigned32,
                hwDslamPppoeFlowStatisticsReceiveUnknownType    Unsigned32
                }

        hwDslamPppoeFlowStatisticsIndex OBJECT-TYPE
            SYNTAX Unsigned32
            MAX-ACCESS not-accessible
            STATUS current
            DESCRIPTION
                "The index of the PPPoE statistics on flow.
                "
            ::= { hwDslamPppoeFlowStatisticsEntry 1 }

        hwDslamPppoeFlowStatisticsRowStatus OBJECT-TYPE
            SYNTAX RowStatus
            MAX-ACCESS read-create
            STATUS current
            DESCRIPTION
                "The present operation status of the row.
                 CreateAndGo(4) means enable the PPPoE statistics on flow.
                 Destroy(6) means disable the PPPoE statistics on flow.
                 Active(1) will be returned in the get operation.
                "
            ::= { hwDslamPppoeFlowStatisticsEntry 2 }

        hwDslamPppoeFlowStatisticsOperMode OBJECT-TYPE
            SYNTAX INTEGER {
                   reset(1),
                   invalid(2)
                }
            MAX-ACCESS read-write
            STATUS current
            DESCRIPTION
                "Indicates reset the PPPoE statistics on flow.
                 Options:
                 1. reset(1)   -In the set operation, reset the PPPoE statistics on flow.
                 2. invalid(2) -In the get operation, the invalid value 2 is returned.
                 Default: invalid(2)
                "
            ::= { hwDslamPppoeFlowStatisticsEntry 3 }

        hwDslamPppoeFlowStatisticsReceivePadi OBJECT-TYPE
            SYNTAX Unsigned32 (0..4294967295)
            MAX-ACCESS read-only
            STATUS current
            DESCRIPTION
                "Number of received PADI packets.
                "
            ::= { hwDslamPppoeFlowStatisticsEntry 4 }

        hwDslamPppoeFlowStatisticsReceivePado OBJECT-TYPE
            SYNTAX Unsigned32 (0..4294967295)
            MAX-ACCESS read-only
            STATUS current
            DESCRIPTION
                "Number of received PADO packets.
                "
            ::= { hwDslamPppoeFlowStatisticsEntry 5 }

        hwDslamPppoeFlowStatisticsReceivePadr OBJECT-TYPE
            SYNTAX Unsigned32 (0..4294967295)
            MAX-ACCESS read-only
            STATUS current
            DESCRIPTION
                "Number of received PADR packets.
                "
            ::= { hwDslamPppoeFlowStatisticsEntry 6 }

        hwDslamPppoeFlowStatisticsReceivePads OBJECT-TYPE
            SYNTAX Unsigned32 (0..4294967295)
            MAX-ACCESS read-only
            STATUS current
            DESCRIPTION
                "Number of received PADS packets.
                "
            ::= { hwDslamPppoeFlowStatisticsEntry 7 }

        hwDslamPppoeFlowStatisticsReceivePadt OBJECT-TYPE
            SYNTAX Unsigned32 (0..4294967295)
            MAX-ACCESS read-only
            STATUS current
            DESCRIPTION
                "Number of received PADT  packets.
                "
            ::= { hwDslamPppoeFlowStatisticsEntry 8 }

        hwDslamPppoeFlowStatisticsSendPadi OBJECT-TYPE
            SYNTAX Unsigned32 (0..4294967295)
            MAX-ACCESS read-only
            STATUS current
            DESCRIPTION
                "Number of sent PADI packets.
                "
            ::= { hwDslamPppoeFlowStatisticsEntry 9 }

        hwDslamPppoeFlowStatisticsSendPado OBJECT-TYPE
            SYNTAX Unsigned32 (0..4294967295)
            MAX-ACCESS read-only
            STATUS current
            DESCRIPTION
                "Number of sent PADO packets.
                "
            ::= { hwDslamPppoeFlowStatisticsEntry 10 }

        hwDslamPppoeFlowStatisticsSendPadr OBJECT-TYPE
            SYNTAX Unsigned32 (0..4294967295)
            MAX-ACCESS read-only
            STATUS current
            DESCRIPTION
                "Number of sent PADR packets.
                "
            ::= { hwDslamPppoeFlowStatisticsEntry 11 }

        hwDslamPppoeFlowStatisticsSendPads OBJECT-TYPE
            SYNTAX Unsigned32 (0..4294967295)
            MAX-ACCESS read-only
            STATUS current
            DESCRIPTION
                "Number of sent PADS packets.
                "
            ::= { hwDslamPppoeFlowStatisticsEntry 12 }

        hwDslamPppoeFlowStatisticsSendPadt OBJECT-TYPE
            SYNTAX Unsigned32 (0..4294967295)
            MAX-ACCESS read-only
            STATUS current
            DESCRIPTION
                "Number of sent PADT packets.
                "
            ::= { hwDslamPppoeFlowStatisticsEntry 13 }

        hwDslamPppoeFlowStatisticsTagTooLong OBJECT-TYPE
            SYNTAX Unsigned32 (0..4294967295)
            MAX-ACCESS read-only
            STATUS current
            DESCRIPTION
                "Number of packets exceed the maximum tag size.
                "
            ::= { hwDslamPppoeFlowStatisticsEntry 14 }

        hwDslamPppoeFlowStatisticsFrameTooLong OBJECT-TYPE
            SYNTAX Unsigned32 (0..4294967295)
            MAX-ACCESS read-only
            STATUS current
            DESCRIPTION
                "Number of packets exceed the maximum packet size.
                "
            ::= { hwDslamPppoeFlowStatisticsEntry 15 }

        hwDslamPppoeFlowStatisticsReceiveUntrusted OBJECT-TYPE
            SYNTAX Unsigned32 (0..4294967295)
            MAX-ACCESS read-only
            STATUS current
            DESCRIPTION
                "Number of received packets with untrusted tag.
                "
            ::= { hwDslamPppoeFlowStatisticsEntry 16 }

        hwDslamPppoeFlowStatisticsReceiveUnknownType OBJECT-TYPE
            SYNTAX Unsigned32 (0..4294967295)
            MAX-ACCESS read-only
            STATUS current
            DESCRIPTION
                "Number of received packets with unknown type.
                "
            ::= { hwDslamPppoeFlowStatisticsEntry 17 }

        hwDslamPppoeReverse OBJECT-TYPE
            SYNTAX INTEGER
                {
                enable(1),
                disable(2)
                }
            MAX-ACCESS read-write
            STATUS current
            DESCRIPTION
                "Indicates the status of the global reverse PPPoE packets switch.
                 Options:
                 1. enable(1)   -indicates the reverse PPPoE packets are forwarded
                 2. disable(2)  -indicates the reverse PPPoE packets are dropped
                 Default: disable(2)
                "
            ::= { hwPITP 25 }

        hwDslamRaioCableLabsSuboptionTable OBJECT-TYPE
            SYNTAX SEQUENCE OF HwDslamRaioCableLabsSuboptionEntry
            MAX-ACCESS not-accessible
            STATUS current
            DESCRIPTION
                "Used for setting and querying the RAIO CableLabs suboption.
                The index of this table is hwDslamRaioCableLabsSuboptionIndex.
                "
            ::= { hwPITP 26 }

        hwDslamRaioCableLabsSuboptionEntry OBJECT-TYPE
            SYNTAX HwDslamRaioCableLabsSuboptionEntry
            MAX-ACCESS not-accessible
            STATUS current
            DESCRIPTION
                "Used for setting and querying the RAIO CableLabs suboption.
                 The index of this entry is hwDslamRaioCableLabsSuboptionIndex.
                "
            INDEX { hwDslamRaioCableLabsSuboptionIndex }
            ::= { hwDslamRaioCableLabsSuboptionTable 1 }

        HwDslamRaioCableLabsSuboptionEntry ::=
            SEQUENCE {
                hwDslamRaioCableLabsSuboptionIndex
                    INTEGER,
                hwDslamRaioCableLabsSuboptionStatus
                    INTEGER,
                hwDslamRaioCableLabsSuboptionPara
                    OCTET STRING
             }

        hwDslamRaioCableLabsSuboptionIndex OBJECT-TYPE
            SYNTAX INTEGER {
                docsisversion(1)
                }
            MAX-ACCESS not-accessible
            STATUS current
            DESCRIPTION
                "Indicates the RAIO CableLabs suboption. This leaf is an index.
                 Options:
                 1. docsisversion(1)         -indicates the DOCSIS version suboption
                "
            ::= { hwDslamRaioCableLabsSuboptionEntry 1 }

        hwDslamRaioCableLabsSuboptionStatus OBJECT-TYPE
            SYNTAX INTEGER {
                enable(1),
                disable(2)
                }
            MAX-ACCESS read-write
            STATUS current
            DESCRIPTION
                "Indicates the status of the RAIO CableLabs suboption.
                 Options:
                 1. enable(1)  -indicates the RAIO CableLabs suboption is enable
                 2. disable(2) -indicates the RAIO CableLabs suboption is disable
                 Default: disable(2)
                "
            ::= { hwDslamRaioCableLabsSuboptionEntry 2 }

        hwDslamRaioCableLabsSuboptionPara OBJECT-TYPE
            SYNTAX OCTET STRING  (SIZE (0..255))
            MAX-ACCESS read-write
            STATUS current
            DESCRIPTION
                "Indicates the parameters of RAIO CableLabs suboption.
                 Range: a string of 0-255 characters.
                 When hwDslamRaioCableLabsSuboptionIndex is 1,
                 the first byte indicates the DOCSIS major version(ranges from 1 to 9),
                 and the second byte indicates the DOCSIS minor version(ranges from 0 to 9),
                 and other bytes are reserved, for example, 30 indicates
                 that the DOCSIS version is 3.0.
                "
            ::= { hwDslamRaioCableLabsSuboptionEntry 3 }

        hwDslamRAIOAncpAggCidFormatString OBJECT-TYPE
            SYNTAX OCTET STRING  (SIZE (0..127))
            MAX-ACCESS read-write
            STATUS current
            DESCRIPTION
                "Indicates the character string of the Access-Aggregation-Circuit-ID-ASCII format
                 and Access-Aggregation-Circuit-ID-Binary format.
 	         Range: a string of 0-127 characters."
            ::= { hwPITP 27 }

        hwDslamRaioDHCPv6Option17CableLabsSubSuboptionTable OBJECT-TYPE
            SYNTAX SEQUENCE OF HwDslamRaioDHCPv6Option17CableLabsSubSuboptionEntry
            MAX-ACCESS not-accessible
            STATUS current
            DESCRIPTION
                "Used for setting and querying the RAIO DHCPv6 Option17 CableLabs sub-suboption.
                 The index of this table is hwDslamRaioDHCPv6Option17CableLabsSuboptionIndex and
                 hwDslamRaioDHCPv6Option17CableLabsSubSuboptionIndex."
            ::= { hwPITP 28 }

        hwDslamRaioDHCPv6Option17CableLabsSubSuboptionEntry OBJECT-TYPE
            SYNTAX HwDslamRaioDHCPv6Option17CableLabsSubSuboptionEntry
            MAX-ACCESS not-accessible
            STATUS current
            DESCRIPTION
                "Used for setting and querying the RAIO DHCPv6 Option17 CableLabs sub-suboption.
                 The index of this entry is hwDslamRaioDHCPv6Option17CableLabsSuboptionIndex and
                 hwDslamRaioDHCPv6Option17CableLabsSubSuboptionIndex."
            INDEX { hwDslamRaioDHCPv6Option17CableLabsSuboptionIndex, hwDslamRaioDHCPv6Option17CableLabsSubSuboptionIndex }
            ::= { hwDslamRaioDHCPv6Option17CableLabsSubSuboptionTable 1 }

        HwDslamRaioDHCPv6Option17CableLabsSubSuboptionEntry ::=
            SEQUENCE {
                hwDslamRaioDHCPv6Option17CableLabsSuboptionIndex
                    Integer32,
                hwDslamRaioDHCPv6Option17CableLabsSubSuboptionIndex
                    Integer32,
                hwDslamRaioDHCPv6Option17CableLabsSubSuboptionStatus
                    INTEGER,
                hwDslamRaioDHCPv6Option17CableLabsSubSuboptionPara
                    OCTET STRING
             }

        hwDslamRaioDHCPv6Option17CableLabsSuboptionIndex OBJECT-TYPE
            SYNTAX Integer32 (0..65535)
            MAX-ACCESS not-accessible
            STATUS current
            DESCRIPTION
                "Indicates the RAIO DHCPv6 Option17 CableLabs suboption. This leaf is an index.
                 Range: 0-65535
                "
            ::= { hwDslamRaioDHCPv6Option17CableLabsSubSuboptionEntry 1 }

        hwDslamRaioDHCPv6Option17CableLabsSubSuboptionIndex OBJECT-TYPE
            SYNTAX Integer32 (0..65535)
            MAX-ACCESS not-accessible
            STATUS current
            DESCRIPTION
                "Indicates the RAIO DHCPv6 Option17 CableLabs sub-suboption. This leaf is an index.
                 Range: 0-65535
                "
            ::= { hwDslamRaioDHCPv6Option17CableLabsSubSuboptionEntry 2 }

        hwDslamRaioDHCPv6Option17CableLabsSubSuboptionStatus OBJECT-TYPE
            SYNTAX INTEGER {
                enable(1),
                disable(2)
                }
            MAX-ACCESS read-write
            STATUS current
            DESCRIPTION
                "Indicates the status of the RAIO DHCPv6 Option17 CableLabs sub-suboption.
                 Options:
                 1. enable(1)  -indicates the RAIO DHCPv6 Option17 CableLabs sub-suboption is enable
                 2. disable(2) -indicates the RAIO DHCPv6 Option17 CableLabs sub-suboption is disable
                 Default: disable(2)
                "
            ::= { hwDslamRaioDHCPv6Option17CableLabsSubSuboptionEntry 3 }

        hwDslamRaioDHCPv6Option17CableLabsSubSuboptionPara OBJECT-TYPE
            SYNTAX OCTET STRING  (SIZE (0..255))
            MAX-ACCESS read-write
            STATUS current
            DESCRIPTION
                "Indicates the parameters of RAIO DHCPv6 Option17 CableLabs sub-suboption.
                 Range: a string of 0-255 characters.
                 When hwDslamRaioDHCPv6Option17CableLabsSuboptionIndex is 1025, and
                 hwDslamRaioDHCPv6Option17CableLabsSubSuboptionIndex is 1,
                 the first byte indicates the DOCSIS major version(ranges from 1 to 9),
                 and the second byte indicates the DOCSIS minor version(ranges from 0 to 9),
                 and other bytes are reserved, for example, 30 indicates
                 that the DOCSIS version is 3.0.
                "
            ::= { hwDslamRaioDHCPv6Option17CableLabsSubSuboptionEntry 4 }

        hwDslamPITPTransparentUserVlanType OBJECT-TYPE
            SYNTAX   BITS
            {
             untag(0),
             singleTag(1),
             multiTag(2)
            }
            MAX-ACCESS read-write
            STATUS       current
            DESCRIPTION
            "
            Indicates the user VLAN based on which PITP pmode is transparently transmitted.
            Options:
            1. untag(0)            -indicates that the user packet does not contain VLANs
            2. singleTag(1)        -indicates that the user packet contains a single VLAN
            3. multiTag(2)         -indicates that the user packet contains multiple VLANs
            When singleTag is 0, set hwDslamPITPTransparentSingleUserVlanList to a null character string.
            When singleTag is 1, set hwDslamPITPTransparentSingleUserVlanList to a valid character string.
            "
            ::= { hwPITP 29 }

        hwDslamPITPTransparentSingleUserVlanList OBJECT-TYPE
            SYNTAX       OCTET STRING (SIZE (0..255))
            MAX-ACCESS read-write
            STATUS       current
            DESCRIPTION
            "
             Indicates the list of user single VLANs contained in the packets whose PITP pmode is transparently transmitted.
             VLAN ranges from 0 to 4095. The VLAN list is a character string consisting of digits (0-9) or digits and VLAN segments.
             Digits and VLAN segments are separated by a comma, for example, 2,200-300.
             For example:
             1.To set user-side VLAN status to singleTag, VLAN list to 2,100-300, do as follows:
               singleTag(1) is set to 1 in hwDslamPITPTransparentUserVlanType, hwDslamPITPTransparentSingleUserVlanList:2,100-300
             2.To set user-side VLAN status to untag and multiTag, do as follows:
               untag(0) and multiTag(2) are set to 1 in hwDslamPITPTransparentUserVlanType, hwDslamPITPTransparentSingleUserVlanList is a null character string.
            "
            ::= { hwPITP 30 }

        hwDslamRaioSuboptionActualDataRateType OBJECT-TYPE
            SYNTAX INTEGER
                {
                actualDataRate(1),
                actualNetDataRate(2)
                }
            MAX-ACCESS read-write
            STATUS current
            DESCRIPTION
                "Indicates the actual data rate type of RAIO suboption.
                 Options:
                 1. actualDataRate(1)    -indicates the RAIO suboption is actual data rate. The meaning of actualDataRate is defined in ITU-T G.997.1, paragraph 7.5.2.1 actual data rate.
                 2. actualNetDataRate(2) -indicates the RAIO suboption is actual net data rate. The meaning of actualNetDataRate is defined in ITU-T G.997.1, paragraph 7.5.2.8 actual net data rate (ACTNDR).
                 Default: actualDataRate(1)
                "
            ::= { hwPITP 31 }

        hwDslamRadiusNasPortIdRAIOMode OBJECT-TYPE
            SYNTAX INTEGER
                {
                common(1),
                xdslPortRate(2),
                cntel(3),
                ti(4),
                neuf(5),
                portUserLabel(6),
                bt(7),
                servicePortUserLabel(8),
                dslForumDefault(9),
                brt(10),
                userDefined(11),
                ft(12),
                cntelXpon(13),
                tm(14),
                bbf(15),
                vnpt(16),
                true(17)
                }
            MAX-ACCESS   read-write
            STATUS       current
            DESCRIPTION
                "Indicates the RAIO mode of RADIUS NAS-Port-Id.
                 Options:
                 1. common(1)               -indicates the RAIO mode of RADIUS NAS-Port-Id is common
                 2. xdslPortRate(2)         -indicates the RAIO mode of RADIUS NAS-Port-Id is Xdsl port rate
                 3. cntel(3)                -indicates the RAIO mode of RADIUS NAS-Port-Id is Xdsl add BRAS
                 4. ti(4)                   -indicates the RAIO mode of RADIUS NAS-Port-Id is TI Add Dhcp && PITP Tag
                 5. neuf(5)                 -indicates the RAIO mode of RADIUS NAS-Port-Id is neuf
                 6. portUserLabel(6)        -indicates the RAIO mode of RADIUS NAS-Port-Id is portUserLabel
                 7. bt(7)                   -indicates the RAIO mode of RADIUS NAS-Port-Id is bt
                 8. servicePortUserLabel(8) -indicates the RAIO mode of RADIUS NAS-Port-Id is servicePortUserLabel
                 9. dslForumDefault(9)      -indicates the RAIO mode of RADIUS NAS-Port-Id is dslForumDefault
                 10. brt(10)                -indicates the RAIO mode of RADIUS NAS-Port-Id is brt
                 11. userDefined(11)        -indicates the RAIO mode of RADIUS NAS-Port-Id is user defined
                 12. ft(12)                 -indicates the RAIO mode of RADIUS NAS-Port-Id is ft
                 13. cntelXpon(13)          -indicates the RAIO mode of RADIUS NAS-Port-Id is Xpon add BRAS
                 14. tm(14)                 -indicates the RAIO mode of RADIUS NAS-Port-Id is tm
                 15. bbf(15)                -indicates the RAIO mode of RADIUS NAS-Port-Id is bbf
                 16. vnpt(16)               -indicates the RAIO mode of RADIUS NAS-Port-Id is vnpt
                 17. true(17)               -indicates the RAIO mode of RADIUS NAS-Port-Id is true
                 Default: common(1)
                 Restrictions:
                 bt(7) is not supported.
                 When this leaf is set to userDefined(11), the specific RAIO format must be configured through hwDslamRAIOFormatTable.
                "
            ::= { hwPITP 32}

        hwDslamRaioSuboptionFastReport OBJECT-TYPE
            SYNTAX INTEGER
                {
                 disable(1),
                 enable(2)
                }
            MAX-ACCESS   read-write
            STATUS       current
            DESCRIPTION
                "Indicates that fast sub-option report by DHCP/DHCPv6/PPPoE+ sub-option 0x81/0x82/0x8C/0x8E is enabled or disabled globally.
                 Options:
                 1. disable(1)             - Indicates that fast sub-option report by DHCP/DHCPv6/PPPoE+ sub-option 0x81/0x82/0x8C/0x8E is disabled globally.
                 2. enable(2)              - Indicates that fast sub-option report by DHCP/DHCPv6/PPPoE+ sub-option 0x81/0x82/0x8C/0x8E is enabled globally.
                 Default: disable(1)
                "
            ::= { hwPITP 33 }

    END
