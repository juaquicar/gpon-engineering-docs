-- ============================================================================
-- Copyright (C) 2016 by  HUAWEI TECHNOLOGIES. All rights reserved.
-- Description: Huawei bulk performance statistics MIB object includes bulk 
--              performance statistics file configuration, FTP client management, 
--              and threshold alarm configuration and management.
--              The NMS creates a performance statistics file, statistical object,
--              and statistical content through the MIB interface, and starts the performance statistics.
--              The host collects the content of the statistical object,
--              creates a file of the statistical content at a fixed interval for collecting statistics, 
--              and then reports a trap to the NMS for it to obtain data. 
--              The NMS can also back up the statistics file to the NMS server through the MIB interface.
--              A threshold needs to be set for monitoring the performance data. 
--              When the data exceeds the threshold, an alarm indicating that the data exceeds the 
--              threshold is generated and reported to the NMS automatically.
--              The information item that needs to be collected can be configured through the NMS. 
--              The collection task can be started or stopped through the NMS. 
--              The item that needs to be collected can be backed up through the NMS.
-- Reference:  
-- Version: V1.74
-- ============================================================================

    HUAWEI-BULKSTATISTICS-MIB DEFINITIONS ::= BEGIN
        IMPORTS
            huaweiUtility, hwCfgInfoCollect
                FROM HUAWEI-MIB
                IpAddress, Integer32, Unsigned32, Counter64, 
            OBJECT-TYPE, MODULE-IDENTITY, OBJECT-IDENTITY, NOTIFICATION-TYPE          
                FROM SNMPv2-SMI                 
            RowStatus, TruthValue, DisplayString
                FROM SNMPv2-TC
            hwLoadBackupResult
                FROM HUAWEI-LOAD-BACKUP-MIB;
        
        hwBulkStatistics MODULE-IDENTITY
            LAST-UPDATED "201603300000Z"
            ORGANIZATION "Huawei Technologies Co.,Ltd."
            CONTACT-INFO 
                   "Huawei Industrial Base
                    Bantian, Longgang
                    Shenzhen 518129
                    People's Republic of China
                    Website: http://www.huawei.com
                    Email: support@huawei.com
                   "
            DESCRIPTION
                "
                Huawei bulk performance statistics MIB object includes bulk 
                performance statistics file configuration, FTP client management, 
                and threshold alarm configuration and management.
                The NMS creates a performance statistics file, statistical object,
                and statistical content through the MIB interface, and starts the performance statistics.
                The host collects the content of the statistical object,
                creates a file of the statistical content at a fixed interval for collecting statistics, 
                and then reports a trap to the NMS for it to obtain data. 
                The NMS can also back up the statistics file to the NMS server through the MIB interface.
                A threshold needs to be set for monitoring the performance data. 
                When the data exceeds the threshold, an alarm indicating that the data exceeds the 
                threshold is generated and reported to the NMS automatically.
                The information item that needs to be collected can be configured through the NMS. 
                The collection task can be started or stopped through the NMS. 
                The item that needs to be collected can be backed up through the NMS.              
                "
 
--  Revision history
	     REVISION	 "201603300000Z"	
             DESCRIPTION "V1.74, Modify the description of hwBatchQueryParameter" 

	     REVISION	 "201601270000Z"	
             DESCRIPTION "V1.73, Add the following enums of the hwBulkObjectCapItemList:
	            pmpMaxDsSNR(970),
                    pmpMinDsSNR(971),
                    pmpPrimaryDs(972),
                    pmpPrimaryUs(973),
                    pmpRxByte(974),
                    pmpTxByte(975),
                    pmpSuccessReg(976),	
                    pmpFailReg(977),
                    pmpRepeatReg(978),
                    pmpStationMaintenance(979),
                    pmpStationMaintenanceMiss(980),
                    pmpStationMaintainConMiss(981),
                    pmpPowerAdjust(982),
                    pmpSeverelyPowerAdjust(983),
                    pmpUnstableConnection(984),
                    pmpMaxUsSNR(985),
                    pmpMinUsSNR(986)" 

             REVISION	 "201511300000Z"	
             DESCRIPTION "V1.72, Delete BITS from HUAWEI-BULKSTATISTICS-MIB DEFINITIONS" 
                        
             REVISION	 "201511230000Z"	
             DESCRIPTION "V1.71, Added MIB nodes to support the incremental collect information" 
             
             REVISION	 "201509280000Z"	
             DESCRIPTION "V1.70, Modify the description of hwBatchQueryParameter hwBatchQueryParameter" 

             REVISION	 "201506240000Z"	 
             DESCRIPTION "V1.69,  Add the following enums of the hwBulkObjectCapItemList:
                     pmpSigAttnUs(92),
                     pmpSigAttnDs(93),
                     pmpLineAttnPbUs(94),
                     pmpLineAttnPbDs(95), 
                     pmpSignalAttnPbUs(96),
                     pmpSignalAttnPbDs(97), 
                     pmpSnrMarginPbUs(98),
                     pmpSnrmarginPbDs(99),"

             REVISION	 "201504250000Z"	  
             DESCRIPTION "V1.68, Modify the description of hwBulkFileObjectMainType:
                               6           160         G.fast port                                                                 
                               6           161         G.fast Xlin-data
                               6           162         G.fast Segment
                          Modify the follow description of the hwBulkFileObjectSubType:
                               6           160         G.fast port                                                                 
                               6           161         G.fast Xlin-data
                               6           162         G.fast Segment."

             REVISION	 "201504030000Z"	 
             DESCRIPTION "V1.67, Modify the description of following MIB nodes:
                          hwBatchQueryType,hwBatchQueryCurrentType and hwBatchQueryParameter"
			  
             REVISION	 "201503310000Z"	 
             DESCRIPTION "V1.66, Modify the example description of hwBatchQueryParameter"
                          
             REVISION	 "201503260000Z"	 
             DESCRIPTION "V1.65, Modify the description of following MIB nodes:
                          hwBatchQueryType,hwBatchQueryCurrentType and hwBatchQueryParameter"
             
             REVISION	 "201503090000Z"	 
             DESCRIPTION "V1.64, Add the following enums of the hwBulkObjectCapItemList:
                          pmp-cm-status(950),
                          pmp-cm-us-width(951),
                          pmp-cm-us-frequency(952),
                          pmp-cm-us-cmts-Eqd(953),
                          pmp-cm-us-act-Eqd(954),
                          pmp-cm-us-snr(955),
                          pmp-cm-us-tx-power(956),
                          pmp-cm-us-goodcode(957),
                          pmp-cm-us-corrected(958),
                          pmp-cm-us-uncorrected(959),
                          pmp-cm-us-ccer(960),
                          pmp-cm-us-ucer(961),
                          pmp-cm-ds-frequency(962),
                          pmp-cm-ds-snr(963),
                          pmp-cm-ds-rx-power(964),
                          pmp-cm-ds-ccer(965),
                          pmp-cm-ds-ucer(966),
                          pmp-cm-ds-goodcode(967),
                          pmp-cm-ds-corrected(968),
                          pmp-cm-ds-uncorrected(969),
                          Add the follow description of the hwBulkFileObjectMainType:
                              197         7          Cable Modem                     
                          Add the follow description of the hwBulkFileObjectSubType:
                              197         7          Cable Modem."       
                              
             REVISION    "201502090000Z"      
             DESCRIPTION "V1.63, Add the following description of the hwBulkFileObjectMainType:    
                               191         7           GPON ONU Wifi Statistics                                                                
                               191         8           GPON ONU Wifi STA Info  
                               191         9           GPON ONU Wifi Neighbor AP info
                               192         7           EPON ONU Wifi Package Statistics
                               192         8           EPON ONU Wifi STA Info 
                               192         9           EPON ONU Wifi Neighbor AP info
                          Add the following description of the hwBulkFileObjectSubType:
                               191         7           GPON ONU Wifi Statistics
                               191         8           GPON ONU Wifi STA Info 
                               191         9           GPON ONU Wifi Neighbor AP info                                                               
                               192         7           EPON ONU Wifi Statistics
                               192         8           EPON ONU Wifi STA Info 
                               192         9           EPON ONU Wifi Neighbor AP info 
                          Modified the description of the hwBulkFileObjectMainType:
                               182         1           XPON ONT Optical Module Dynamic Info                                              
                               182         2           XPON UNI Optical Module Dynamic Info                                              
                               182         3           EPON ONT Optical Module Dynamic Info                                              
                               182         4           EPON UNI Optical Module Dynamic Info                                              
                               191         1           GPON UNI PORT Statistics                                                          
                               191         2           GPON ONU Statistics                                                                                                           
                               191         15          XPON ONT ETH PORT Statistics                                                      
                               192         1           EPON UNI PORT Statistics                                                         
                               192         2           EPON ONU Statistics                                                                                                                 
                               192         11          EPON ONT ETH PORT Statistics   
                          Add the following enums of the hwBulkObjectCapItemList: 
                          pmpXponOnuWifiTxTotalPackets(871),
                          pmpXponOnuWifiTxErrPackets(872),
                          pmpXponOnuWifiTxDiscardPackets(873),
                          pmpXponOnuWifiRxTotalPackets(874),
                          pmpXponOnuWifiRxErrPackets(875),
                          pmpXponOnuWifiRxDiscardPackets(876),
                          pmpXponOnuWifiTransQualityLevel(877),
                          pmpXponOnuWifiDsRate(878), 
                          pmpXponOnuWifiUsRate(879),
                          pmpXponOnuWifiRSSI(880),
                          pmpXponOnuWifiSNR(881),
                          pmpXponOnuWifiSignalQualityLevel(882),
                          pmpXponOnuWifiIneighborAP(883),
                          pmpXponOnuWifiAPFactor(884). 
                             
                         Add the following description of the hwBulkFileConditionTable and hwBulkFileConditionEntry: 
                         Statistical conditions can be issued in hexadecimal notation or using a character string.  
                         Changed the range of hwBulkFileCollectCondition from (1..254) to (1..200).
			 "                          
	     
	     REVISION    "201501050000Z"      
             DESCRIPTION "V1.62, added hwBulkFileCollectCondition and hwBulkFileCollectRowStatus object in 
                          hwBulkFileConditionTable.added hwFTPClientNum object in hwFTPClientTable. added 
                          hwFTPClientMaxNum object"
             
             REVISION    "201412180000Z"      
             DESCRIPTION "V1.61, Correct the node hwBulkObjectCapItemRowStatus read-write to read-create."
             REVISION    "201411110000Z"  
	         
             DESCRIPTION "V1.60, Add the follow description of the hwBulkFileObjectMainType:
                               6           176         G.fast port                                                                 
                               6           181         G.fast Xlin-data
                               7           101         G.fast Segment
                          Add the follow description of the hwBulkFileObjectSubType:
                               6           176         G.fast port                                                                 
                               6           181         G.fast Xlin-data
                               7           101         G.fast Segment."
             
             REVISION    "201408250000Z"      
             DESCRIPTION "V1.59, modified the description of hwBulkBackupSuccessCommonTrap."

             REVISION    "201406300000Z"      
             DESCRIPTION "V1.58, 1. removed all hyphens (-) from enumerated values of hwBulkFileColNumMode. 
                                 2. removed all hyphens (-) from enumerated values of hwBulkObjectCapItemList.
                                 3. removed all hyphens (-) from enumerated values of hwBulkFileObjectMainType.
                                 4. modified 'MAX-ACCESS not-accessible' to 'MAX-ACCESS accessible-for-notify' of hwBulkSaveFileIndex.
                                 5. removed all hyphens (-) from enumerated values of hwBulkFileNameRule.
                                 6. modified 'MAX-ACCESS not-accessible' to 'MAX-ACCESS accessible-for-notify' of hwFTPClientIndex.
                                 7. removed all hyphens (-) from enumerated values of hwDefineMontype.
                                 8. modified 'MAX-ACCESS not-accessible' to 'MAX-ACCESS accessible-for-notify' of hwBatchQuerySn."

             REVISION    "201405260000Z"      
             DESCRIPTION "V1.57, Add the Object hwWaitfetchTimeout."
            
             REVISION    "201403280000Z"      
             DESCRIPTION "V1.56, Add the following enums of the hwBulkObjectCapItemList: pmp-gain-al-us(215), pmp-gain-al-ds(216)."
            
             REVISION    "201403030000Z"      
             DESCRIPTION "V1.55, modified the description of hwBulkFileTable.
                                 modified the description of hwBulkFileEntry.
                                 modified the description of hwBulkFileObjectMainType.
                                 modified the description of hwBulkFileObjectSubType.
                                 modified the description of hwBulkFileNameRule."
            
             REVISION    "201401160000Z"      
             DESCRIPTION "V1.54, Add the following enums of the hwBulkObjectCapItemList: pmp-rtxactuaeftr-ds(90), pmp-rtxactuaeftr-us(91)."
            
             REVISION    "201311190000Z"      
             DESCRIPTION "V1.53, Modify description to the hwBatchQueryParameter, add description to the hwBatchQueryReturnList."
            
             REVISION    "201309040000Z"      
             DESCRIPTION "V1.52, Change the maximum length of hwCollectOID from 128 to 127."
                        
             REVISION    "201306270000Z"      
             DESCRIPTION "V1.51, Add the following enums of the hwBulkObjectCapItemList:
                          pmp-rtxleftr-ds(84), pmp-rtxleftr-us(85), pmp-rtxefb-ds(86), pmp-rtxefb-us(87),
                          pmp-rtxmineftr-ds(88), pmp-rtxmineftr-us(89)."

             REVISION    "201204160000Z"  
             DESCRIPTION "V1.50, Modified the description of hwBulkFileObjectMainType,hwBulkFileObjectSubType. 
                          Add the following enums of the hwBulkObjectCapItemList:      
                          pmp-xlin-data(261)."

             REVISION    "201301210000Z"
             DESCRIPTION "V1.49, Add the following enums of the hwBulkObjectCapItemList:
                          pmp-epon-uni-optics-10g-tx-power(780),pmp-epon-uni-laser-10g-bias-curr(781),
                          pmp-epon-nni-peer-optics-tx-power(800),
                          pmp-epon-uni-1g-channel-us-rate(851),
                          pmp-epon-uni-1g-channel-err-pkt-ratio(852),
                          pmp-epon-uni-1g-channel-us-bytes(853),
                          pmp-epon-uni-1g-channel-ds-bytes(854),
                          pmp-epon-uni-1g-channel-ds-rate(855),
                          pmp-epon-uni-1g-channel-us-packets(856),
                          pmp-epon-uni-1g-channel-ds-packets(857),
                          pmp-epon-uni-1g-channel-us-error-packets(858),
                          pmp-epon-uni-1g-channel-us-discard-packets(859),
                          pmp-epon-uni-1g-channel-ds-discard-packets(860),
                          pmp-epon-uni-10g-channel-us-rate(861),
                          pmp-epon-uni-10g-channel-err-pkt-ratio(862),
                          pmp-epon-uni-10g-channel-us-bytes(863),
                          pmp-epon-uni-10g-channel-ds-bytes(864),
                          pmp-epon-uni-10g-channel-ds-rate(865),
                          pmp-epon-uni-10g-channel-us-packets(866),
                          pmp-epon-uni-10g-channel-ds-packets(867),
                          pmp-epon-uni-10g-channel-us-error-packets(868),
                          pmp-epon-uni-10g-channel-us-discard-packets(869),
                          pmp-epon-uni-10g-channel-ds-discard-packets(870).
                          Modify the enum name of pmp-xpon-uni-laser-bias-curr to pmp-xpon-uni-optics-bias-curr,  
                          Modify the enum name of pmp-epon-uni-laser-bias-curr to pmp-epon-uni-optics-bias-curr, 
                          Modify the enum name of pmp-xpon-nni-laser-bias-curr to pmp-xpon-nni-optics-bias-curr, 
                          Modify the enum name of pmp-epon-nni-laser-bias-curr to pmp-epon-nni-optics-bias-curr, 
                          Modify the enum name of pmp-epon-uni-laser-10g-bias-curr to pmp-epon-uni-optics-10g-bias-curr. 
                          "
 
             REVISION    "201212200000Z"
             DESCRIPTION "V1.48, Add the following enums of the hwBulkObjectCapItemList:
                          single-ended-framelossratio-near-max(750),
                          single-ended-framelossratio-near-min(751),
                          single-ended-framelossratio-near-average(752),
                          single-ended-framelossratio-far-max(753),
                          single-ended-framelossratio-far-min(754),
                          single-ended-framelossratio-far-average(755),
                          two-way-delay-max(756),
                          two-way-delay-min(757),
                          two-way-delay-average(758),
                          two-way-jitter-max(759),
                          two-way-jitter-min(760),
                          two-way-jitter-average(761),
                          one-way-delay-far-max(762),
                          one-way-delay-far-min(763),
                          one-way-delay-far-average(764),
                          one-way-jitter-far-max(765),
                          one-way-jitter-far-min(766),
                          one-way-jitter-far-average(767),
                          one-way-delay-near-max(768),
                          one-way-delay-near-min(769),
                          one-way-delay-near-average(770),
                          one-way-jitter-near-max(771),
                          one-way-jitter-near-min(772),
                          one-way-jitter-near-average(773)
                          Add the follow description of the hwBulkFileObjectMainType:
                          200         0           Y1731 PM
                          Add the follow description of the hwBulkFileObjectSubType:
                          200         0           Y1731 PM" 
                    
             REVISION    "201212030000Z"
             DESCRIPTION "V1.47, Add the following enums of the hwBulkObjectCapItemList:
                          pmp-fec-unevt-ner-us(63),
                          pmp-fec-unevt-far-ds(64),
                          pmp-en-blk-ner-us(65),   
                          pmp-en-blk-far-ds(66),   
                          pmp-rtx-cw-ner-us(67),   
                          pmp-rtx-cw-far-ds(68),   
                          pmp-rtx-ccw-ner-us(69),  
                          pmp-rtx-ccw-far-ds(70),  
                          pmp-rtx-unccw-ner-us(71),
                          pmp-rtx-unccw-far-ds(72),
                          pmp-xtur-vds-num(73),    
                          pmp-xtur-ver-num(74),    
                          pmp-act-delay-us(75),    
                          pmp-act-delay-ds(76)
                          pmp-adsl-extprf-name(77),    
                          pmp-band-plan(78),       
                          pmp-act-psd-ds(79),      
                          pmp-act-psd-us(80),      
                          pmp-xtur-svd-num(81),    
                          pmp-port-state(82),      
                          pmp-cpe-type(83), 
                          pmp-txpsd-us(211),  
                          pmp-txpsd-ds(212),  
                          pmp-qln-vector-us(213),  
                          pmp-qln-vector-ds(214)"  
                              
             REVISION    "201210120000Z"
             DESCRIPTION "V1.46, Add the enum of the hwBatchQueryType:macinfo(4),
                          add the enum of the hwBatchQueryCurrentType:macinfo(4)."
                        
             REVISION    "201207180000Z"
             DESCRIPTION "V1.45, Add the following enums of the hwBulkObjectCapItemList:
                          pmp-elem1-support(61),
                          pmp-interval-valid(62),
                          pmp-eth-interval-valid(348),
                          modified the following enums of the hwBulkObjectCapItemList:
                          pmp-tran-green-send-discard-eth-number(308),
                          pmp-tran-yellow-send-discard-eth-number(311),
                          pmp-xpon-uni-optics-temp(363),  
                          pmp-xpon-uni-laser-bias-curr(364),
                          pmp-xpon-uni-optics-volt(365),
                          pmp-xpon-uni-optics-tx-power(366),
                          pmp-xpon-nni-optics-temp(394),
                          pmp-xpon-nni-laser-bias-curr(395),
                          pmp-xpon-nni-optics-volt(396),
                          pmp-xpon-nni-optics-tx-power(397),
                          pmp-xpon-nni-optics-rx-power(398),
                          pmp-xpon-olt-nni-optics-rx-power(399),
                          pmp-xpon-onu-eth-port-us-rate(424),
                          pmp-xpon-onu-eth-port-ds-rate(425),  
                          pmp-xpon-onu-eth-port-rx-total(426),
                          pmp-xpon-onu-eth-port-rx-unic(427),
                          pmp-xpon-onu-eth-port-rx-brdc(428),
                          pmp-xpon-onu-eth-port-rx-mltc(429),
                          pmp-xpon-onu-eth-port-tx-total(430),
                          pmp-xpon-onu-eth-port-tx-unic(431),
                          pmp-xpon-onu-eth-port-tx-brdc(432),
                          pmp-xpon-onu-eth-port-tx-mltc(433),
                          pmp-xpon-onu-eth-port-rx-octs(434),
                          pmp-xpon-onu-eth-port-tx-octs(435),
                          pmp-xpon-onu-eth-port-rx-error-packets(436)."
                        
             REVISION    "201206190000Z"
             DESCRIPTION "V1.44,  1.Change the maximum length of hwCollectTableName from 64 to 63.
                                  2.Modify the error for the syntax."
            
             REVISION    "201205080000Z"
             DESCRIPTION "V1.43, Add the following enums of the hwBulkObjectCapItemList:
                          pmp-gpon-nni-recv-error-packets(700),
                          pmp-gpon-nni-tran-packets(701),
                          pmp-gpon-nni-recv-packets(702),
                          pmp-epon-nni-recv-error-packets(730),
                          pmp-epon-nni-tran-packets(731),
                          pmp-epon-nni-recv-packets(732),
                          pmp-epon-uni-tran-packets(388),
                          pmp-epon-uni-recv-packets(389),
                          Modified the enum pmp-lols-fer-us(19) of the hwBulkObjectCapItemList."
            
             REVISION    "201204250000Z"
             DESCRIPTION "V1.42,  1.add the description to the hwCollectTableName."
                                 
             REVISION    "201204170000Z"
             DESCRIPTION "V1.41,  1.Change the maximum length of hwCollectTableName from 31 to 64.
                                  2.Change the maximum length of hwCollectTableInfo from 255 to 510."
                        
             REVISION   "201203290000Z"
             DESCRIPTION "V1.40, The description of hwTrapAutoBackupFileName is modified.
                          Add the following enum of the hwBulkObjectCapItemList:
                          pmp-pcb-ds(57),
                          pmp-modu-mode(58),
                          pmp-pbo-ds(59),
                          pmp-pbo-us(60)."
            
             REVISION    "201203150000Z"
             DESCRIPTION "V1.39,  Modified the following type of the hwBatchQueryCurrentType and hwBatchQueryType from INTEGER to integer32,
                          and add the description of ontLearnedMac(3)."

             REVISION    "201203060000Z"  
             DESCRIPTION "V1.38, Add the following enums of the hwBulkObjectCapItemList:      
                          board-cpu-occupation(600),      
                          board-temperature(601),      
                          board-dsp-occupation(602),      
                          board-mgif-failed-num(650)." 

             REVISION    "201201300000Z"
             DESCRIPTION "V1.37, Add standard trap nodes:
                          hwTrapAutoBackupFileName,hwBulkAutobackupSuccessTrap and hwBulkAutobackupFailTrap.                         
                          Add the following enums of the hwBulkFileFormat:bulkASCIIWithZipFile(3).
                          Changed the name of bulkASCII to bulkASCIIWithDeflate(2)"
                         
             REVISION    "201201290000Z"
             DESCRIPTION "V1.36, Modified the description of hwBulkFileObjectMainType,hwBulkFileObjectSubType.
                          Add the following enums of the hwBulkObjectCapItemList:
                          270~271,312~347,373,384~387,390~391,400~407,416~418,434~436,450~452,500~508,520~524"
                         
             REVISION    "201201170000Z"
             DESCRIPTION "V1.35, Add the following enums of the hwBulkObjectCapItemList:
                          pmp-resyn-ratio(56)."
             
             REVISION    "201111070000Z"
             DESCRIPTION "V1.34, Modified the description of hwBulkFileObjectMainType,hwBulkFileObjectSubType and hwFTPDestFileName.
                          Add the following enums of the hwBulkObjectCapItemList:
                          pmp-gpon-olt-nni-optics-rx-power(399),
                          pmp-epon-olt-nni-optics-rx-power(415)"

             REVISION    "201110210000Z"
             DESCRIPTION "V1.33, Add the Object hwBulkFileNameRule,modified the value list of hwBulkFileCollectInterval."

             REVISION    "201109010000Z"
             DESCRIPTION "V1.32, Add the Object hwBatchQueryFile."
 
             REVISION    "201108230000Z"
             DESCRIPTION "V1.31, Add the following enums of the hwBulkObjectCapItemList:
                          pmp-rtxused-us(54),
                          pmp-rtxused-ds(55)."
                         
             REVISION    "201107100000Z"
             DESCRIPTION "V1.30, Add the following enums of the hwBulkObjectCapItemList:
                          pmp-tran-discard-eth-port-packets(305),
                          pmp-tran-green-send-eth-port-octs(306),
                          pmp-tran-green-send-eth-port-number(307),
                          pmp-tran-green-send-discard-eth-numbe(308),
                          pmp-tran-yellow-send-eth-port-octs(309),
                          pmp-tran-yellow-send-eth-port-number(310),
                          pmp-tran-yellow-send-discard-eth-numbe(311),
                          pmp-gpon-uni-tx-discard-packets(372),
                          pmp-epon-uni-tx-discard-packets(383)."
            
             REVISION    "201106300000Z"
             DESCRIPTION "V1.29, modified the description of this MIB"

             REVISION    "201105270000Z"
             DESCRIPTION "V1.28, Add the following enums of the hwBulkObjectCapItemList:
                          pmp-inminpeq-us(48),pmp-inminpeq-ds(49),pmp-inmiat-us(50),pmp-inmiat-ds(51),pmp-inmme-us(52),pmp-inmme-ds(53),
                          pmp-gpon-uni-tran-octs(367),pmp-gpon-uni-recv-octs(368),pmp-gpon-uni-tran-packets(369),pmp-gpon-uni-recv-packets(370),pmp-gpon-uni-discard-packets(371),"
            
             REVISION    "201105130000Z"
             DESCRIPTION "V1.27, modified the description of this MIB"

             REVISION    "201102190000Z"
             DESCRIPTION "V1.26, Added MIB nodes to support the statistics of SPUA."

 
             REVISION    "201011090000Z"
             DESCRIPTION "V1.25, The description of this MIB is modified according to the tool."
 
             REVISION    "201008250000Z"
             DESCRIPTION "V1.24, modified the contact-info and the revision history. Modified the description of leaves.
                          Modified the description of hwBulkFileObjectMainType and hwBulkFileObjectSubType 
                          and add the values of the hwBulkObjectCapItemList for PON product."
                  
             REVISION    "201006120000Z"
             DESCRIPTION "V1.23, modified and supplemented the description in the object. 
                          Abandoned object hwBulkAndTCARelationship and all the objects in hwDefineTCATable and hwBackupCollectInfoParaTable.
                          Changed the name of hwBulkBackupSucesComnTrap to hwBulkBackupSuccessCommonTrap.
                          Changed the name of hwBulkFileFailAlmTrap to hwBulkFileFailAlarmTrap.
                          Changed the name of hwBulkBackupStartComnTrap to hwBulkBackupStartCommonTrap."
                                                
             REVISION    "201003030000Z"
             DESCRIPTION "V1.22, implemented DT requirements and changed the syntax and semantics of SIMPLETEST."
            
             REVISION    "201002250000Z"
             DESCRIPTION "V1.21, modified the description of hwBulkFileObjectMainType and hwBulkFileObjectSubType."
            
             REVISION    "201002200000Z"
             DESCRIPTION "V1.20, Changed the private parameters hwFTPClientIndex, hwFTPClientFileName, 
                          and hwFTPDestFileName of hwBulkBackupStartComnTrap to hwBulkSaveFileName 
                          and hwBulkSaveFileTime." 
                        
             REVISION    "201002200000Z"
             DESCRIPTION "V1.19, changed the range of hwCollectTableName from 1-32 to 1-31." 
            
             REVISION    "201002030000Z"
             DESCRIPTION "V1.18, implemented DT requirements. 
                          Added or modified MIB nodes to support the status-enumerated value of the GET operation."                                

             REVISION    "201001290000Z"
             DESCRIPTION "V1.17, added the definitions of standard trap nodes 
                          and associated trap parameter nodes."
                         
             REVISION    "201001250000Z"
             DESCRIPTION "V1.16, 1, this MIB does not meet the requirements of SIMPLETEST. 
                          Cleared alarms and errors of MIB BROWSER.
                          Added MIB description according to new requirements."
                        
             REVISION    "200911050000Z"
             DESCRIPTION "V1.15, added Recover hwBulkFileObjectMainType and hwBulkFileObjectSubType object in 
                          hwBulkFileTable, added hwBulkObjectCapItemList object, and added hwBulkObjectCapItemTable."

             REVISION    "200907130000Z"
             DESCRIPTION "V1.13, modified the format of hwFtpDestFileName, character limit in the 
                          names of  source file and target file under multi-document mode, and  
                          description of the name format of individual files."
                         
             REVISION    "200905080000Z"
             DESCRIPTION "V1.12, added description of emunerated values for 
                          hwDefineFacilityType and hwDefineMontype objects."
                         
             REVISION    "200903190000Z"
             DESCRIPTION "V1.11, modified the order of OIDs of hwBulkFileIndex, hwBulkAndTCARelationship
                          and hwBulkSaveFileTable, and recovered the functions of hwBulkFileTableNextIndex, 
                          hwBulkFileCount and hwBulkObjectIndexCount objects."
                        
            REVISION    "200903090000Z"
            DESCRIPTION "V1.10, modified part of description of MIB table for batch performance statistics."
            
            REVISION    "200902160000Z"
            DESCRIPTION "V1.09, modified MIB table of batch performance statistics, 
                         and added new table for performance monitoring."
                         
            REVISION    "200803260000Z"
            DESCRIPTION "V1.08, added notes for the operation of real-time query.
                         Modified the position of leaf in hwCollectOperationSet to 
                         support the operation of walk in mibbrowser."
                        
            REVISION    "200801180000Z"
            DESCRIPTION "V1.07, added objects to support the backup of files collected by the NMS through FTP."
            
            REVISION    "200712170000Z"
            DESCRIPTION "V1.05, added configuration of data-collection object and data-collection operation object."
            
            REVISION    "200701220000Z"
            DESCRIPTION "V1.04, added two leaves of main type and subtype, 
                         and deleted the option of 'one day' in collecting time and saving time."
                         
            REVISION    "200611240000Z"
            DESCRIPTION "V1.03, collated and optimized MIB interface for batch performance statistics to form baseline."
            
            REVISION    "200607310000Z"
            DESCRIPTION "V1.02, added leaf according to requirement of the NMS."
            
            REVISION    "200605310000Z"
            DESCRIPTION "V1.01, baseline the version."
            
            REVISION    "200604270000Z"
            DESCRIPTION "V1.00, completed the draft."
            ::= { huaweiUtility 103 }
        
        hwBulkFile  OBJECT IDENTIFIER ::= { hwBulkStatistics 1 }
            
        hwBulkFileMgmt OBJECT IDENTIFIER ::= { hwBulkFile 1 }
                
        hwBulkFileCopyMax OBJECT-TYPE
            SYNTAX Integer32
            MAX-ACCESS read-write
            STATUS obsolete
            DESCRIPTION
                "
                Maximum number of the bulk files that are allowed to back up.
                When the bulk file is created successfully, 
                the NMS will get the bulk file from the devices periodically. 
                It is required that the host device back up the bulk file in periods.
                Because the system resources are limited, this object defines the maximum of backup files. 
                When it hits, the earliest backup file will be overwritten by new ones. 
                If the hwBulkFileTable is not empty, modification to this object value is not allowed.
                "
            ::= { hwBulkFileMgmt 1 }
        
        hwBulkFileTableNextIndex OBJECT-TYPE
            SYNTAX  Integer32
            MAX-ACCESS read-only
            STATUS current
            DESCRIPTION
                "
                Next available index for table hwBulkFileTable.
                If no available index, the value will be filled with '-1'. 
                "
            ::= { hwBulkFileMgmt 2 }
            
        hwBulkFileCount     OBJECT-TYPE
            SYNTAX  Integer32
            MAX-ACCESS read-only
            STATUS current
            DESCRIPTION
                "
                The total number of the bulk file currently.
                "
            ::= { hwBulkFileMgmt 3 }
        
            
-- File management table
        hwBulkFileTable OBJECT-TYPE
            SYNTAX SEQUENCE OF HwBulkFileEntry
            MAX-ACCESS  not-accessible
            STATUS current
            DESCRIPTION
                " 
                Bulk file management table, providing creat/modify/delete operations.
                To create a bulk file, you need create a related record in this table,
                and add object nodes in hwBulkObjectTable.If you delete a record, 
                the object records in hwBulkObjectTable and all backup files will be also deleted.
                The index of this table is hwBulkFileIndex.
                "
            ::= { hwBulkFileMgmt 4 }
        
        hwBulkFileEntry OBJECT-TYPE
            SYNTAX HwBulkFileEntry
            MAX-ACCESS not-accessible
            STATUS current
            DESCRIPTION
                "
                Bulk file management table, providing creat/modify/delete operations.
                To create a bulk file, you need create a related record in this table,
                and add object nodes in hwBulkObjectTable.If you delete a record, 
                the object records in hwBulkObjectTable and all backup files will be also deleted.
                The index of this entry is hwBulkFileIndex.
                "
            INDEX { hwBulkFileIndex }
            ::= { hwBulkFileTable 1 }
        
        HwBulkFileEntry ::= SEQUENCE 
            {
                hwBulkFileIndex  Integer32,
                hwBulkFileName  OCTET STRING,
                hwBulkFileStorage INTEGER,
                hwBulkFileFormat INTEGER,
                hwBulkFileCollectInterval INTEGER,
                hwBulkFileNmsGetInterval INTEGER,           
                hwBulkFileStatus INTEGER,      
                hwBulkFileCurrDirectoryPath OCTET STRING,
                hwBulkFileObjectMainType Integer32,
                hwBulkFileObjectSubType Integer32,
                hwBulkFileRowStatus RowStatus,
                hwBulkFileColNumMode INTEGER,
                hwBulkFileCollectStartTime OCTET STRING,
                hwBulkFileCopyNum Integer32,
                hwBulkObjectCapItemList BITS
            }
        
         hwBulkFileIndex OBJECT-TYPE
            SYNTAX Integer32
            MAX-ACCESS read-only
            STATUS current
            DESCRIPTION
                " 
                Index of bulk file,a unique identifier for a bulk file.
                "
            ::= { hwBulkFileEntry 1 }

        hwBulkFileName OBJECT-TYPE
            SYNTAX OCTET STRING (SIZE (1..63))
            MAX-ACCESS read-create
            STATUS current
            DESCRIPTION
                " 
                Bulk file name.
                If you specify a path in the file name, this file is invalid.
                "
            ::= { hwBulkFileEntry 2 }
        
        hwBulkFileStorage OBJECT-TYPE
            SYNTAX INTEGER
            { 
                ephemeral(1), 
                volatile(2), 
                permanent(3) 
            }
            MAX-ACCESS read-create
            STATUS current        
            DESCRIPTION
                "
                Storage mode of the statistics file.  
                Options:
                1.ephemeral(1) -data file of small volume. It applies to be read once.
                2.volatile(2)  -stored in memory. Easy to lose.
                3.permanent(3) -stored in hard disk. Keep well.
                "
            DEFVAL { volatile }
            ::= { hwBulkFileEntry 3 }
        
        hwBulkFileFormat OBJECT-TYPE
            SYNTAX INTEGER
            { 
                 standardBER(1), 
                 bulkASCIIWithDeflate(2),
                 bulkASCIIWithZipFile(3) 
            }
            MAX-ACCESS read-create
            STATUS current
            DESCRIPTION
                "
                Bulk file formats. 
                Options:
                1.standardBER(1)-standard SNMP ASN.1 BER.
                2.bulkASCIIWithDeflate(2)  -readable ASCII with deflate format.
                3.bulkASCIIWithZipFile(3)  -readable ASCII with zip format.
                "
            DEFVAL {bulkASCIIWithDeflate}
            ::= { hwBulkFileEntry 4 }
        
        hwBulkFileCollectInterval OBJECT-TYPE
            SYNTAX INTEGER
            { 
                fifteenMinutes(1),
                thirtyMinutes(2),
                oneHour(3),
                sixHour(4),
                oneDay(5),
                twoHour(6),
                twelveHour(7)
            }
            MAX-ACCESS read-create
            STATUS current
            DESCRIPTION
                "
                Data collection interval.                 
                Options:
                1.fifteenMinutes(1) -Every 15 minutes.
                2.thirtyMinutes(2)  -Every 30 minutes.
                3.oneHour(3)        -Every 1 hour.                
                4.sixHour(4)        -Every 6 hours.
                5.oneDay(5)         -Every 1 day.
                6.twoHour(6)        -Every 2 hours.
                7.twelveHour(7)     -Every 12 hours.
                "
            DEFVAL {fifteenMinutes}
            ::= { hwBulkFileEntry 5 }
        
        hwBulkFileNmsGetInterval OBJECT-TYPE
            SYNTAX INTEGER
            {
                hour(1),
                thirtyMinutes(2),
                fifteenMinutes(3),
                sixHour(4),
                oneDay(5)
            }
            MAX-ACCESS read-create
            STATUS current
            DESCRIPTION
                "
                File report interval. The interval thirtyMinutes is not supported. 
                The file report interval cannot be shorter than the data collection interval.
                Options:
                1.hour(1)               -The host generates a statistics file every hour. 
                2.thirtyMinutes(2)      -The host generates a statistics file every 30 minutes.
                3.fifteenMinutes(3)     -The host generates a statistics file every 15 minutes.
                4.sixHour(4)            -The host generates a statistics file every six hour.
                5.oneDay(5)             -The host generates a statistics file every day.
                Data collection interval and file storage interval can be only one of the following combinations:
                Data collection interval file storage interval
                15 minutes               15 minutes or 1 hour
                6 hour                   6 hours
                1 day                    1 day

                This object takes effect when the centralized bulk feature is enabled, 
                and does not take effect when the distributed bulk feature is enabled.
                "
            DEFVAL {hour}
            ::= { hwBulkFileEntry 6 }
            
        hwBulkFileStatus OBJECT-TYPE
            SYNTAX INTEGER
            { 
                ready(1), 
                create(2), 
                running(3), 
                nospace(4), 
                noMem(5), 
                writeErr(6), 
                stopped(7) 
            }
            MAX-ACCESS read-create
            STATUS current
            DESCRIPTION
                " 
                Bulk file status.               
                Options:
                1.ready(1)   -indicates that the statistics file is only created, 
                              leaving the actual statistics collection to be started. This value cannot be set.
                2.create(2)  -indicates the starting of the file. If succeeds, the status changes to running. 
                              If fails, an error code is returned.
                3.running(3) -indicates that the statistics file is already started successfully 
                              and in the running state currently. This value cannot be set.
                4.nospace(4) -indicates that creating or writing the file failed. 
                              The cause is no free space in hard disk. This value cannot be set.
                5.noMem(5)   -indicates that creating or writing the file failed. The cause is no free memory. 
                              This value cannot be set.
                6.writeErr(6)-indicates an Unknown error. The file cannot be written.
                7.stopped(7) -indicates that the task is suspended.
                If this value is set when in the running status, then writing file is stopped. 
                Meanwhile, the system generates a file based on the collected data.
                "
        ::= { hwBulkFileEntry 7 }
        
        hwBulkFileCurrDirectoryPath OBJECT-TYPE
            SYNTAX OCTET STRING (SIZE (1..31))
            MAX-ACCESS read-only
            STATUS current
            DESCRIPTION
                "
                The latest index of the statistics file.
                "
            ::= { hwBulkFileEntry 8 }   

        hwBulkFileObjectMainType OBJECT-TYPE
            SYNTAX Integer32
            MAX-ACCESS read-write
            STATUS current
            DESCRIPTION
                "
                Identify main-type of object. The device will collect statistics of all the ports according to 
                to hwBulkFileObjectMainType and hwBulkFileObjectSubType if these two objects are not null.
                The values of hwBulkFileObjectMainType and hwBulkFileObjectSubType need to match as follows:
                --------------------------------------                                                                 
                ulMainType   ulSubType     Note                                                                        
                ---------------------------------------                                                                
                   1           101         Device                                                                      
                   3           113         V5 Interface user frame                                                     
                   4           100         Board                                                                       
                   4           101         Memory                                                                      
                   6           105         ADSL port(only support ADSL2+)                                              
                   6           108         E1 port                                                                     
                   6           109         Ethernet port
                   6           111         interboard-port                                                               
                   6           112         backboard port
                   6           113         V5 user                                                                     
                   6           119         ATM port                                                                    
                   6           126         SHDSL port                                                                  
                   6           141         DS3 port     
                   6           160         G.fast port
                   6           161         G.fast Xlin-data
                   6           162         G.fast Segment                                                                  
                   6           173         Ethernet port                                                               
                   6           175         VDSL2 port                                                                   
                   6           180         VDSL2 Xlin-data                                                                     
                   6           1080        E1 port                                                                     
                   6           108000      E1 port                                                                     
                   7           100         VDSL2 Segment                
                   112         0           Vcl flux                                                                    
                   112         1           Vpl flux                                                                    
                   112         101         C VLAN
                   112         102         XPON Service-port
                   114         1           V5 interface                                                                
                   114         2           2M link                                                                     
                   114         3           Logic C channel                                                             
                   120         0           VLAN                                                                        
                   127         1           IMA group                                                                   
                   127         2           IMA link  
                   145         0           MG                                                                          
                   153         0           L2UA link                                                                   
                   153         1           L2UA link   
                   182         1           XPON ONT Optical Module Dynamic Info
                   182         2           XPON UNI Optical Module Dynamic Info
                   182         3           EPON ONT Optical Module Dynamic Info
                   182         4           EPON UNI Optical Module Dynamic Info                   
                   191         1           GPON UNI PORT Statistics
                   191         2           GPON ONU Statistics
                   191         7           GPON ONU Wifi Statistics 
                   191         8           GPON ONU Wifi STA Info 
                   191         9           GPON ONU Wifi Neighbor AP info
                   191         15          XPON ONT ETH PORT Statistics
                   192         1           EPON UNI PORT Statistics
                   192         2           EPON ONU Statistics                                                               
                   192         7           EPON ONU Wifi Statistics
                   192         8           EPON ONU Wifi STA Info 
                   192         9           EPON ONU Wifi Neighbor AP Info
                   192         11          EPON ONT ETH PORT Statistics
                   197         7           Cable Modem
                   200         0           Y1731 PM
                ---------------------------------------
                "                                                               
            ::= { hwBulkFileEntry 9 } 
            
        hwBulkFileObjectSubType OBJECT-TYPE
            SYNTAX Integer32
            MAX-ACCESS read-write
            STATUS current
            DESCRIPTION
                "
                Identify sub-type of object. The device will collect statistics on all ports according
                to hwBulkFileObjectMainType and hwBulkFileObjectSubType if these two leaves are not null. 
                The values of hwBulkFileObjectMainType and hwBulkFileObjectSubType need to match as follows:
                --------------------------------------                   
                ulMainType   ulSubType     Note                          
                ---------------------------------------                  
                   1           101         Device                        
                   3           113         V5 Interface user frame       
                   4           100         Board                         
                   4           101         Memory                        
                   6           105         ADSL port(only support ADSL2+)
                   6           108         E1 port                       
                   6           109         Ethernet port
                   6           111         interboard-port                 
                   6           112         backboard port
                   6           113         V5 user                       
                   6           119         ATM port                      
                   6           126         SHDSL port                    
                   6           141         DS3 port    
                   6           160         G.fast port                 
                   6           161         G.fast Xlin-data
                   6           162         G.fast Segment                   
                   6           173         Ethernet port                 
                   6           175         VDSL2 port    
                   6           180         VDSL2 Xlin-data  
                   6           1080        E1 port                       
                   6           108000      E1 port                       
                   7           100         VDSL2 Segment                                     
                   112         0           Vcl flux                      
                   112         1           Vpl flux                      
                   112         101         C VLAN
                   112         102         XPON Service-port
                   114         1           V5 interface                  
                   114         2           2M link                       
                   114         3           Logic C channel               
                   120         0           VLAN                          
                   127         1           IMA group                     
                   127         2           IMA link   
                   145         0           MG                            
                   153         0           L2UA link                     
                   153         1           L2UA link    
                   182         1           XPON ONT Optical Module Dynamic Info
                   182         2           XPON UNI Optical Module Dynamic Info
                   182         3           EPON ONT Optical Module Dynamic Info
                   182         4           EPON UNI Optical Module Dynamic Info                   
                   191         1           GPON UNI PORT Statistics
                   191         2           GPON ONU Statistics
                   191         7           GPON ONU Wifi Statistics 
                   191         8           GPON ONU Wifi STA Info 
                   191         9           GPON ONU Wifi Neighbor AP info
                   191         15          XPON ONT ETH PORT Statistics
                   192         1           EPON UNI PORT Statistics
                   192         2           EPON ONU Statistics                                                               
                   192         7           EPON ONU Wifi Statistics
                   192         8           EPON ONU Wifi STA Info 
                   192         9           EPON ONU Wifi Neighbor AP Info
                   192         11          EPON ONT ETH PORT Statistics
                   197         7           Cable Modem
                   200         0           Y1731 PM
                ---------------------------------------
                "
            ::= { hwBulkFileEntry 10 } 
                    
        hwBulkFileRowStatus OBJECT-TYPE
            SYNTAX RowStatus
            MAX-ACCESS read-create
            STATUS current
            DESCRIPTION
                "
                Row operation object. When the centralized bulk feature is enabled, 
                the file in the running state cannot be deleted, whereas when the 
                distributed bulk feature is enabled, the file in any state can be deleted.
                "
            ::= { hwBulkFileEntry 11 } 
            
        hwBulkFileColNumMode OBJECT-TYPE
            SYNTAX INTEGER
            { 
                reportLastSection(1), 
                notReportLastSection(2)
            }
            MAX-ACCESS read-create
            STATUS current
            DESCRIPTION
                "
                Setting whether to report the statistics collected in the previous interval. 
                After the statistics file is created, the identifier cannot be changed.
                Options:
                1.reportLastSection(1)    -indicates that the statistics collected in the previous interval 
                                           is contained in the statistics file of the current interval.
                2.notReportLastSection(2)-indicates that the statistics data of the last interval 
                                           is not contained in the statistics file of the current interval. 
                This object takes effect only when the centralized bulk feature is enabled, 
                and does not take effect when the distributed bulk feature is enabled.
                "
            DEFVAL {reportLastSection}
            ::= { hwBulkFileEntry 12 }  
            
        hwBulkFileCollectStartTime OBJECT-TYPE
            SYNTAX OCTET STRING (SIZE (1..5))
            MAX-ACCESS read-create
            STATUS current
            DESCRIPTION
                "
                Setting the start time of the data collection with intervals of six hours or one day. 
                The default start time is 00:00, and can only be an integer multiple of 15 minutes. 
                The start time of the data collection with the interval of 15 minutes can be set,
                but it does not take effect actually.
                "
            DEFVAL { "0:0" }
            ::= { hwBulkFileEntry 13 }
        
        hwBulkFileCopyNum OBJECT-TYPE
            SYNTAX Integer32
            MAX-ACCESS read-only
            STATUS current
            DESCRIPTION
                "
                The number of saved files during this task, read-only.
                "
            ::= { hwBulkFileEntry 14 }
            
        hwBulkObjectCapItemList OBJECT-TYPE
            SYNTAX BITS
            {
                    pmpDslOprMode(0),
                    pmpAturVdrId(1),
                    pmpDslPrfName(2),
                    pmpCrcEcNerUs(3),
                    pmpCrcEcFerDs(4),
                    pmpFecsNerUs(5),
                    pmpFecsFerDs(6),
                    pmpFecEvtNerUs(7),
                    pmpFecEvtFerDs(8),
                    pmpEsNerUs(9),
                    pmpEsFerDs(10),
                    pmpSesNerUs(11),
                    pmpSesFerDs(12),
                    pmpUasNerUs(13),
                    pmpUasNerDs(14),
                    pmpLossNerUs(15),
                    pmpLossFerDs(16),
                    pmpLofsNerUs(17),
                    pmpLofsFerDs(18),
                    pmpLolsFerUs(19),
                    pmpLopsFerDs(20),
                    pmpSucInit(21),
                    pmpFailFullInit(22),
                    pmpLineAttnUs(23),
                    pmpLineAttnDs(24),
                    pmpSnrUs(25),
                    pmpSnrDs(26),
                    pmpLineRateUs(27),
                    pmpLineRateDs(28),
                    pmpMaxAtblDrUs(29),
                    pmpMaxAtblDrDs(30),
                    pmpUpTime(31),
                    pmpTrfcUs(32),
                    pmpTrfcDs(33),
                    pmpPwrStt(34),
                    pmpNtePwrStt(35),
                    pmpAatpUs(36),
                    pmpAatpDs(37),
                    pmpRUs(38),
                    pmpRDs(39),
                    pmpSUs(40),
                    pmpSDs(41),
                    pmpDUs(42),
                    pmpDDs(43),
                    pmpNUs(44),
                    pmpNDs(45),
                    pmpActInpUs(46),
                    pmpActinpDs(47),
                    pmpInmInpeqUs(48),
                    pmpInmInpeqDs(49),
                    pmpInmIatUs(50),
                    pmpInmIatDs(51),
                    pmpInmmeUs(52),
                    pmpInmmeDs(53),
                    pmpRtxusedUs(54),
                    pmpRtxusedDs(55),
                    pmpResynRatio(56),
                    pmpPcbDs(57),
                    pmpModuMode(58),
                    pmpPboDs(59),
                    pmpPboUs(60),
                    pmpElem1Support(61),
                    pmpIntervalValid(62),
                    pmpFecUnevtNerUs(63),
                    pmpGecUnevtNarDs(64),
                    pmpEnBlkNerUs(65),   
                    pmpEnBlkFarDs(66),   
                    pmpRtxCwNerUs(67),   
                    pmpRtxCwFarDs(68),   
                    pmpRtxCcwNerUs(69),  
                    pmpRtxCcwFarDs(70),  
                    pmpRtxUnccwNerus(71),
                    pmpRtxUnccwFards(72),
                    pmpXturVdsNum(73),    
                    pmpXturVerNum(74),    
                    pmpActDelayUs(75),    
                    pmpActDelayDs(76),
                    pmpAdslExtprfName(77),    
                    pmpBandPlan(78),       
                    pmpActPsdDs(79),      
                    pmpActPsdUs(80),      
                    pmpXturSvdNum(81),    
                    pmpPortState(82),      
                    pmpCpeType(83),
                    pmpRtxleftrDs(84),
                    pmpRtxleftrUs(85),
                    pmpRtxefbDs(86),
                    pmpRtxefbUs(87),
                    pmpRtxmineftrDs(88),
                    pmpRtxmineftruUs(89),
                    pmpRtxactuaeftrDs(90),
                    pmpRtxactuaeftrUs(91),
                    pmpSigAttnUs(92),
                    pmpSigAttnDs(93),
                    pmpLineAttnPbUs(94),
                    pmpLineAttnPbDs(95), 
                    pmpSignalAttnPbUs(96),
                    pmpSignalAttnPbDs(97), 
                    pmpSnrMarginPbUs(98),
                    pmpSnrmarginPbDs(99),
                    pmpSnrPtUs(201),
                    pmpSnrPtDs(202),
                    pmpBitAlUs(203),
                    pmpBitAlDs(204),
                    pmpHlogUs(205),
                    pmpHlogDs(206),
                    pmpQlnUs(207),
                    pmpQlnDs(208),
                    pmpGrpsizeUs(209),
                    pmpGrpsizeDs(210),
                    pmpTxpsdUs(211),  
                    pmpTxpsdDs(212),  
                    pmpQlnVectorUs(213),  
                    pmpQlnVectorDs(214),
                    pmpGainAlUs(215),  
                    pmpGainAlDs(216),
                    pmpUPackets(250),
                    pmpDPackets(251),
                    pmpUBytes(252),
                    pmpDBytes(253),
                    pmpUCarDPackets(254),
                    pmpDCarDPackets(255),
                    pmpUODPackets(256),
                    pmpDODPackets(257), 
                    pmpUCvlanPackets(258),
                    pmpDCvlanPackets(259), 
                    pmpXlinData(261),
                    pmpXponServiceVlan(270),
                    pmpXponOnuId(271),
                    pmpTranOcts(300),
                    pmpRecvOcts(301), 
                    pmpTranEthPortPackets(302),
                    pmpRecvEthPortPackets(303),
                    pmpRecvDiscardEthPortPackets(304),
                    pmpTranDiscardEthPortPackets(305), 
                    pmpTranGreenSendEthPortOcts(306),
                    pmpTranGreenSendethPortNumber(307),
                    pmpTranGreensendDiscardEthNumber(308),
                    pmpTranYellowSendEthPortOcts(309),
                    pmpTranYellowSendEthPortNumber(310),
                    pmpTranYellowSendDiscardEthNumber(311),
                    pmpEthTranUnicastPackets(312),
                    pmpEthRecvUnicastPackets(313),
                    pmpEthTranMulticastPackets(314),
                    pmpEthrecvMulticastPackets(315),
                    pmpEthtranBoardcastPackets(316),
                    pmpEthrecvBoardcastPackets(317),
                    pmpEthTranPausePackets(318),
                    pmpEthAlignmentErrorPackets(319),
                    pmpEthTranCrcErrorPackets(320),
                    pmpEthRecvCrcErrorPackets(321),
                    pmpEthCollisionPackets(322),
                    pmpEthTranOversizedPackets(323),
                    pmpEthRecvOversizedPackets(324),
                    pmpEthSingleCollisionPackets(325),
                    pmpEthMultiCollisionPackets(326),
                    pmpEthDiscardUndersizedPackets(327),
                    pmpEthTranUndersizedPackets(328),
                    pmpEthRecvUndersizedPackets(329),
                    pmpEthTranFragments(330),
                    pmpEthRecvFragments(331),
                    pmpEthTranJabbers(332),
                    pmpEthRecvJabbers(333),
                    pmpEthTran64BytePackets(334),
                    pmpEthRecv64BytePackets(335),
                    pmpEthTran65127BytePackets(336),
                    pmpEthRecv65127BytePackets(337),
                    pmpEthTran128255BytePackets(338),
                    pmpEthRecv128255BytePackets(339),
                    pmpEthTran256511BytePackets(340),
                    pmpEthRecv256511BytePackets(341),
                    pmpEthTran5121023BytePackets(342),
                    pmpEthRecv5121023BytePackets(343),
                    pmpEthTran10241518BytePackets(344),
                    pmpEthRecv10241518BytePackets(345),
                    pmpEthTranErrorPackets(346),
                    pmpEthRecvErrorPackets(347),
                    pmpEthIntervalValid(348),
                    pmpGponUniUsRate(360),
                    pmpGponUniDsRate(361), 
                    pmpGponUniErrPktRatio(362),
                    pmpGponUniOpticsTemp(363),  
                    pmpXponUniOpticsBiasCurr(364),
                    pmpXponUniOpticsVolt(365),
                    pmpXponUniOpticsTxPower(366),
                    pmpGponUniTranOcts(367),
                    pmpGponUniRecvOcts(368),
                    pmpGponUniTranPackets(369),
                    pmpGponUniRecvPackets(370),
                    pmpGponUniDiscardPackets(371),
                    pmpGponUniTxDiscardPackets(372), 
                    pmpGponUniRecvErrorPackets(373),
                    pmpEponUniUsRate(376),
                    pmpEponUniDsRate(377),  
                    pmpEponUniErrPktRatio(378),
                    pmpEponUniOpticsTemp(379),
                    pmpEponUniOpticsBiasCurr(380),
                    pmpEponUniOpticsVolt(381),
                    pmpEponUniOpticsTxPower(382),
                    pmpEponUniTxDiscardPackets(383),
                    pmpEponUniRxDiscardPackets(384),
                    pmpEponUniRecvOcts(385),
                    pmpEponUniTranOcts(386),
                    pmpEponUniRecvErrorPackets(387),
                    pmpEponUniTranPackets(388),
                    pmpEponUniRecvPackets(389),
                    pmpGponNniUsOcts(390),
                    pmpGponNniDsOcts(391),
                    pmpGponNniUsRate(392),
                    pmpGponNniDsRate(393),
                    pmpXponNniOpticsTemp(394),
                    pmpXponNniOpticsBiasCurr(395),
                    pmpXponNniOpticsVolt(396),
                    pmpXponNniOpticsTxPower(397),
                    pmpXponNniOpticsRxPower(398),
                    pmpXponOltNniopticsRxPower(399),
                    pmpGponNniLofi(400),
                    pmpGponNniUpErrDelimiter(401),
                    pmpGponNniUpErrBip(402),
                    pmpGponNniDownerrBip(403),
                    pmpGponNniupFecCorrectBlock(404),
                    pmpGponNniupFecUncorrectBlock(405),
                    pmpGponNniUpHec(406),
                    pmpGponNniOfflineTimes(407),
                    pmpEponNniUsRate(408),
                    pmpEponNniDsRate(409),
                    pmpEponNniOpticsTemp(410),
                    pmpEponNniOpticsBiasCurr(411),
                    pmpEponNniOpticsVolt(412),
                    pmpEponNniOpticsTxPower(413),
                    pmpEponNniOpticsRxPower(414),
                    pmpEponOltNniOpticsRxPower(415),
                    pmpEponNniUsOcts(416),
                    pmpEponNniDsOcts(417),
                    pmpEponNniofflinetimes(418),
                    pmpXponOnuEthPortUsRate(424),
                    pmpXponOnuEthPortDsRate(425),  
                    pmpXponOnuEthPortRxTotal(426),
                    pmpXponOnuEthPortRxUnic(427),
                    pmpXponOnuEthPortRxBrdc(428),
                    pmpXponOnuEthPortRxMltc(429),
                    pmpXponOnuEthPortTxTotal(430),
                    pmpXponOnuEthPortTxUnic(431),
                    pmpXponOnuEthPortTxBrdc(432),
                    pmpXponOnuEthPortTxMltc(433),
                    pmpXponOnuEthPortRxOcts(434),
                    pmpXponOnuEthPortTxOcts(435),
                    pmpXponOnuethPortRxErrorPackets(436),
                    pmpEponOnuEthPortUsRate(440),
                    pmpEponOnuEthPortDsRate(441),
                    pmpEponOnuEthPortRecvTotal(442),
                    pmpEponOnuEthPortRxUnic(443),
                    pmpEponOnuEthPortRxBrdc(444),
                    pmpEponOnuEthPortRxMltc(445),
                    pmpEponOnuEthPortTxTotal(446),
                    pmpEponOnuEthPortTxUnic(447), 
                    pmpEponOnuEthPortTxBrdc(448),
                    pmpEponOnuEthPortTxMltc(449),
                    pmpEponOnuEthPortRxOcts(450),
                    pmpEponOnuEthPortTxOcts(451),
                    pmpEponOnuEthPortRxErrorPackets(452),
                    pmpBackboardPortBandwith(500),
                    pmpRecvSmallMainboardOcts(501),
                    pmpTranSmallMainboardOcts(502),
                    pmpRecvDiscardSmallMainboardPackets(503),
                    pmpTranDiscardSmallMainboardPackets(504),
                    pmpRecvBigMainboardOcts(505),
                    pmpTranBigMainboardOcts(506),
                    pmpRecvDiscardBigMainboardPackets(507),
                    pmpTranDiscardBigMainboardPackets(508),
                    pmpInterboardportBandwith(520),
                    pmpInterboardportRecvOcts(521),
                    pmpInterboardportTranOcts(522),
                    pmpInterboardportRecvDiscardpackets(523),
                    pmpInterboardportTranDiscardpackets(524),
                    boardCpuOccupation(600),       
                    boardTemperature(601),       
                    boardDspOccupation(602),      
                    boardMgifFailedNum(650),
                    pmpGponNniRecvErrorPackets(700),
                    pmpGponNniTranPackets(701),
                    pmpGponNniRecvPackets(702),
                    pmpEponNniRecvErrorPackets(730),
                    pmpEponNniTranPackets(731),
                    pmpEponNniRecvPackets(732),
                    singleEndedFramelossratioNearMax(750),
                    singleEndedFramelossratioNearMin(751),
                    singleEndedFramelossratioNearAverage(752),
                    singleEndedFramelossratioFarMax(753),
                    singleEndedFramelossratioFarMin(754),
                    singleEndedFramelossratioFarAverage(755),
                    twoWayDelayMax(756),
                    twoWayDelayMin(757),
                    twoWayDelayAverage(758),
                    twoWayJitterMax(759),
                    twoWayJitterMin(760),
                    twoWayJitterAverage(761),
                    oneWayDelayFarMax(762),
                    oneWayDelayFarMin(763),
                    oneWayDelayFarAverage(764),
                    oneWayJitterFarMax(765),
                    oneWayJitterFarMin(766),
                    oneWayJitterFarAverage(767),
                    oneWayDelayNearMax(768),
                    oneWayDelayNearMin(769),
                    oneWayDelayNearAverage(770),
                    oneWayJitterNearMax(771),
                    oneWayJitterNearMin(772),
                    oneWayJitterNearAverage(773),
                    pmpEponUniOptics10gTxPower(780),
                    pmpEponUniOptics10gBiasCurr(781),
                    pmpEponNniPeerOpticsTxPower(800),
                    pmpEponUni1gChannelUsRate(851),
                    pmpEponUni1gChannelErrPktRatio(852),
                    pmpEponUni1gChannelUsBytes(853),
                    pmpEponUni1gChannelDsBytes(854),
                    pmpEponUni1gChannelDsRate(855),
                    pmpEponUni1gChannelUsPackets(856),
                    pmpEponUni1gChannelDsPackets(857),
                    pmpEponUni1gChannelUsErrorPackets(858),
                    pmpEponUni1gChannelUsDiscardPackets(859),
                    pmpEponUni1gChannelDsDiscardPackets(860),
                    pmpEponUni10gChannelUsrate(861),
                    pmpEponUni10gChannelErrPktRatio(862),
                    pmpEponUni10gChannelUsBytes(863),
                    pmpEponUni10gChannelDsBytes(864),
                    pmpEponUni10gChannelDsRate(865),
                    pmpEponUni10gChannelUsPackets(866),
                    pmpEponUni10gChannelDsPackets(867),
                    pmpEponUni10gChannelUsErrorPackets(868),
                    pmpEponUni10gChannelUsDiscardPackets(869),
                    pmpEponUni10gChannelDsDiscardPackets(870),
                    pmpXponOnuWifiTxTotalPackets(871),
                    pmpXponOnuWifiTxErrPackets(872),
                    pmpXponOnuWifiTxDiscardPackets(873),
                    pmpXponOnuWifiRxTotalPackets(874),
                    pmpXponOnuWifiRxErrPackets(875),
                    pmpXponOnuWifiRxDiscardPackets(876),
                    pmpXponOnuWifiTransQualityLevel(877),
                    pmpXponOnuWifiDsRate(878), 
                    pmpXponOnuWifiUsRate(879),
                    pmpXponOnuWifiRSSI(880),
                    pmpXponOnuWifiSNR(881),
                    pmpXponOnuWifiSignalQualityLevel(882),
                    pmpXponOnuWifiIneighborAP(883),
                    pmpXponOnuWifiAPFactor(884),
                    pmpCmStatus(950),
                    pmpCmUsWidth(951),
                    pmpCmUsFrequency(952),
                    pmpCmUsCmtsEqd(953),
                    pmpCmUsActEqd(954),
                    pmpCmUsSnr(955),
                    pmpCmUsYxPower(956),
                    pmpCmUsGoodcode(957),
                    pmpCmUsCorrected(958),
                    pmpCmUsUncorrected(959),
                    pmpCmUsCcer(960),
                    pmpCmUsUcer(961),
                    pmpCmDsFrequency(962),
                    pmpCmDsSnr(963),
                    pmpCmDsRxPower(964),
                    pmpCmDsCcer(965),
                    pmpCmDsUcer(966),
                    pmpCmDsGoodcode(967),
                    pmpCmDsCorrected(968),
                    pmpCmDsUncorrected(969),
		    pmpMaxDsSNR(970),
                    pmpMinDsSNR(971),
                    pmpPrimaryDs(972),
                    pmpPrimaryUs(973),
                    pmpRxByte(974),
                    pmpTxByte(975),
                    pmpSuccessReg(976),	
                    pmpFailReg(977),
                    pmpRepeatReg(978),
                    pmpStationMaintenance(979),
                    pmpStationMaintenanceMiss(980),
                    pmpStationMaintainConMiss(981),
                    pmpPowerAdjust(982),
                    pmpSeverelyPowerAdjust(983),
                    pmpUnstableConnection(984),
                    pmpMaxUsSNR(985),
                    pmpMinUsSNR(986)
            }
            MAX-ACCESS read-write
            STATUS current
            DESCRIPTION
                " 
                List of the statistical index. Through this object, 
                the statistical index can be configured in batches in the format of bit-domain string. 
                Each file supports up to 256 statistical indexes.
                The statistical index hwBulkObjectCapItemList is of the bit type. 
                It can be configured as follows: to configure the index n, set the nth in the bit string to 1, 
                that is,......000100......For example, to configure the index 1, 
                set the first character of the string to 1, 
                and issue 0100 0000, namely, # 0x40 (note that the value of the bit type starts from 0). 
                For example, to configure the index 8, set the eighth character of the string to 1, 
                and issue 0000 0000 1000 0000, namely, # 0x00 0x80.
                If the statistical indexes 1, 2, 3, 201, 202 are supported, 
                # 0x70 0x00 0x00 0x00 0x00 0x00 0x00 0x00 0x00 0x00 0x00 0x00 0x00 0x00 0x00 0x00 
                0x00 0x00 0x00 0x00 0x00 0x00. 0x00 0x00. 0x00 0x60 is issued. 
                This object takes effect only when the distributed bulk feature is enabled.
                "
            ::= { hwBulkFileEntry 15 }
        
        hwBulkSaveFileTable OBJECT-TYPE
            SYNTAX SEQUENCE OF HwBulkSaveFileEntry
            MAX-ACCESS  not-accessible
            STATUS current
            DESCRIPTION
                "
                This table is used for querying information about the history
                files saved by the statistical object. 
                The indexes of this table are hwBulkFileIndex and hwBulkSaveFileIndex.
                This table does not support operations such as create, modify and delete, 
                but supports get and walk operations.
                "
            ::= { hwBulkFileMgmt 5 }
        
        hwBulkSaveFileEntry OBJECT-TYPE
            SYNTAX HwBulkSaveFileEntry
            MAX-ACCESS not-accessible
            STATUS current
            DESCRIPTION
                " 
                This table is used for querying information about the history
                files saved by the statistical object. 
                The indexes of this entry are hwBulkFileIndex and hwBulkSaveFileIndex.
                This table does not support operations such as create, modify and delete, 
                but supports get and walk operations.
                "
            INDEX { hwBulkFileIndex,hwBulkSaveFileIndex }
            ::= { hwBulkSaveFileTable 1 }
        
        HwBulkSaveFileEntry ::= SEQUENCE 
            {
                hwBulkSaveFileIndex  Integer32,
                hwBulkSaveFileTime OCTET STRING
            }
            
         hwBulkSaveFileIndex OBJECT-TYPE
            SYNTAX Integer32
            MAX-ACCESS accessible-for-notify
            STATUS current
            DESCRIPTION
                " 
                Index of bulk file copy. It is a unique identifier for a bulk save file.
                "
            ::= { hwBulkSaveFileEntry 1 }
            
        hwBulkSaveFileTime OBJECT-TYPE
            SYNTAX OCTET STRING (SIZE (1..20))
            MAX-ACCESS read-only
            STATUS current
            DESCRIPTION
                "
                Time of saving the statistics file.
                "
            ::= { hwBulkSaveFileEntry 2 }
            
-- End of file management table
        hwBulkAndTCARelationship OBJECT-TYPE
            SYNTAX INTEGER
            {
                on(1),
                off(2)
            }
            MAX-ACCESS read-write
            STATUS obsolete 
            DESCRIPTION
                "
                Switch of the correlation between the bulk performance statistics and threshold alarm. 
                Options:
                1.on(1) -the switch is on.
                2.off(2)-the switch is off.
                This object is not supported currently.
                "
            ::= { hwBulkFileMgmt 6 }
        
        hwBulkFileNameRule OBJECT-TYPE
            SYNTAX BITS
                {
                filenameIpaddress(0),
                filenameInterval(1)
                }
            MAX-ACCESS read-write
            STATUS current
            DESCRIPTION
                "This object is used to set the rule for naming a statistic file. If this object is set to
                 interval, the measurement period is contained in the backup file. If this object is set to 
                 ipaddress, the source IP address of the trap is contained in the backup file. If this object
                 is not specified, the default value is used and the rule for naming a statistics file in 
                 this version is the same as that in the earlier version."
            ::= { hwBulkFileMgmt 7 }

        hwBulkFileConditionTable OBJECT-TYPE
            SYNTAX SEQUENCE OF HwBulkFileConditionEntry
            MAX-ACCESS  not-accessible
            STATUS current
            DESCRIPTION
                "
                Indicates the statistical condition table, on which users can add, delete, 
                or modify statistical conditions. Before adding a statistical condition, 
                use hwBulkFileTable to configure a statistical task. To delete a statistical condition, 
                use hwBulkFileCollectRowStatus. Before deleting a statistical task, use hwBulkFileConditionTable 
                to delete corresponding statistical conditions. To modify an existing statistical condition, modify 
                the value of the hwBulkFileCollectCondition field.Statistical conditions can be issued in hexadecimal notation or using a character string.
                The index of this table is hwBulkFileObjectMainType, hwBulkFileObjectSubType and hwBulkFileCollectInterval."
            ::= { hwBulkFileMgmt 8 }
        
        hwBulkFileConditionEntry OBJECT-TYPE
            SYNTAX HwBulkFileConditionEntry
            MAX-ACCESS not-accessible
            STATUS current
            DESCRIPTION
                " 
                Indicates the statistical condition table, on which users can add, delete, 
                or modify statistical conditions. Before adding a statistical condition, 
                use hwBulkFileTable to configure a statistical task. To delete a statistical condition, 
                use hwBulkFileCollectRowStatus. Before deleting a statistical task, use hwBulkFileConditionTable 
                to delete corresponding statistical conditions. To modify an existing statistical condition, modify 
                the value of the hwBulkFileCollectCondition field.Statistical conditions can be issued in hexadecimal notation or using a character string.
                The index of this entry is hwBulkFileObjectMainType, hwBulkFileObjectSubType and hwBulkFileCollectInterval."
            INDEX { hwBulkFileObjectMainType,hwBulkFileObjectSubType,hwBulkFileCollectInterval }
            ::= { hwBulkFileConditionTable 1 }

        HwBulkFileConditionEntry ::= SEQUENCE
            {
                hwBulkFileCollectCondition OCTET STRING,
                hwBulkFileCollectRowStatus RowStatus
            }

        hwBulkFileCollectCondition OBJECT-TYPE
            SYNTAX OCTET STRING (SIZE (1..200))
            MAX-ACCESS read-write
            STATUS current
            DESCRIPTION
                "
                Statistical condition.
                "
            ::= { hwBulkFileConditionEntry 1 } 
                        
        hwBulkFileCollectRowStatus OBJECT-TYPE
            SYNTAX RowStatus
            MAX-ACCESS read-create
            STATUS current
            DESCRIPTION
                "
                Row status of the statistical condition.
                "
            ::= { hwBulkFileConditionEntry 2 }
                                
-- End of file management table
        hwBulkObjectMgmt OBJECT IDENTIFIER ::= { hwBulkFile 2 }
       
-- OID management table in the bulk file
        hwBulkOIDTable OBJECT-TYPE
            SYNTAX SEQUENCE OF HwBulkOIDEntry
            MAX-ACCESS  not-accessible
            STATUS current
            DESCRIPTION
                " 
                OID management table in the bulk file. Prerequisite for the operation is that the 
                bulk file is listed in the hwBulkFileTable and the file state is ready.
                The indexes of this table are hwBulkOID and hwBulkFileIndex in hwBulkFileTable.                 
                In the case of the distributed bulk performance statistics, this table is not supported. 
                "
            ::= { hwBulkObjectMgmt 1 }
        
        hwBulkOIDEntry OBJECT-TYPE
            SYNTAX HwBulkOIDEntry
            MAX-ACCESS not-accessible
            STATUS current
            DESCRIPTION
                " 
                OID management table in the bulk file. Prerequisite for the operation is that the 
                bulk file is listed in the hwBulkFileTable and the file state is ready.
                The indexes of this entry are hwBulkOID and hwBulkFileIndex in hwBulkFileTable.                 
                In the case of the distributed bulk performance statistics, this table is not supported. 
                "
            INDEX { hwBulkFileIndex, 
                    IMPLIED hwBulkOID }
            ::= { hwBulkOIDTable 1 }
        
        HwBulkOIDEntry ::= SEQUENCE 
            {  
                hwBulkOID OBJECT IDENTIFIER,
                hwBulkOIDRowStatus RowStatus
            }
                    
        hwBulkOID OBJECT-TYPE
            SYNTAX OBJECT IDENTIFIER
            MAX-ACCESS not-accessible
            STATUS current
            DESCRIPTION
                "
                Index in the case of adding the object in the statistics file. 
                The OID of the object is collected. The OID need not contain the index. 
                The maximum length of the OID (excluding '.') is 20 digits.
                "
            ::= { hwBulkOIDEntry 1 }

-- This object will be deleted because device need not calculate difference value and the NMS only wants absolute value.
--      hwBulkOIDIsStatistical OBJECT-TYPE
--          SYNTAX INTEGER{ absolute(1), difference(2)}
--          MAX-ACCESS read-create
--          STATUS current
--          DESCRIPTION
--              " 
--              Judge whether the objects of bulk files are statistic or others.
--              absolute(1):      The objects are not statistics. The data is absolute value.  
--              difference(2):    The objects are statistics. The data is difference value.
--              "
--          ::= { hwBulkOIDEntry 2 }            
                              
        hwBulkOIDRowStatus OBJECT-TYPE
            SYNTAX RowStatus
            MAX-ACCESS read-create
            STATUS current
            DESCRIPTION
                " 
                Row operation object hwBulkOIDRowStatus. 
                When the creation operation is performed in hwBulkOIDRowStatus, the enumeration value createAndGo (4) is used.                  
                During the creation operation, hwBulkFileIndex and hwBulkObjectIndex must be issued together.
                Before the creation operation, make sure that hwBulkFileTable contains a statistical file record.
                If a file corresponds to multiple OIDs, the program checks whether the number of OIDs is the same as 
                the number of indexes. If the number of OIDs is different from the number of indexes, the file 
                cannot be issued. The user must ensure that the indexes corresponding to the same OID in different 
                tables are the same. Otherwise, the collected data may be abnormal. 
                During dynamic creation, the creation configuration takes effect only after the next report period 
                of the statistical file.
                When the deletion operation is performed, the enumeration value destroy (6) is used. 
                During the deletion operation, the indexes hwBulkFileIndex and hwBulkFileIndexmust must be 
                issued together. When the statistical task is started, after the IOD is deleted, 
                it cannot be queried but still exists actually. 
                The deletion of the OID takes effect after the next report period.  
                "
            ::= { hwBulkOIDEntry 2  }
            
-- Object management table in the bulk file
    
        hwBulkIndexMgmt OBJECT IDENTIFIER ::= { hwBulkFile 3 }
    
        hwBulkObjectIndexCount OBJECT-TYPE
            SYNTAX Integer32
            MAX-ACCESS read-only
            STATUS current
            DESCRIPTION
                " 
                Total number of object indexes.
                "
            ::= { hwBulkIndexMgmt 1 }

        hwBulkObjectTable OBJECT-TYPE
            SYNTAX SEQUENCE OF HWBulkObjectEntry
            MAX-ACCESS  not-accessible
            STATUS current
            DESCRIPTION
                " 
                Object management table in the bulk file,
                providing add/delete operations.
                Prerequisite for the operation is that the 
                bulk file is listed in hwBulkFileTable 
                and the file state is ready.
                The indexes of this table are hwBulkObjectIndex and hwBulkFileIndex in hwBulkFileTable.
                The object hwBulkObjectOIDIndex can be used to configure a precise index or a fuzzy index.
                When one MIB object has multiple indexes, a '.' is used to separate the indexes.
                For example, in a MIB table with the shelf ID/slot ID/port ID as the index, 
                when you need to collect the information about shelf 0/slot 5/port 2,
                configure a precise index, namely, a character string 0.5.2.
                When you need to collect the information about all the ports in slot 5 of shelf 0, 
                configure a fuzzy index, namely, a character string 0.5.all. all is used to represent fuzzy index.
                When you need to collect the information about all the ports, use a fuzzy index all.all.all.
                In the case of the distributed bulk performance statistics, this table is not supported.              
                "
            ::= { hwBulkIndexMgmt 2 }
        
        hwBulkObjectEntry OBJECT-TYPE
            SYNTAX HWBulkObjectEntry 
            MAX-ACCESS not-accessible
            STATUS current
            DESCRIPTION
                "
                Object management table in the bulk file,
                providing add/delete operations.
                Prerequisite for the operation is that the 
                bulk file is listed in hwBulkFileTable 
                and the file state is ready.
                The indexes of this entry are hwBulkObjectIndex and hwBulkFileIndex in hwBulkFileTable.
                The object hwBulkObjectOIDIndex can be used to configure a precise index or a fuzzy index.
                When one MIB object has multiple indexes, a '.' is used to separate the indexes.
                For example, in a MIB table with the shelf ID/slot ID/port ID as the index, 
                when you need to collect the information about shelf 0/slot 5/port 2,
                configure a precise index, namely, a character string 0.5.2.
                When you need to collect the information about all the ports in slot 5 of shelf 0, 
                configure a fuzzy index, namely, a character string 0.5.all. all is used to represent fuzzy index.
                When you need to collect the information about all the ports, use a fuzzy index all.all.all.
                In the case of the distributed bulk performance statistics, this table is not supported.              
                "
            INDEX { hwBulkFileIndex,hwBulkObjectIndex }
            ::= { hwBulkObjectTable 1 }
        
        HWBulkObjectEntry ::= SEQUENCE 
            {
                hwBulkObjectIndex Integer32,
                hwBulkObjectOIDIndex OCTET STRING,
                hwBulkObjectLength Integer32,
                hwBulkObjectRowStatus RowStatus
            }
        
        hwBulkObjectIndex OBJECT-TYPE
            SYNTAX Integer32  
            MAX-ACCESS not-accessible
            STATUS current
            DESCRIPTION
                " 
                Object index in the Bulk file.
                A unique identifier for a record,
                indicating the sequence of objects.
                "
            ::= { hwBulkObjectEntry 1 }
        
        hwBulkObjectOIDIndex OBJECT-TYPE
            SYNTAX OCTET STRING(SIZE (1..63))
            MAX-ACCESS read-create
            STATUS current
            DESCRIPTION
                " 
                Start index of objects in a task,
                for each task there can be many start index.In order
                to get a value , a complete OID can be formed by adding the hwBulkOID in 
                hwBulkOIDTable and the hwBulkObjectOIDIndex from hwBulkObjectTable.
                "
            ::= { hwBulkObjectEntry 2 }

        hwBulkObjectLength OBJECT-TYPE
                SYNTAX Integer32
                MAX-ACCESS read-create
                STATUS obsolete
                DESCRIPTION
                    " 
                    Number of continuous objects. 
                    The default value is 1, indicating that only this object value will be collected.
                    "
                DEFVAL {1}
            ::= { hwBulkObjectEntry 3 }                                    
                                                                        
        hwBulkObjectRowStatus OBJECT-TYPE
            SYNTAX RowStatus
            MAX-ACCESS read-create
            STATUS current
            DESCRIPTION
                "
                Row operation object hwBulkObjectRowStatus. The enumeration value destroy (6)
                is used for the deletion.During the deletion operation, 
                the indexes hwBulkFileIndex and hwBulkObjectIndex must be issued together. 
                When the statistics file is running, 
                the deletion will take effect in the next report period after the deletion operation is performed.
                During the creation operation, hwBulkFileIndex and hwBulkObjectIndex must be issued together.
                Before the creation operation, make sure that hwBulkFileTable contains a statistical file.
                hwBulkObjectOIDIndex can be to configure a precise index or a fuzzy index. When one MIB object has multiple indexes, 
                a '.' is used to separate the indexes.
                For example, in a MIB table with the shelf ID/slot ID/port ID as the index, 
                when you need to collect the information about shelf 0/slot 5/port 2, configure a precise index, namely, a character string 0.5.2.
                When you need to collect the information about all the ports in slot 5 of shelf 0, configure a fuzzy index, namely, 
                a character string 0.5.all. all is used to represent fuzzy index.
                When you need to collect the information about all the ports, use a fuzzy index all.all.all. 
                The index with its index type configured to character string type is not supported.
                If the configured index is the same as the data that is already configured, the operation fails.               
                "
            ::= { hwBulkObjectEntry 4 }

-- Object CapItem table in the bulk file

        hwBulkObjectCapItemMgnt OBJECT IDENTIFIER ::= { hwBulkFile 5 }
        
        -- 1.3.6.1.4.1.2011.6.103.1.5.1
        hwBulkObjectCapItemTable OBJECT-TYPE
            SYNTAX SEQUENCE OF HwBulkObjectCapItemEntry
            MAX-ACCESS not-accessible
            STATUS current
            DESCRIPTION
                "
                This table is used to add or delete the statistical 
                index in the configuration of the statistics file.
                The indexes of this table are hwBulkObjectCapItem and hwBulkFileIndex in hwBulkFileTable.
                This table does not support the modify operation.
                In the case of the distributed bulk performance statistics, this table cannot be operated.
                "
            ::= { hwBulkObjectCapItemMgnt 1 }
        
        -- 1.3.6.1.4.1.2011.6.103.1.5.1.1
        hwBulkObjectCapItemEntry OBJECT-TYPE
            SYNTAX HwBulkObjectCapItemEntry
            MAX-ACCESS not-accessible
            STATUS current
            DESCRIPTION
                "
                This table is used to add or delete the statistical 
                index in the configuration of the statistics file.
                The indexes of this entry are hwBulkObjectCapItem and hwBulkFileIndex in hwBulkFileTable.
                This table does not support the modify operation.
                In the case of the distributed bulk performance statistics, this table cannot be operated.
                "
            INDEX { hwBulkFileIndex, hwBulkObjectCapItem }
            ::= { hwBulkObjectCapItemTable 1 }
        
        HwBulkObjectCapItemEntry ::= SEQUENCE 
            { 
                hwBulkObjectCapItem
                    Integer32,
                hwBulkObjectCapItemRowStatus
                    RowStatus
            }

        -- 1.3.6.1.4.1.2011.6.103.1.5.1.1.1
        hwBulkObjectCapItem OBJECT-TYPE
            SYNTAX Integer32
            MAX-ACCESS read-only
            STATUS current
            DESCRIPTION
                "
                Statistical task index, which is used for setting the performance data items for a statistical task.
                "
            ::= { hwBulkObjectCapItemEntry 1 }
        
        -- 1.3.6.1.4.1.2011.6.103.1.5.1.1.2
        hwBulkObjectCapItemRowStatus OBJECT-TYPE
            SYNTAX RowStatus
            MAX-ACCESS read-create
            STATUS current
            DESCRIPTION
                "
                Row operation object. When the statistics file is running, the statistical 
                index can be added or deleted. The adding or deletion takes effect after 
                the next period of the statistics file. Each statistics file can be configured
                with up to 256 statistical indexes. If the number of statistical indexes exceeds 256,
                you cannot add the statistical index any more.When the statistics file is running,
                at least one statistics file needs to be left undeleted. If the number of statistical 
                indexes is 1, you cannot delete the statistical index any more. 
                This restriction does not apply to the case of the non-running state of the statistics file.
                createAndGo(4)is supplied to create a new instance of a conceptual row.  
                destroy(6)is supplied to delete the instances associated with an existing conceptual row.              
                "
            ::= { hwBulkObjectCapItemEntry 2 }
        
        -- 1.3.6.1.4.1.2011.6.103.1.6
        hwBulkTrapVbOids OBJECT IDENTIFIER ::= { hwBulkFile 6 }
        
        -- 1.3.6.1.4.1.2011.6.103.1.6.1       
         hwTrapAutoBackupFileName OBJECT-TYPE
            SYNTAX OCTET STRING (SIZE (1..129)) 
            MAX-ACCESS accessible-for-notify
            STATUS current
            DESCRIPTION
                "
                The file name of auto-backup bulk file. The format of the file name is 'statistical task name_time_file index_[ipaddress]_[interval]'.
                Parameters ipaddress and interval are optional. 
                If the value of node hwBulkFileFormat is bulkASCIIWithZipFile(3), the file is a .zip file and the file name is 
                'statistical task name_time_file index_[ipaddress]_[interval].zip'.If the value of node hwBulkFileFormat is not 
                bulkASCIIWithZipFile(3), the file is not a .zip file.
                Statistical task names correspond to the values of parameter hwBulkFileName, and hwBulkFileName contains 1 to 63 characters.
                The time format for version2 is DDHHMM and that for version3 is YYYYMMDDHHMMSS. The time indicates the 
                time when the file is created for version2. The time indicates the start time of data collection for version3.
                File indexes correspond to the values of parameter hwBulkSaveFileIndex. 
                Ipaddress is the source IP address of TRAP.
                Parameter interval indicates data collection interval.
                File names can be generated automatically before transfer. 
                The length of the file name cannot be longer than 129 characters.
                "
            ::= { hwBulkTrapVbOids 1 }       
        
        -- 1.3.6.1.4.1.2011.6.103.1.7
        hwBulkTraps OBJECT IDENTIFIER ::= { hwBulkFile 7 }
        
        -- 1.3.6.1.4.1.2011.6.103.1.7.1
        hwBulkAlarmTraps OBJECT IDENTIFIER ::= { hwBulkTraps 1 }
        hwBulkAlarmTrapsPrefix OBJECT IDENTIFIER ::= { hwBulkAlarmTraps 0 }
        -- 1.3.6.1.4.1.2011.6.103.1.7.1.1
        hwBulkFileFailAlarmTrap NOTIFICATION-TYPE
            OBJECTS 
                { 
                    hwBulkFileIndex 
                }
            STATUS current
            DESCRIPTION 
                "
                This trap message is reported when the statistic file is created unsuccessfully.
                "
            ::= { hwBulkAlarmTrapsPrefix 1 }
        
        -- 1.3.6.1.4.1.2011.6.103.1.7.2
        hwBulkCommonTraps OBJECT IDENTIFIER ::= { hwBulkTraps 2 }
        
        hwBulkCommonTrapsPrefix OBJECT IDENTIFIER ::= { hwBulkCommonTraps 0 }
        
        -- 1.3.6.1.4.1.2011.6.103.1.7.2.1
        hwBulkBackupStartCommonTrap NOTIFICATION-TYPE
            OBJECTS 
                { 
                    hwBulkFileIndex, 
                    hwBulkSaveFileIndex, 
                    hwBulkSaveFileTime 
                }
            STATUS current
            DESCRIPTION 
                "
                When the centralized bulk performance statistic feature is enabled and a statistical task is started, 
                this trap message is reported after a statistical file is generated.
                When the distributed bulk performance statistic feature is enabled, this trap message is reported 
                after the host incorporates all the board files.
                "
            ::= { hwBulkCommonTrapsPrefix 1 }
        
        -- 1.3.6.1.4.1.2011.6.103.1.7.2.2
        hwBulkBackupSuccessCommonTrap NOTIFICATION-TYPE
            OBJECTS 
                { 
                    hwFTPClientIndex, 
                    hwFTPClientFileName, 
                    hwFTPDestFileName, 
                    hwFTPClientState 
                }
            STATUS current
            DESCRIPTION 
                "
                A trap message that contains the file backup result is reported after a statistical file is tried to back up on the NMS.
                "
            ::= { hwBulkCommonTrapsPrefix 2 }
        
        -- 1.3.6.1.4.1.2011.6.103.1.7.2.0.3
        hwBulkAutobackupSuccessTrap NOTIFICATION-TYPE
            OBJECTS 
               { 
                    hwTrapAutoBackupFileName, 
                    hwBulkFileIndex, 
                    hwBulkFileCopyNum
               }
            STATUS current      
                DESCRIPTION 
                    "
                    This trap message is reported when the statistical file is auto-backed up successfully on the NMS.          
                    "
        ::= { hwBulkCommonTrapsPrefix 3 }

        
        -- 1.3.6.1.4.1.2011.6.103.1.7.2.0.4
        hwBulkAutobackupFailTrap NOTIFICATION-TYPE
            OBJECTS 
               { 
                    hwTrapAutoBackupFileName, 
                    hwBulkFileIndex, 
                    hwBulkFileCopyNum,
                    hwLoadBackupResult
               }
            STATUS current      
                DESCRIPTION 
                    "
                    This trap message is reported when the statistical file is auto-backed up unsuccessfully on the NMS.          
                    "
        ::= { hwBulkCommonTrapsPrefix 4 }            
                
-- End of object management

        hwBulkFTPClient       OBJECT IDENTIFIER ::= { hwBulkStatistics 2 }
        hwFTPClientMgmt       OBJECT IDENTIFIER ::= { hwBulkFTPClient 1 }

-- FTP client management table

        hwFTPClientTableNextIndex OBJECT-TYPE
            SYNTAX  Integer32
            MAX-ACCESS read-only
            STATUS current
            DESCRIPTION
                "
                Next available index for table FTPClientTable. 
                If no available index, the value will be filled with '-1'. 
                "
            ::= { hwFTPClientMgmt 1 }
            
        hwFTPClientTable OBJECT-TYPE
            SYNTAX SEQUENCE OF HwFTPClientEntry
            MAX-ACCESS  not-accessible
            STATUS current
            DESCRIPTION
                "
                FTP client management table is used for transferring the statistics file,  
                and providing add/delete operations. The host servers as client, 
                while the NMS as server. The index of this table is hwFTPClientIndex.  
                The operation for this table can be successful only when the bulk 
                collection of the backup files is successful.
                "
            ::= { hwFTPClientMgmt 2 }
        
        hwFTPClientEntry OBJECT-TYPE
            SYNTAX HwFTPClientEntry
            MAX-ACCESS not-accessible
            STATUS current
            DESCRIPTION
                "
                FTP client management table is used for transferring the statistics file,  
                and providing add/delete operations. The host servers as client, 
                while the NMS as server. The index of this entry is hwFTPClientIndex.
                The operation for this table can be successful only when the bulk 
                collection of the backup files is successful.                                 
                "
            INDEX { hwFTPClientIndex }
            ::= { hwFTPClientTable 1 }
        
        HwFTPClientEntry ::= SEQUENCE 
            {
                hwFTPClientIndex Integer32,
                hwFTPClientMode INTEGER,
                hwFTPClientOper INTEGER,
                hwFTPClientFileName OCTET STRING,  
                hwFTPDestFileName OCTET STRING,  
                hwFTPClientServerIP IpAddress,
                hwFTPClientUserName OCTET STRING,
                hwFTPClientPasswd OCTET STRING,       
                hwFTPClientIfIndex Integer32,
                hwFTPClientState INTEGER,
                hwFTPClientRowStatus RowStatus,
                hwFTPClientServerPort Integer32,
                hwFTPClientNum Integer32
            }
        
        hwFTPClientIndex OBJECT-TYPE
            SYNTAX Integer32 (1..4)
            MAX-ACCESS accessible-for-notify
            STATUS current
            DESCRIPTION
                " 
                FTP client index, an unique identifier of a record.
                "
            ::= { hwFTPClientEntry 1 }
        
        hwFTPClientMode OBJECT-TYPE
                SYNTAX INTEGER
                {
                    ftp(1),
                    tftp(2),
                    sftp(3)
                }
                MAX-ACCESS read-create
                STATUS current
                DESCRIPTION
                    " 
                    FTP mode: ftp(1), tftp(2), sftp(3)
                    Options:
                    1.ftp(1)  -FTP client mode.
                    2.tftp(2) -TFTP client mode.
                    3.sftp(3) -SFTP client mode.
                    If FTP/SFTP is used to transfer files, hwFTPClientUserName and hwFTPClientPasswd need to be bound.
                    Binding is not required in the case of file transfer through TFTP. 
                    The specified port ID needs to be bound in the case of file transfer through SFTP.
                    "
            ::= { hwFTPClientEntry 2 }
        
        hwFTPClientOper OBJECT-TYPE
                SYNTAX INTEGER
                { 
                    putBinary(1) 
                }
                MAX-ACCESS read-create
                STATUS current
                DESCRIPTION
                    "
                    File transfer format. 
                    Options:
                    1.putBinary(1) -file transfer format is putBinary.
                    "
            ::= { hwFTPClientEntry 3 }
        
        hwFTPClientFileName OBJECT-TYPE
                SYNTAX OCTET STRING (SIZE (1..254))
                MAX-ACCESS read-create
                STATUS current
                DESCRIPTION
                    "
                    Source file name. In the case of centralized bulk performance statistics, 
                    the format is 'copy index of the latest file + / + name of the statistics file'.
                    For example, if the statistical task is ABCD and you need to obtain the second file, 
                    the file name of the hwFTPClientFileName is 2/ABCD.
                    In the case of distributed bulk performance statistics, 
                    the format is 'version of the file list|index of the file 1(hwBulkSaveFileIndex)/index 
                    of the statistical task 1(hwBulkFileIndex), file index 2/statistical task index 2......'.
                    For the file list version, only version2 and version3 are currently supported. For example, 
                    when the user needs to obtain the first, second, third, 
                    and fourth files with the statistical task index being 1 and the fifth, 
                    sixth, seventh and eighth files with the statistical task index being 6, 
                    then the value of the issued hwFTPClientFileName is version2|1/1,2/1,3/1,4/1,5/6,6/6,7/6,8/6.
                    "
                
            ::= { hwFTPClientEntry 4 }
        
        hwFTPDestFileName OBJECT-TYPE
                SYNTAX OCTET STRING (SIZE (1..254))
                MAX-ACCESS read-create
                STATUS current
                DESCRIPTION
                    "
                    Destination file name, including path. In the centralized bulk performance statistics collection, 
                    the format of the file name is 'path name + | + destination file name'.
                    For the purpose of saving FTP connections, when the NMS needs to obtain multiple statistics files, 
                    the Mput/Mget mode of FTP can be used. In this case, hwFTPClientFileName 
                    and hwFTPDestFileName must contain multiple file names.
                    The files are in the format of 'path|file name 1|file name 2|file name 3......'. 
                    Even if the path is null, the format must be '|file name 1|file name 2|file name 3......'. 
                    In hwFTPClientFileName, each file name corresponds to its own index. 
                    In hwFTPDestFileName, however, one path corresponds to multiple file names.
                    For example, when the path is c:\temp and two files need to be obtained, 
                    hwFTPDestFileName is in the format of 'c:\temp|file name 1|file name 2', 
                    and hwFTPClientFileName is in the format of '|1/ABCD|20/XYZ|30/XXXX'.
                    In the case of distributed bulk performance statistics, 
                    the format is 'version of the file list|path for uploading the file|device ID|day 
                    and time|file index (hwBulkSaveFileIndex)/index 
                    of the statistical task 1 (hwBulkFileIndex), file index/statistical 
                    task index (hwBulkFileIndex)......'.For the file list version, 
                    Version2 and version3 are currently supported. Path for uploading the file can be provided with
                    the drive letter, such as c:\temp. 
                    The time format for version 2 is DDHHMM and that for version3 is YYYYMMDDHHMMSS. The time indicates the 
                    time when the file is created for version2. The time indicates the start time of data collection for version3. 
                    The system automatically creates the time for version3. For example, if the user needs to transfer the first, 
                    second, third and fourth files under the device 7340032 and with the statistical index 
                    being 1 at 13:30:20 on the December 2, 2012, and the fifth, sixth, seventh,
                    and eighth files with the statistical index being 6 to the local directory of bulkfile, 
                    then the value of the issued hwFTPClientFileName is version2| bulkfile|
                    7340032|021330|1/1,2/1,3/1,4/1,5/6,6/6,7/6,8/6.If the version is version3,then the value of the issued 
                    hwFTPClientFileName is version3| bulkfile|||1/1,2/1,3/1,4/1,5/6,6/6,7/6,8/6.
                    It should be noted that the file lists (file sequence) in hwFTPClientFileName and 
                    hwFTPDestFileName must be completely the same.                    
                    The format of the file name is 'statistical task name (hwBulkFileName)_time_file index[_ipadress][_interval]'.                
                    In TFTP mode, the path cannot be configured.
                    hwBulkFileName contains 1 to 63 characters. 
                    The path specified for FTP/SFTP contains 1 to 63 characters. 
                    Therefore, the sum of hwBulkFileName and path cannot be longer than 128 characters.           
                    "
            ::= { hwFTPClientEntry 5 }

        hwFTPClientServerIP OBJECT-TYPE
                SYNTAX IpAddress
                MAX-ACCESS read-create
                STATUS current
                DESCRIPTION
                    " 
                    IP address of the FTP server.
                    "
            ::= { hwFTPClientEntry 6 }
        
        hwFTPClientUserName OBJECT-TYPE
                SYNTAX OCTET STRING (SIZE (0..31))      
                MAX-ACCESS read-create
                STATUS current
                DESCRIPTION
                    " 
                    User name for FTP/SFTP connection. For the TFTP mode, this field is invalid.
                    "
                DEFVAL  { ''H }
            ::= { hwFTPClientEntry 7 }
        
        hwFTPClientPasswd OBJECT-TYPE
                SYNTAX OCTET STRING (SIZE (0..15))      
                MAX-ACCESS read-create
                STATUS current
                DESCRIPTION
                    " 
                    Password for FTP/SFTP connection. For the TFTP mode, this field is invalid.
                    "
                DEFVAL  { ''H}
            ::= { hwFTPClientEntry 8 }  
            
        hwFTPClientIfIndex OBJECT-TYPE
                SYNTAX Integer32
                MAX-ACCESS read-create
                STATUS current
                DESCRIPTION 
                    "
                    IfIndex in the bulk file in order to get all data with IfIndex as the object index.
                    If the IfIndex equals to zero, the final file will be filled with all data in current memory.
                    "  
            ::= { hwFTPClientEntry 9 }
        
        hwFTPClientState OBJECT-TYPE
                SYNTAX INTEGER 
                { 
                    running(1), 
                    success(2), 
                    fileOpenFail(3), 
                    unreachableServerIp(4),
                    linkFailed(5),
                    authenticateFailed(6), 
                    fileReadFailed(7), 
                    fileWriteFailed(8),
                    failed(9)
                }
                MAX-ACCESS read-only
                STATUS current
                DESCRIPTION
                    " 
                    FTP operation status:                                                                              
                    Options:
                    1.running(1)            -indicates that FTP is running. If you set this object as running, 
                                             the FTP will be started.                
                    2.success(2)            -indicates that FTP completed successfully.                                                              
                    3.fileOpenFail(3)       -indicates that FTP failed. The cause is file open failure.                                         
                    4.unreachableServerIp(4)-indicates that FTP failed. The cause is that the IP 
                                             address of the server is not reachable. 
                    5.linkFailed(5)         -indicates that FTP failed. The cause is connecting to server failed.                                 
                    6.authenticateFailed(6) -indicates that FTP failed.
                                             The cause is authenticating failed.For FTP mode only.             
                    7.fileReadFailed(7)     -indicates that FTP failed. The cause is reading file failed.                                     
                    8.fileWriteFailed(8)    -indicates that FTP failed. The cause is writing file failed.
                    9.failed(9)             -indicates that FTP failed,General error.
                    "  
                                                        
            ::= { hwFTPClientEntry 10 }
        
        hwFTPClientRowStatus OBJECT-TYPE
            SYNTAX RowStatus
            MAX-ACCESS read-create
            STATUS current
            DESCRIPTION
                " 
                Row operation object.
                createAndGo(4)is supplied to create a new instance of a conceptual row.  
                destroy(6)is supplied to delete the instances associated with an existing conceptual row. 
                "
            ::= { hwFTPClientEntry 11 }
        
        hwFTPClientServerPort OBJECT-TYPE
            SYNTAX Integer32
            MAX-ACCESS read-create
            STATUS current
            DESCRIPTION
                "
                In SFTP port.FTP and TFTP modes, this field is invalid.
                "
            ::= { hwFTPClientEntry 12 }

         hwFTPClientNum OBJECT-TYPE
            SYNTAX Integer32
            MAX-ACCESS read-write
            STATUS current
            DESCRIPTION
                " 
                Indicates the maximum number of concurrent FTP/SFTP processes. For the TFTP mode, this field is invalid.
                "
            ::= { hwFTPClientEntry 13 }

        hwFTPClientMaxNum OBJECT-TYPE
            SYNTAX Integer32
            MAX-ACCESS read-only
            STATUS current
            DESCRIPTION
                "
                Indicates the maximum number of concurrent FTP/SFTP processes. For the TFTP mode, this field is invalid.
                "
            ::= { hwFTPClientMgmt 3 }

-- File management table
        
        hwTCAObjects OBJECT IDENTIFIER ::= { hwBulkStatistics 3 }
        
        hwTCAMgmt OBJECT IDENTIFIER ::= { hwTCAObjects 1 }
        
        hwDefineTCATable OBJECT-TYPE
            SYNTAX SEQUENCE OF HwDefineTCAEntry
            MAX-ACCESS not-accessible
            STATUS obsolete 
            DESCRIPTION
                "
                TCA Management Table. This object is not supported currently.
                The indexes of this table are hwDefineFacilityType, hwDefineMontype, hwDefineAid and hwDefineTmper.                
                "
            ::= { hwTCAMgmt 1 }
        
        hwDefineTCAEntry OBJECT-TYPE
            SYNTAX HwDefineTCAEntry
            MAX-ACCESS not-accessible
            STATUS obsolete 
            DESCRIPTION
                "
                TCA Management Table. This object is not supported currently.
                The indexes of this entry are hwDefineFacilityType, hwDefineMontype, hwDefineAid and hwDefineTmper.
                "
            INDEX { hwDefineFacilityType, hwDefineMontype, hwDefineAid, hwDefineTmper }
            ::= { hwDefineTCATable 1 }
        
        HwDefineTCAEntry ::= SEQUENCE 
            { 
                hwDefineFacilityType
                    INTEGER,
                hwDefineMontype
                    INTEGER,
                hwDefineAid
                    OCTET STRING,
                hwDefineTmper
                    INTEGER,
                hwDefineThlev
                    OCTET STRING,
                hwDefineRowStatus
                    RowStatus
             }

        hwDefineFacilityType OBJECT-TYPE
            SYNTAX INTEGER 
            { 
               system(1),
               igmp(2),
               dhcp(3),
               eapol(4), 
               vlan(5),
               ampeth(100),
               xdsladsl(200)               
            }
            MAX-ACCESS not-accessible
            STATUS obsolete 
            DESCRIPTION
                "
                Facility type. This object is not supported currently.
                Options:
                1.system(1)    -indicates facility type is system.
                2.igmp(2)      -indicates facility type is igmp.
                3.dhcp(3)      -indicates facility type is dhcp.
                4.eapol(4)     -indicates facility type is eapol. 
                5.vlan(5)      -indicates facility type is vlan.
                6.ampeth(100)  -indicates facility type is ampeth.
                7.xdsladsl(200)-indicates facility type is xdsladsl.                  
                "
            ::= { hwDefineTCAEntry 1 }
        
        hwDefineMontype OBJECT-TYPE
            SYNTAX INTEGER
            {
                cpu(1),
                memory(2),
                rxdd(3),
                rxdrq(4),
                rxdrl(5), 
                rxdi(6),
                rxuntrust(7),
                rxovl(8),
                rxovlopt(9),
                rxdisp(10),
                txdisp(11),
                rxgqpm(12),
                rxsqpm(13),
                rxrpv2m(14),
                rxerpv2m(15),
                rxrpv3m(16),
                rxerpv3m(17),
                rxlpm(18),
                txgqpm(19),
                txsqpm(20),
                txrpv2m(21),
                txerpv2m(22),
                txlpm(23),
                acpm(24),
                acum(25),
                rxinvpm(26),
                rxrpv1u(27),
                rxerpv1u(28),
                rxrpv2u(29),
                rxerv2u(30), 
                rxrpv3u(31),
                rxerpv3u(32),
                rxlpv2u(33),
                txgqpu(34),
                txsqpu(35),
                rxinvpu(36),
                rxeapf(37),
                txeapf(38),
                rxeapsf(39),
                rxeaplf(40),
                rxeaprf(41),
                rxeappf(42),
                rxieapf(43),
                rxleeapf(44),
                ethCrc(100),
                ethUnderpkt(101),
                ethOverpkt(102),
                ethStatsfrag(103),
                ethStajavvers(104),
                modemInitline(200),
                modemInitfial(201),
                modemFecs(202),
                modemEs(203),
                modemSes(204),
                modemLoss(205),
                modemUas(206),
                modemChcrc(207),
                modemChfec(208)
            }
            MAX-ACCESS not-accessible
            STATUS obsolete 
            DESCRIPTION
                "
                Type of the monitored object
                Options:
                1.cpu(1)        -cpu
                2.memory(2)     -memory
                3.rxdd(3)       -The number of DHCP DISCOVER.
                4.rxdrq(4)      -The number of DHCP REQUEST.
                5.rxdrl(5)      -The number of DHCP RELEASE.
                6.rxdi(6)       -The number of DHCP INFORM.
                7.rxuntrust(7)  -The number of DHCP Option82 Packets with Untrusted Option82.
                8.rxovl(8)      -The number of DHCP Option82 Packets exceed the maximum size 
                                 after appending option82.
                9.rxovlopt(9)   -The number of packets exceed the maximum option82 size.
                10.rxdisp(10)   -The number of Discarded Packets of Upstream data flow from user to server in vlan.
                11.txdisp(11)   -The number of Discarded Packets of Downstream data flow from server to user in vlan.
                12.rxgqpm(12)   -The number of IGMP General Query Packets Received in MVLAN.
                13.rxsqpm(13)   -The number of IGMP Specific Query Packets Received in MVLAN.
                14.rxrpv2m(14)  -The number of IGMP Report Packet of Version 2 Received in MVLAN.
                15.rxerpv2m(15) -The number of Error IGMP Report Packet of Version 2 Received in MVLAN.
                16.rxrpv3m(16)  -The number of IGMP Report Packets of Version 3 Received Per MVLAN.
                17.rxerpv3m(17) -The number of Error IGMP Report Packets of Version 3 Received in MVLAN.
                18.rxlpm(18)    -The number of IGMP Leave Packets Received in MVLAN.
                19.txgqpm(19)   -The number of IGMP General Query Packets Send Out in MVLAN.
                20.txsqpm(20)   -The number of IGMP Specific Query Packets Send Out in MVLAN.
                21.txrpv2m(21)  -The number of IGMP Report Packets of Version 2 Send Out in MVLAN.
                22.txerpv2m(22) -The number of IGMP Error Report Packets of Version 2 Send Out in Mvlan.
                23.txlpm(23)    -The number of IGMP Leave Packets Send Out in Mvlan.
                24.acpm(24)     -The number of IGMP Actived Programs in Mvlan.
                25.acum(25)     -The number of IGMP Actived Users in Mvlan.
                26.rxinvpm(26)  -The number of IGMP Invalid Packets Received in Mvlan.
                27.rxrpv1u(27)  -The number of IGMP Report Packets of Version v1 Received by user.
                28.rxerpv1u(28) -The number of IGMP Error Report Packets of Version v1 Received by user.
                29.rxrpv2u(29)  -The number of IGMP Report Packets of Version v2 Received by user.
                30.rxerv2u(30)  -The number of Error IGMP Report Packets of Version v2 Received by user.
                31.rxrpv3u(31)  -The number of IGMP Report Packets of Version v3 Received by user.
                32.rxerpv3u(32) -The number of Error IGMP Report Packets of Version v3 Received by user.
                33.rxlpv2u(33)  -The number of IGMP Leave Packets of Version v2 Received by user.
                34.txgqpu(34)   -The number of IGMP General Query Packets Send Out by user.
                35.txsqpu(35)   -The number of IGMP Specific Query Packets Send Out by user.
                36.rxinvpu(36)  -The number of IGMP Invalid Packets Received by user.
                37.rxeapf(37)   -The number of EAPOL Frames of any type that have been received.
                38.txeapf(38)   -The number of EAPOL Frames of any type that have been transmitted.
                39.rxeapsf(39)  -The number of EAPOL Start Frames that have been received.
                40.rxeaplf(40)  -The number of EAPOL Logoff frames that have been received.
                41.rxeaprf(41)  -The number of EAPOL Resp/Id Frames that have been received.
                42.rxeappf(42)  -The number of Valid EAPOL Response Frames (other than Resp/Id frames)
                                 that have been received.
                43.rxieapf(43)  -The number of Invalid EAPOL frames that have been  received.
                44.rxleeapf(44) -The number of Length Error EAPOL frames that have been received.
                45.ethCrc(100) -The total number of packets received that had a length of between 64 and 1518 , 
                                 but had a bad FCS.
                46.ethUnderpkt(101)-The total number of packets received that were less than 64 octets long
                                 and were otherwise well formed.
                47.ethOverpkt(102)-The total number of packets received that were longer than 1518 octets 
                                 and were otherwise well formed.
                48.ethStatsfrag(103)-The total number of packets received that were less than 64 octets in 
                                 length and had a bad FCS.
                49.ethStajavvers(104)-The total number of packets received that were nlonger than 1518 octets 
                                  had either a bad FCS.
                50.modemInitline(200)-Count of full initializations attempted on the line since agent reset.
                51.modemInitfial(201)-Count of failed full initializations on the line since agent reset.
                52.modemFecs(202)-Count of seconds since agent reset that there was at least one FEC.
                53.modemEs(203)-Count of seconds since agent reset that there was ATU-C and ATU-R.
                                 (ATU-C: CRC-8 &gt;= 1 for one or more bearer channels OR
                                 LOS &gt;= 1 OR SEF &gt;= 1 OR LPR &gt;= 1
                                 ATU-R: FEBE &gt;= 1 for one or more bearer channels OR
                                 LOS-FE &gt;= 1 OR RDI &gt;= 1 OR LPR-FE &gt;= 1.)
                54.modeMses(204)-Count of seconds since agent reset that there was ATU-C and ATU-R.
                                  (ATU-C: (CRC-8 summed over all bearer channels) &gt;= 18 OR
                                   LOS &gt;= 1 OR SEF &gt;= 1 OR LPR &gt;= 1
                                   ATU-R: (FEBE summed over all bearer channels) &gt;= 18 OR
                                   LOS-FE &gt;= 1 OR RDI &gt;= 1 OR LPR-FE &gt;= 1)
                55.modemLoss(205)-Count of seconds since agent reset that there was LOS.
                56.modemUas(206) -Count of seconds in Unavailability State since agent reset.
                57.modemChcrc(207)-Count of CRC-8 anomalies occurring in the channel since agent reset.
                58.modemChfec(208)-Count of FEC anomalies occurring in the channel since agent reset.
                This object is not supported currently. 
                "
            ::= { hwDefineTCAEntry 2 }
        
        hwDefineAid OBJECT-TYPE
            SYNTAX OCTET STRING
            MAX-ACCESS not-accessible
            STATUS obsolete 
            DESCRIPTION
                "
                Index of the monitored object. This object is not supported currently.
                "
            ::= { hwDefineTCAEntry 3 }
        
        hwDefineTmper OBJECT-TYPE
            SYNTAX INTEGER
            {
                fifteenMinutes(1),
                oneday(2)
            }
            MAX-ACCESS not-accessible
            STATUS obsolete
            DESCRIPTION
                "
                Monitoring period. This object is not supported currently.
                Options: 
                1.fifteenMinutes(1) -monitoring period is fifteen minutes.
                2.oneday(2)         -monitoring period is one day.
                "
            ::= { hwDefineTCAEntry 4 }
        
        hwDefineThlev OBJECT-TYPE
            SYNTAX OCTET STRING (SIZE (1..6))
            MAX-ACCESS read-create
            STATUS obsolete 
            DESCRIPTION
                "
                Threshold of the monitored object. This object is not supported currently.
                "
            ::= { hwDefineTCAEntry 5 }
        
        hwDefineRowStatus OBJECT-TYPE
            SYNTAX RowStatus
            MAX-ACCESS read-create
            STATUS obsolete 
            DESCRIPTION
                "
                Row status. This object is not supported currently.
                "
            ::= { hwDefineTCAEntry 6 }
        -- Batch Query table   
       
        hwBatchQuery OBJECT IDENTIFIER ::= { hwBulkStatistics 4 }
        
        hwBatchQueryMgmt OBJECT IDENTIFIER ::= { hwBatchQuery 1 }

       
       -- Batch Query Capability table 
               
        hwBQueryCapabilityTable OBJECT-TYPE
            SYNTAX SEQUENCE OF   HwBQueryCapabilityEntry
            MAX-ACCESS not-accessible
            STATUS current 
            DESCRIPTION
                "
                The index of this table is hwBatchQueryType.                
                "
            ::= { hwBatchQueryMgmt 1 }
        
        hwBQueryCapabilityEntry OBJECT-TYPE
            SYNTAX HwBQueryCapabilityEntry
            MAX-ACCESS not-accessible
            STATUS current 
            DESCRIPTION
                "
                The index of this entry is hwBatchQueryType.  
                "
            INDEX { hwBatchQueryType }
            ::= { hwBQueryCapabilityTable 1 }
        
        HwBQueryCapabilityEntry ::= SEQUENCE 
            {  
                hwBatchQueryType
                    Integer32,
                hwBatchQueryCapability
                    OCTET STRING
             }

        hwBatchQueryType OBJECT-TYPE
            SYNTAX Integer32
            MAX-ACCESS not-accessible
            STATUS current 
            DESCRIPTION
                "
                Batch Query type. 
                Options: 
                1.ontinfo(1)-ont info.
                2.ontMulticastForwardingTable(2)-ont multicast forwarding table.
                3.ontLearnedMac(3)-ont learned MAC.   
                4.macinfo(4)-MAC info.  
                5.xdslSegmentinfo(5)- status parameters of XDSL subcarriers.                           
                6.ontWifiExtendedInfo(6)-ont wifi used state and attached AP Info.                           
                "
            ::= { hwBQueryCapabilityEntry 1 }
        
        hwBatchQueryCapability OBJECT-TYPE
            SYNTAX OCTET STRING (SIZE (1..256))
            MAX-ACCESS read-only
            STATUS current 
            DESCRIPTION
                "
                Indicates the batch query capability. The capability is in the TLV format.
                The format of the TLV is shown in the following figure.
                ---------------------------------------------------------
                | TOTAL-LENGTH | TLV-TYPE  |  TLV-LENGTH  |  TLV-VALUE  | 
                ---------------------------------------------------------
                               | TLV-TYPE  |  TLV-LENGTH  |  TLV-VALUE  | 
                               ------------------------------------------                
                               |   .................................    |
                               |-----------------------------------------
                               | TLV-TYPE  |  TLV-LENGTH  |  TLV-VALUE  | 
                               ------------------------------------------
                TOTAL-LENGTH occupies two bytes to store the whole length of all the TLV, including TOTAL-LENGTH itself.
                TLV-TYPE occupies two bytes to store the TLV type.
                TLV-LENGTH occupies two bytes to store the TLV length, which indicates the bytes TLV-VALUE occupies.                                   
                TLV-VALUE is the content of the TLV.                               
                                               
                Assume that the ONT supported-capability is 00.17.00.00.00.04.00.00.00.3F.00.01.00.04.01.00.01.01.00.02.00.01.00. 
                The capability description is as follows:
                ----------------------
                |  TLV total length  |
                |        00.17       |
                -----------------------------------------------
                |  TLV1 type  |  TLV1 length  |  TLV1 value   |
                |    00.00    |     00.04     |  00.00.00.3F  |
                ----------------------------------------------- 
                |  TLV2 type  |  TLV2 length  |  TLV2 value   |
                |    00.01    |     00.04     |  01.00.01.01  |
                -----------------------------------------------
                |  TLV3 type  |  TLV3 length  |  TLV3 value   |
                |    00.02    |     00.01     |      00       |
                -----------------------------------------------         
                TLV total length:
                  00.17: the total length of the TLV is 23 Bytes.
                TLV1:
                  00.00: it is the field submask supported by the batch query.
                  00.04: the length of the TLV1 value is 4 Bytes.
                  00.00.00.3F: this value indicates that the supported fields are 0, 1, 2, 3, 4, and 5.
                TLV2:
                  00.01: it is the TLV type list supported by the batch query.
                  00.04: the length of the TLV2 value is 4 Bytes.
                  01.00.01.01: this value indicates that values 256 and 257 are supported.
                TLV3:
                  00.02: it indicates whether the batch query to be delayed.
                  00.01: the length of the TLV3 value is 1 Bytes.
                  00: it indicates that the batch query does not need to be delayed.
                "
            ::= { hwBQueryCapabilityEntry 2 }
        
        -- Batch Query Set table 
                
        hwBatchQuerySetTable OBJECT-TYPE
            SYNTAX SEQUENCE OF   HwBatchQuerySetEntry
            MAX-ACCESS not-accessible
            STATUS current 
            DESCRIPTION
                "
                The index of this table is hwBatchQuerySn.                
                "
            ::= { hwBatchQueryMgmt 2 }
        
        hwBatchQuerySetEntry OBJECT-TYPE
            SYNTAX HwBatchQuerySetEntry
            MAX-ACCESS not-accessible
            STATUS current 
            DESCRIPTION
                "
                The index of this entry is hwBatchQuerySn.  
                "
            INDEX { hwBatchQuerySn }
            ::= { hwBatchQuerySetTable 1 }
        
        HwBatchQuerySetEntry ::= SEQUENCE 
            { 
                hwBatchQuerySn
                    Integer32, 
                hwBatchQueryCurrentType
                    Integer32,                
                hwBatchQueryParameter
                    OCTET STRING,    
                hwBatchQueryRowStatus
                    RowStatus 
             }

        hwBatchQuerySn OBJECT-TYPE
            SYNTAX Integer32 
            MAX-ACCESS accessible-for-notify
            STATUS current 
            DESCRIPTION
                "
                Batch query SN.              
                "
            ::= { hwBatchQuerySetEntry 1 }
        
        hwBatchQueryCurrentType OBJECT-TYPE
            SYNTAX Integer32
            MAX-ACCESS read-write
            STATUS current 
            DESCRIPTION
                "
                Current batch query type.
                Options: 
                1.ontinfo(1)-ont info.
                2.ontMulticastForwardingTable(2)-ont multicast forwarding table.  
                3.ontLearnedMac(3)-ont learned MAC.     
                4.macinfo(4)-MAC info. 
                5.xdslSegmentinfo(5) - status parameters of XDSL subcarriers.        
                6.ontWifiExtendedInfo(6)-ont wifi used state and attached AP Info.        
                "
            ::= { hwBatchQuerySetEntry 2 }     
            
         hwBatchQueryParameter OBJECT-TYPE
            SYNTAX OCTET STRING (SIZE (1..256))
            MAX-ACCESS read-write
            STATUS current 
            DESCRIPTION
                "
                Indicates the batch query parameter to set. The parameter is in the TLV format and supports a maximum of 255 characters. 
                The format of the TLV is shown in the following figure.                             
                The batch query can be based on board, port, or specific fields. 
                ---------------------------------------------------------
                | TOTAL-LENGTH | TLV-TYPE  |  TLV-LENGTH  |  TLV-VALUE  | 
                ---------------------------------------------------------
                               | TLV-TYPE  |  TLV-LENGTH  |  TLV-VALUE  | 
                               ------------------------------------------                
                               |   .................................    |
                               |-----------------------------------------
                               | TLV-TYPE  |  TLV-LENGTH  |  TLV-VALUE  | 
                               ------------------------------------------
                TOTAL-LENGTH occupies two bytes to store the whole length of all the TLV, including TOTAL-LENGTH itself.
                TLV-TYPE occupies two bytes to store the TLV type. 
                TLV-LENGTH occupies two bytes to store the TLV length, which indicates the bytes TLV-VALUE occupies.                                   
                TLV-VALUE is the content of the TLV.        
        
                For example, 00.0B.01.00.00.05.00.0C.02.00.02 indicates querying the multicast forwarding entries for ONT 2 based on subrack ID/slot ID/port ID 0/12/2.
                The parameter description is as follows:
                ----------------------
                |  TLV total length  |
                |        00.0B       |
                --------------------------------------------------
                |  TLV1 type  |  TLV1 length  |   TLV1 value     |
                |    01.00    |     00.05     |  00.0C.02.00.02  |
                --------------------------------------------------  
                TLV total length:
                  00.0B: the total length of the TLV is 11 Bytes.
                TLV1:
                  01.00: indicates a query based on ONT.
                  00.05: the length of the TLV1 value is 5 Bytes
                  00.0C.02.00.02: indicates a query on the ONT 2 connected to port 0/12/2.

                For example, 00.0F.01.01.00.09.00.0C.02.00.02.00.01.00.01 indicates querying the multicast forwarding entries for ETH port 1 on ONT 2 connected to port 0/12/2.
                The parameter description is as follows:
                ----------------------
                |  TLV total length  |
                |        00.0F       |
                --------------------------------------------------------------
                |  TLV1 type  |  TLV1 length  |   TLV1 value                 |
                |    01.01    |     00.09     |  00.0C.02.00.02.00.01.00.01  |
                --------------------------------------------------------------  
                TLV total length:
                  00.0F: the total length of the TLV is 15 Bytes.
                TLV1:
                  01.01: indicates a query based on a port on the ONT. Currently, only the ETH type is supported. 
                  00.09: the length of the TLV1 value is 9 Bytes
                  00.0C.02.00.02.00.01.00.01: indicates the query for ETH port 1 on ONT 2 connected to port 0/12/2.
                  
                For example, 00.0A.01.01.00.04.00.00.0A.02 indicates that the dynamic MAC address is queried by port and frame ID/slot ID/port ID is 0/10/2.
                The parameter description is as follows:
                ----------------------
                |  TLV total length  |
                |        00.0A       |
                --------------------------------------------------
                |  TLV1 type  |  TLV1 length  |   TLV1 value     |
                |    01.01    |     00.04     |  00.00.0A.02     |
                --------------------------------------------------  
                TLV total length:
                  00.0A: indicates that the total length of the TLV is 10 bytes.
                TLV1:
                  01.01: indicates the mode by which a dynamic MAC address is queried. 257 indicates that the dynamic MAC address is queried by port.
                  00.04: indicates that the length of the TLV1 value is 4 bytes.
                  00.00.0A.02: indicates a query on port 0/10/2.

                For example, 00.0A.01.03.00.04.00.02.FF.FF indicates that the dynamic MAC address is queried by VLAN and the VLAN ID is 2.
                The parameter description is as follows:
                ----------------------
                |  TLV total length  |
                |        00.0A       |
                --------------------------------------------------
                |  TLV1 type  |  TLV1 length  |   TLV1 value     |
                |    01.03    |     00.04     |  00.02.FF.FF     |
                --------------------------------------------------  
                TLV total length:
                  00.0A: indicates that the total length of the TLV is 10 bytes.
                TLV1:
                  01.03: indicates the mode by which a dynamic MAC address is queried. 259 indicates that the dynamic MAC address is queried by VLAN.
                  00.04: indicates that the length of the TLV1 value is 4 bytes.
                  00.02: indicates a query on VLAN ID 2.
                  FF.FF: indicates reserved bytes.

                For example, 00.0A.01.07.00.04.00.00.00.01 indicates that the dynamic MAC address is queried by serivce port and the service-port ID is 1.
                The parameter description is as follows:
                ----------------------
                |  TLV total length  |
                |        00.0A       |
                --------------------------------------------------
                |  TLV1 type  |  TLV1 length  |   TLV1 value     |
                |    01.07    |     00.04     |  00.00.00.01     |
                --------------------------------------------------  
                TLV total length:
                  00.0A: indicates that the total length of the TLV is 10 bytes.
                TLV1:
                  01.07: indicates the mode by which a dynamic MAC address is queried. 263 indicates that the dynamic MAC address is queried by service port.
                  00.04: indicates that the length of the TLV1 value is 4 bytes.
                  00.00.00.01: indicates a query on service-port ID 1.
                  
                For example, 00.13.01.00.00.05.00.00.01.01.01.01.01.00.04.00.00.00.04 indicates that the XDSL subcarriers is queried by port,and frame ID/slot ID/port ID is 0/1/1,
                the direction of the subcarrier is upstream.
                The parameter description is as follows:
                ----------------------
                |  TLV total length  |
                |        00.13       |
                --------------------------------------------------
                |  TLV1 type  |  TLV1 length  |   TLV1 value     |
                |    01.00    |     00.05     |  00.00.01.01.01  |
                --------------------------------------------------
                |  TLV2 type  |  TLV2 length  |   TLV2 value     |
                |    01.01    |     00.04     |  00.00.00.04     |
                --------------------------------------------------   
                TLV total length:
                  00.13: indicates the total length of the TLV is 19 bytes.
                TLV1:
                  01.00: indicates the port and upstream or downstream direction of the subcarrier.
                  00.05: indicates the length of the TLV1 value is 4 bytes.
                  00.00.01.01.01: indicates a query on frame 0 slot 1 port 1,the subcarrier direction is upstream.
                  
                TLV2:
                  01.01: indicates the type of this query.
                  00.04: indicates that the length of the TLV2 value is 5 bytes.
                  00.00.00.04: indicates the type is Quiet Line Noise values.
                  TLV2 value is subcarrier type,each bit represents one type,the subcarrier type is as follows:
                  bit0 :real component of HLIN
                  bit1 :imaginary component of HLIN 
                  bit2 :Hlog
                  bit3 :Quiet Line Noise
                  bit4 :SNR Margin. 
                  bit5 :the bits allocation per subcarrier
                  bit6 :the gain allocation per subcarrier
                  bit7 :the TxPSD per subcarrier.
                  bit8 :the SnrMargin per subcarrier.
                  bit9 :Quiet Line Noise with vector
                  bit10:the RMC bits allocation per subcarrier
		  
                For example, 00.10.01.FF.00.0A.00.00.00.00.00.00.00.00.00.00 indicates that the ont wifi used state and attached AP Info is queried by FramID and the FramID is 0.
                The parameter description is as follows:
                ----------------------
                |  TLV total length  |
                |        00.10       |
                --------------------------------------------------------------------
                |  TLV1 type  |  TLV1 length  |   TLV1 value                       |
                |    01.FF    |     00.0A     |  00.00.00.00.00.00.00.00.00.00     |
                --------------------------------------------------------------------  
                TLV total length:
                  00.10: indicates that the total length of the TLV is 16 bytes.
                TLV1:
                  01.FF: indicates a query based on frame. 
                  00.0A: indicates that the length of the TLV1 value is 10 bytes.
                  00.00.00.00.00.00.00.00.00.00: indicates a query on frame ID 0.
                "
            ::= { hwBatchQuerySetEntry 3 }  
            
          hwBatchQueryRowStatus OBJECT-TYPE
            SYNTAX RowStatus
            MAX-ACCESS read-create
            STATUS current 
            DESCRIPTION
                "
                Row operation object. 
                createAndGo(4)is supplied to create a new instance of a conceptual row.  
                destroy(6)is supplied to delete the instances associated with an existing conceptual row..
                "
            ::= { hwBatchQuerySetEntry 4 }
            
        -- Batch Query Get table 
                
        hwBatchQueryGetTable OBJECT-TYPE
            SYNTAX SEQUENCE OF   HwBatchQueryGetEntry
            MAX-ACCESS not-accessible
            STATUS current 
            DESCRIPTION
                "
                The indexes of this table are hwBatchQuerySn and hwBatchQueryStartNo.                
                "
            ::= { hwBatchQueryMgmt 3 }
        
        hwBatchQueryGetEntry OBJECT-TYPE
            SYNTAX HwBatchQueryGetEntry
            MAX-ACCESS not-accessible
            STATUS current 
            DESCRIPTION
                "
                The indexes of this entry are hwBatchQuerySn and hwBatchQueryStartNo.  
                "
            INDEX { hwBatchQuerySn,hwBatchQueryStartNo }
            ::= { hwBatchQueryGetTable 1 }
        
        HwBatchQueryGetEntry ::= SEQUENCE 
            { 
                hwBatchQueryStartNo
                    Integer32,  
                hwBatchQueryReturnNum  
                    Integer32,            
                hwBatchQueryReturnList
                    OCTET STRING,    
                hwBatchQueryIsLast
                    INTEGER 
             }

        hwBatchQueryStartNo OBJECT-TYPE
            SYNTAX Integer32            
            MAX-ACCESS not-accessible
            STATUS current 
            DESCRIPTION
                "
                Batch query Start NO.
                "
            ::= { hwBatchQueryGetEntry 1 }  
            
         hwBatchQueryReturnNum OBJECT-TYPE
            SYNTAX Integer32
            MAX-ACCESS read-only
            STATUS current 
            DESCRIPTION
                "
                Batch query return number .
                "
            ::= { hwBatchQueryGetEntry 2 }     
            
         hwBatchQueryReturnList OBJECT-TYPE
            SYNTAX OCTET STRING 
            MAX-ACCESS read-only
            STATUS current 
            DESCRIPTION
                "
                List of batch query result.
                For example, MAC addresses queried in batches are as follows:
                00.00.00.8C.02.01.0A.F0.00.00.00.01.01.02.FF.FF.FF.FF.FF.FF.FF.FF.00.00.0A.02.FF.FF.FF.FF.FF.FF.02.01.0A.F0.00.00.00.01.03.02.FF.FF.FF.FF.FF.FF.FF.FF.00.00.0A.02.FF.FF.FF.FF.FF.FF.02.01.0A.F0.00.00.00.01.02.02.FF.FF.FF.FF.FF.FF.FF.FF.00.00.0A.02.FF.FF.FF.FF.FF.FF.02.01.0A.F0.00.00.00.01.04.02.FF.FF.FF.FF.FF.FF.FF.FF.00.00.0A.02.FF.FF.FF.FF.FF.FF.02.01.00.01.00.E0.A1.26.00.52.FF.FF.FF.FF.FF.FF.FF.FF.00.00.0A.02.FF.FF.FF.FF.FF.FF
                Parameters are described as follows:
                00.00: 2 bytes, indicating queried data type.
                00.8C: 2 bytes, indicating the total length of queried MAC addresses.
                The length of MAC information is 28 bytes. 
		The query results for MAC addresses are as follows:
                (1)02.01.0A.F0.00.00.00.01.01.02.FF.FF.FF.FF.FF.FF.FF.FF.00.00.0A.02.FF.FF.FF.FF.FF.FF
                (2)02.01.0A.F0.00.00.00.01.03.02.FF.FF.FF.FF.FF.FF.FF.FF.00.00.0A.02.FF.FF.FF.FF.FF.FF
                (3)02.01.0A.F0.00.00.00.01.02.02.FF.FF.FF.FF.FF.FF.FF.FF.00.00.0A.02.FF.FF.FF.FF.FF.FF
                (4)02.01.0A.F0.00.00.00.01.04.02.FF.FF.FF.FF.FF.FF.FF.FF.00.00.0A.02.FF.FF.FF.FF.FF.FF
                (5)02.01.00.01.00.E0.A1.26.00.52.FF.FF.FF.FF.FF.FF.FF.FF.00.00.0A.02.FF.FF.FF.FF.FF.FF
                
                Five MAC addresses are parsed in the similar way. The parsing for the first MAC address is as follows: 
                02: 1 byte, indicating the MAC address type (1.Static MAC address; 2.Dynamic MAC address; 3.MAC anti-spoof).
                01: 1 byte, indicating the MAC address location (1.MAC address with other physical locations; 2. MAC address on the Meth interface; 3. MAC address on the PW).
                0A.F0: 2 bytes, indicating that the VLAN ID is 2800.                
                00.00.00.01.01.02: 6 bytes, indicating that the MAC address is 0000-0001-0102.
                FF.FF: 2 bytes, indicating a reserved field.
                FF.FF.FF.FF: 4 bytes, indicating the flow index (FFFFFFFF is an invalid value).
                FF.FF: 2 bytes, indicating the bundle index (FFFF is an invalid value).
                00.00.0A.02: 4 bytes, indicating that frame ID/slot ID/port ID is 0/10/2.
                FF.FF: 2 bytes, indicating VPI. In xPON profile mode, it is ONT ID; In xPON distributing mode, it is Gemport ID (FFFF is an invalid value).
                FF.FF: 2 bytes, indicating VCI. In xPON profile mode, it is GEM index (FFFF is an invalid value).
                FF.FF: 2 bytes, indicating a reserved field.
                "
            ::= { hwBatchQueryGetEntry 3 }  
            
          hwBatchQueryIsLast OBJECT-TYPE
            SYNTAX INTEGER
            {
                islast(1),
                notlast(2)
            }
            MAX-ACCESS read-only
            STATUS current 
            DESCRIPTION
                "
                The result of batch query is the last one or not.
                Options: 
                1.islast(1)-last.
                2.notlast(2)-not last.        
                
                "
            ::= { hwBatchQueryGetEntry 4 }  
            
        hwBatchQueryTrapVbOids OBJECT IDENTIFIER ::= { hwBatchQuery 2 }
        hwBatchQueryResult OBJECT-TYPE
            SYNTAX Integer32
            MAX-ACCESS accessible-for-notify
            STATUS current
            DESCRIPTION
                "
                The result of batch query. 
                "
            ::= { hwBatchQueryTrapVbOids 1 }
        
        hwBatchQueryTraps OBJECT IDENTIFIER ::= { hwBatchQuery 3 }
        hwBatchQueryCommonTraps OBJECT IDENTIFIER ::= { hwBatchQueryTraps 1 }
        hwBatchQueryCommonTrapsPrefix OBJECT IDENTIFIER ::= { hwBatchQueryCommonTraps 0 }
        
        hwBatchQueryResultTrap NOTIFICATION-TYPE
            OBJECTS 
            { 
                hwBatchQuerySn, 
                hwBatchQueryResult 
            }
            STATUS current
            DESCRIPTION
                "
                This trap message is reported when the batch query is complete.
                "
            ::= { hwBatchQueryCommonTrapsPrefix 1 }                         

                --hwCollectSet

        hwCollectSet       OBJECT IDENTIFIER ::= { hwCfgInfoCollect 1 }
                
        hwCollectSetTable OBJECT-TYPE
            SYNTAX SEQUENCE OF HwCollectSetEntry
            MAX-ACCESS  not-accessible
            STATUS current
            DESCRIPTION
                " 
                NMS collect information table, providing add/modify/delete operations.
                The host severs as client, while the NMS as server.
                The index of this table is hwCollectTableName.
                "
            ::= { hwCollectSet 1 }
        
        hwCollectSetEntry OBJECT-TYPE
            SYNTAX HwCollectSetEntry
            MAX-ACCESS not-accessible
            STATUS current
            DESCRIPTION
                " 
                NMS collect information table, providing add/modify/delete operations.
                The host severs as client, while the NMS as server.
                The index of this entry is hwCollectTableName.
                "
            INDEX { IMPLIED hwCollectTableName }
            ::= { hwCollectSetTable 1 }
        
        HwCollectSetEntry ::= SEQUENCE 
            {
                hwCollectTableName OCTET STRING,
                hwCollectOID OCTET STRING,
                hwCollectTableRowStatus RowStatus
            }
                
        hwCollectTableName OBJECT-TYPE
            SYNTAX OCTET STRING (SIZE (1..63))
            MAX-ACCESS not-accessible
            STATUS current
            DESCRIPTION
                "
                The table name. It is in the format of ASCII code separated by '.'. 
                If the table name is specified to a|b, the index is 97.124.98.
                Naming standard: In a table name, there should be one vertical line at most, 
                and the left side and right side of the vertical line cannot be null. 
                For example, identifier|table name or table name. The ASCII codes must be from 0x21 to 0x7E. 
                In the configuration phase, when a table name requires to be added, format identifier|all or all cannot be used.
                "
            ::= { hwCollectSetEntry 1 }
            
        hwCollectOID OBJECT-TYPE
            SYNTAX OCTET STRING (SIZE (0..127))
            MAX-ACCESS read-write
            STATUS current
            DESCRIPTION
                "
                Information of the OIDs. When the NMS adds the information about the entries, 
                the value of the information in the format of 'parent object OID:OID of sub object 1,
                OID of sub object 2......'. This format is called entry object character string hereinafter. 
                The MIB object of the entry OID can be only the OID of the entry object. 
                For the scalar object, the OID of the parent object is directly used.           
                For example, to collect statistics of the objects 
                1.3.6.1.4.1.2011.6.3.4.1.3, 1.3.6.1.4.1.2011.6.3.4.1.4, 
                and 1.3.6.1.4.1.2011.6.3.4.1.1.5 in hwCpuDevTable, you need to enter the 
                objects in the format of '1.3.6.1.4.1.2011.6.3.4.1:3,4,5'.
                "
            ::= { hwCollectSetEntry 2 }
            
        hwCollectTableRowStatus OBJECT-TYPE
            SYNTAX RowStatus
            MAX-ACCESS read-create
            STATUS current
            DESCRIPTION
                "                           
                Row status.
                createAndGo(4) is supplied to create a new instance of a conceptual row.  
                destroy(6) is supplied to delete the instances associated with an existing conceptual row. 
                "
            ::= { hwCollectSetEntry 3 }
            
-- hwCollectOperationSet

        hwCollectOperationSet       OBJECT IDENTIFIER ::= { hwCfgInfoCollect 2 }

        hwCollectState OBJECT-TYPE
            SYNTAX INTEGER
            {
                idle(1),
                collecting(2),
                waitfetch(3),
                tranfering(4)
            }
            MAX-ACCESS read-only
            STATUS current
            DESCRIPTION
                "
                Operation status of the information collection.
                Options:
                1.idle(1)        -indicates that the operation is in the idle state.
                2.collecting(2)  -indicates that the information is being collected.
                3.waitfetch(3)   -indicates that the information collection is complete and the data is to be extracted.
                4.tranfering(4)  -indicates that the file is being transferred.
                "
            ::= { hwCollectOperationSet 1 }
                
        hwCollectOperation OBJECT-TYPE
            SYNTAX INTEGER
            {
                begin(1),
                stop(2),
                processing(3)
            }
            MAX-ACCESS read-create
            STATUS current
            DESCRIPTION
                "               
                Administration operation of the information collection.
                Options:
                1.begin(1)     -indicates that the information collection starts.
                2.stop(2)      -indicates that the information collection stops.
                3.processing(3)-indicates that the collection is ongoing.
                In the begin and stop operations, the object hwCollectTableInfo needs to be bound.
                "
            ::= { hwCollectOperationSet 2 }
            
        hwCollectTableInfo OBJECT-TYPE
            SYNTAX OCTET STRING (SIZE (0..510))
            MAX-ACCESS read-write
            STATUS current
            DESCRIPTION
                "
                Information of the table. This object is used for informing the host of the name of the entry 
                that needs to be collected before the collection is started. 
                If there are multiple entries, a comma is used to separate them.
                For example, if the NMS has already configured three tables of entries, namely, a|b, a|c, 
                and a|d, this parameter can be set to a|b,a|c before the information collection is started. 
                It indicates that information in a|b and a|c needs to be collected.
                If you want to collect the information about all tables carrying a certain flag, 
                configure to flag|all (flag is an identifier) and the information about all required tables can be collected. 
                For example, when you have tables a|b, a|c, and a|d (a is an identifier; b, c, and d are table names) and configure a|all, 
                the information about the three tables can be collected.
                when the value of hwCollectTableInfo is the collection of many table names that are split by commas,
                you are not allowed to name a single table with all or Flag|all (Flag stands for any letter of an ASCII code from 0x21 to 0x7E);
                when the value of hwCollectTableInfo is a single table name, you can name the table with all or Flag|all.
                (Flag stands for any letter of an ASCII code from 0x21 to 0x7E).
                "
            ::= { hwCollectOperationSet 3 }
            
        hwWaitfetchTimeout OBJECT-TYPE
            SYNTAX Integer32 (1..1800)
            MAX-ACCESS read-write
            STATUS current
            DESCRIPTION
                "
                Duration (s) after which the Waitfetch state times out. After the expiration, 
                the Waitfetch status collection automatically stops. 
                "
            ::= { hwCollectOperationSet 4 }

        hwCollectMode OBJECT-TYPE
            SYNTAX INTEGER
            {
                all(1),
                incremental(2)
            }
            MAX-ACCESS read-create
            STATUS current
            DESCRIPTION
                "
                Mode of the information collection. 
                1.all(1)           -indicates that collects data of all tables.
                2.incremental(2)   -indicates that collects data of tables have changes compared with the last collection.
                default value is all(1).
                "
            ::= { hwCollectOperationSet 5 }
            
        hwCollectSeq OBJECT-TYPE
            SYNTAX Unsigned32
            MAX-ACCESS read-create
            STATUS current
            DESCRIPTION
                "
                Seq of the information collection.
                "
            ::= { hwCollectOperationSet 6 }   
            
        hwBackupCollect       OBJECT IDENTIFIER ::= { hwCfgInfoCollect 3 }
        
        hwBackupCollectInfoParaTable OBJECT-TYPE
            SYNTAX SEQUENCE OF HwBackupCollectInfoParaEntry
            MAX-ACCESS not-accessible
            STATUS obsolete 
            DESCRIPTION
                "
                Backup collectinfo parameter table. This object is not supported currently.
                The index of this table is hwBackupCollectInfoRequestID.                 
                "
            ::= { hwBackupCollect 1 }
        
        hwBackupCollectInfoParaEntry OBJECT-TYPE
            SYNTAX HwBackupCollectInfoParaEntry
            MAX-ACCESS not-accessible
            STATUS obsolete 
            DESCRIPTION
                "
                Backup collectinfo parameter table. This object is not supported currently.
                The index of this entry is hwBackupCollectInfoRequestID. 
                "
            INDEX { hwBackupCollectInfoRequestID }
            ::= { hwBackupCollectInfoParaTable 1 }
        
        HwBackupCollectInfoParaEntry ::= SEQUENCE 
            { 
                hwBackupCollectInfoServerIpAddr
                    IpAddress,
                hwBackupCollectInfoMode
                    INTEGER,
                hwBackupCollectInfoFileName
                    OCTET STRING,
                hwBackupCollectInfoUserName
                    OCTET STRING,
                hwBackupCollectInfoPassword
                    OCTET STRING,
                hwBackupCollectInfoRequestID
                    Integer32
             }

        hwBackupCollectInfoServerIpAddr OBJECT-TYPE
            SYNTAX IpAddress
            MAX-ACCESS read-write
            STATUS obsolete 
            DESCRIPTION
                "
                The IP address of server. This object is not supported currently.
                "
            ::= { hwBackupCollectInfoParaEntry 1 }
        
        hwBackupCollectInfoMode OBJECT-TYPE
            SYNTAX INTEGER
            {
                tftp(1),
                modem(2),
                ftp(3),
                sftp(5),
                other(6)
            }
            MAX-ACCESS read-write
            STATUS obsolete 
            DESCRIPTION
                "
                Load protocol:tftp and MODEM currently supported. 
                Options: 
                1.tftp(1) -indicates load protocol is tftp.
                2.modem(2)-indicates load protocol is modem.
                3.ftp(3)  -indicates load protocol is ftp.
                4.sftp(5) -indicates load protocol is sftp.
                5.other(6)-indicates load protocol is other type.
                "
            ::= { hwBackupCollectInfoParaEntry 2 }
        
        hwBackupCollectInfoFileName OBJECT-TYPE
            SYNTAX OCTET STRING (SIZE (1..127))
            MAX-ACCESS read-write
            STATUS obsolete 
            DESCRIPTION
                "
                Backup file name. 
                "
            ::= { hwBackupCollectInfoParaEntry 3 }
        
        hwBackupCollectInfoUserName OBJECT-TYPE
            SYNTAX OCTET STRING (SIZE (1..31))
            MAX-ACCESS read-write
            STATUS obsolete 
            DESCRIPTION
                "
                The backup user name,which is necessary in FTP mode and SFTP mode
                while unnecessary in TFTP mode. This object is not supported currently.
                "
            ::= { hwBackupCollectInfoParaEntry 4 }
        
        hwBackupCollectInfoPassword OBJECT-TYPE
            SYNTAX OCTET STRING (SIZE (1..16))
            MAX-ACCESS read-write
            STATUS obsolete 
            DESCRIPTION
                "
                The backup user password, which is necessary in FTP mode and SFTP mode,
                while unnecessary in TFTP mode. This object is not supported currently.
                "
            ::= { hwBackupCollectInfoParaEntry 5 }
            
        hwBackupCollectInfoRequestID OBJECT-TYPE
            SYNTAX Integer32 
            MAX-ACCESS read-write
            STATUS obsolete 
            DESCRIPTION
                "
                The request index for xml. This object is not supported currently.
                "
            ::= { hwBackupCollectInfoParaEntry 6 }
        
        -- end of hwBackupCollectInfoParaTable
        
        hwCfgInfoQuery OBJECT IDENTIFIER ::= { hwCfgInfoCollect 4 }
        
        
        hwCfgInfoQueryTable OBJECT-TYPE
            SYNTAX SEQUENCE OF HwCfgInfoQueryEntry
            MAX-ACCESS not-accessible
            STATUS current
            DESCRIPTION
                "
                This table is used for querying information in real time. 
                The indexes of this table are hwQueryCondition and hwQueryContent.
                When the table is issued, the length of the hwQueryCondition needs to be specified, 
                and hwQueryCondition and hwQueryContent need to be converted into ASCII codes for issuing.              
                For example, if you need to issue conditions for querying the ID and name 
                of the alarm whose type is device and severity is critical, 
                the issued hwQueryCondition is 1.3.6.1.4.1.2011.6.30.7.1.1.6=4, 1.3.6.1.4.1.2011.6.30.6.1.1.4=2, 
                which can be converted into the ASCII 
                code  49.46.51.46.54.46.49.46.52.46.49.46.50.48.49.49.46.54.46.51.48.46.55.
                46.49.46.49.46.54.61.52.44.49.46.51.46.54.46.49.46.52.46.49.46.50.48.49.49.
                46.54.46.51.48.46.54.46.49.46.49.46.52.61.50; 
                the issued hwQueryContent is abc=1.3.6.1.4.1.2011.6.30.7.1.1:1,2, 
                which can be converted into the ASCII code 97.98.99.61.49.46.51.46.54.46.
                49.46.52.46.49.46.50.48.49.49.46.54.46.51.48.46.55.46.49.46.49.58.49.44.50. 
                With the length of the hwQueryCondition, the finally issued index is 
                63.49.46.51.46.54.46.49.46.52.46.49.46.50.48.49.49.46.54.46.51.48.46.55.46.
                49.46.49.46.54.61.52.44.49.46.51.46.54.46.49.46.52.46.49.46.50.48.49.49.46.
                54.46.51.48.46.54.46.49.46.49.46.52.61.50.97.98.99.61.49.46.51.46.54.46.49.46.52.46.
                49.46.50.48.49.49.46.54.46.51.48.46.55.46.49.46.49.58.49.44.50.             
                "
            ::= { hwCfgInfoQuery 1 }
        
        hwCfgInfoQueryEntry OBJECT-TYPE
            SYNTAX HwCfgInfoQueryEntry
            MAX-ACCESS not-accessible
            STATUS current
            DESCRIPTION
                "
                This table is used for querying information in real time.
                The indexes of this entry are hwQueryCondition and hwQueryContent.
                When the table is issued, the length of the hwQueryCondition needs to be specified, 
                and hwQueryCondition and hwQueryContent need to be converted into ASCII codes for issuing.              
                For example, if you need to issue conditions for querying the ID and name 
                of the alarm whose type is device and severity is critical, 
                the issued hwQueryCondition is 1.3.6.1.4.1.2011.6.30.7.1.1.6=4, 1.3.6.1.4.1.2011.6.30.6.1.1.4=2, 
                which can be converted into the ASCII 
                code  49.46.51.46.54.46.49.46.52.46.49.46.50.48.49.49.46.54.46.51.48.46.55.
                46.49.46.49.46.54.61.52.44.49.46.51.46.54.46.49.46.52.46.49.46.50.48.49.49.
                46.54.46.51.48.46.54.46.49.46.49.46.52.61.50; 
                the issued hwQueryContent is abc=1.3.6.1.4.1.2011.6.30.7.1.1:1,2, 
                which can be converted into the ASCII code 97.98.99.61.49.46.51.46.54.46.
                49.46.52.46.49.46.50.48.49.49.46.54.46.51.48.46.55.46.49.46.49.58.49.44.50. 
                With the length of the hwQueryCondition, the finally issued index is 
                63.49.46.51.46.54.46.49.46.52.46.49.46.50.48.49.49.46.54.46.51.48.46.55.46.
                49.46.49.46.54.61.52.44.49.46.51.46.54.46.49.46.52.46.49.46.50.48.49.49.46.
                54.46.51.48.46.54.46.49.46.49.46.52.61.50.97.98.99.61.49.46.51.46.54.46.49.46.52.46.
                49.46.50.48.49.49.46.54.46.51.48.46.55.46.49.46.49.58.49.44.50.             
                "
            INDEX { hwQueryCondition, IMPLIED hwQueryContent }
            ::= { hwCfgInfoQueryTable 1 }
        
        HwCfgInfoQueryEntry ::= SEQUENCE 
            { 
                hwQueryCondition
                    OCTET STRING,
                hwQueryContent
                    OCTET STRING,
                hwQueryResult
                    OCTET STRING
             }

        hwQueryCondition OBJECT-TYPE
            SYNTAX OCTET STRING (SIZE (1..256))
            MAX-ACCESS read-only
            STATUS current
            DESCRIPTION
                "
                Condition index string. The value is in the format of 'OID1=......, OID2=......'.
                "
            ::= { hwCfgInfoQueryEntry 1 }
        
        hwQueryContent OBJECT-TYPE
            SYNTAX OCTET STRING (SIZE (1..256))
            MAX-ACCESS read-only
            STATUS current
            DESCRIPTION
                "
                Query content. The format is 'name of entry 1 = OID of entry 1:OID number of sub object 1, 
                OID number of sub object 2...... + name of entry 2 = OID of entry 2:number of sub object 1,
                number of sub object 2......'.
                "
            ::= { hwCfgInfoQueryEntry 2 }
        
        hwQueryResult OBJECT-TYPE
            SYNTAX OCTET STRING (SIZE (1..8192))
            MAX-ACCESS read-only
            STATUS current
            DESCRIPTION
                "
                Query result.
                "
            ::= { hwCfgInfoQueryEntry 3 }

        hwCollectTrapVbOids OBJECT IDENTIFIER ::= { hwCfgInfoCollect 5 }
        
        hwCollectFileResult OBJECT-TYPE
            SYNTAX Integer32
            MAX-ACCESS accessible-for-notify
            STATUS current
            DESCRIPTION
                "
                Result of file Collection.
                If the result is 1, it indicates that the configuration file is generated successfully. 
                If the result is 2, it indicates that the generation of the configuration file fails.
                "
            ::= { hwCollectTrapVbOids 1 }

        hwCollectTraps OBJECT IDENTIFIER ::= { hwCfgInfoCollect 6 }
        
        hwCollectAlarmTraps OBJECT IDENTIFIER ::= { hwCollectTraps 1 }

        hwCollectCommonTraps OBJECT IDENTIFIER ::= { hwCollectTraps 2 }
        
        hwCollectCommonTrapsPrefix OBJECT IDENTIFIER ::= { hwCollectCommonTraps 0 }
        
        hwCollectFileResultTrap NOTIFICATION-TYPE
            OBJECTS 
                { 
                    hwCollectFileResult 
                }
            STATUS current
            DESCRIPTION 
                "               
                This trap message is reported when the configuration information is collected.
                "
            ::= { hwCollectCommonTrapsPrefix 1 }
                        
END
