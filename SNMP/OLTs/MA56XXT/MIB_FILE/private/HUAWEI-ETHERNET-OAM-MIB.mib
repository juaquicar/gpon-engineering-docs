-- ============================================================================
-- Copyright (C) 2016 by  HUAWEI TECHNOLOGIES. All rights reserved.
-- Description: This MIB module defines the MIB objects which provides ETHERNET
--              OAM connectivity fault management, ethernet in the First Mile
--              NMS management interfaces.
-- Reference:
-- Version: V1.56
-- ============================================================================
    HUAWEI-ETHERNET-OAM-MIB DEFINITIONS ::= BEGIN

        IMPORTS
            huaweiMgmt
                FROM HUAWEI-MIB
            IpAddress, Integer32, Unsigned32, Counter32, OBJECT-TYPE, MODULE-IDENTITY, NOTIFICATION-TYPE
                FROM SNMPv2-SMI
            RowStatus, TruthValue, MacAddress
                FROM SNMPv2-TC
            dot1agCfmMdIndex, dot1agCfmMaIndex, Dot1agCfmCcmInterval,
            Dot1agCfmMaintAssocName, Dot1agCfmMaintAssocNameType, Dot1agCfmMpDirection,
            Dot1agCfmMaintDomainNameType,Dot1agCfmMaintDomainName,Dot1agCfmMDLevel,
            Dot1agCfmMhfCreation,Dot1agCfmIdPermission
                FROM IEEE8021-CFM-MIB
            dot3OamEventLogIndex, dot3OamEventLogTimestamp, dot3OamEventLogOui, dot3OamEventLogType, dot3OamEventLogLocation,
            dot3OamEventLogWindowHi, dot3OamEventLogWindowLo, dot3OamEventLogThresholdHi, dot3OamEventLogThresholdLo,
            dot3OamEventLogValue, dot3OamEventLogRunningTotal, dot3OamEventLogEventTotal
                FROM DOT3-OAM-MIB
            ifIndex
                FROM IF-MIB
            hwFrameIndex, hwSlotIndex, hwPortIndex
                FROM HUAWEI-DEVICE-MIB;

        hwEthernetOAM MODULE-IDENTITY
            LAST-UPDATED "201601120000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION
                "This MIB module defines the MIB objects which provides ETHERNET OAM connectivity
                 fault management, ethernet in the First Mile NMS management interfaces."

            --  Revision history
            REVISION     "201601120000Z"
            DESCRIPTION  "V1.56, deleted BITS that is imported from SNMPv2-SMI."
            
            REVISION     "201509300000Z"
            DESCRIPTION  "V1.55, added hwCFMSystemAlarmTrap and hwCFMSystemAlarmRecoveryTrap."

            REVISION     "201508180000Z"
            DESCRIPTION  "V1.54, modified the value range of hwOntY1731TestId from 65536..4294967293 to 1..4294967293."

            REVISION     "201508030000Z"
            DESCRIPTION  "V1.53, modified the description of hwCfmMepTransmitLbmDestIsMepId, hwCfmMepTransmitLbTestDestIsMepId and hwCfmMepTransmitLtmTargetIsMepId."
            
            REVISION     "201504210000Z"
            DESCRIPTION  "V1.52, modified the enumerate of hwCfmMepDefects."
            
            REVISION     "201503230000Z"
            DESCRIPTION  "V1.51, deleted the value range of hwOntCfmMepEthPortId."
            
            REVISION     "201407100000Z"
            DESCRIPTION  "V1.50, added hwOntY1731TaskType, hwOntY1731TaskIfActive and hwOntY1731TaskIsContinue."
                                 
            REVISION     "201406100000Z"
            DESCRIPTION  "V1.49, modified the MAX-ACCESS of hwCfmMepIdentifier, 
                                 modified the enumerated values of hwCfmMaNetFormat and hwOntCfmMaNetFormat."
                                    
            REVISION     "201403170000Z"
            DESCRIPTION  "V1.48, added hwY1731TaskType, hwY1731TaskIfActive and hwY1731TaskIsContinue."

            REVISION     "201403100000Z"
            DESCRIPTION  "V1.47, modified the description of hwCfmMepDefects."
            
            REVISION     "201401280000Z"
            DESCRIPTION  "V1.46, modified the description of hwCfmMaAISInterval."

            REVISION     "201401070000Z"
            DESCRIPTION  "V1.45, modified the description of hwCfmMepIfTriggerType, hwCFMMacStatusDefectTrap and hwCfmMaClientLevel.
                                 modified the value range of hwCfmMepVlantag1 from 1..4095|65535 to 1..4095|65534|65535.
                                 modified the value range of hwCfmMipExtVlantag1 from -1|1..4095 to -1|1..4095|65534."

            REVISION     "201311290000Z"
            DESCRIPTION  "V1.44, added the hwEFMPeerExtTable.
                                 added the hwEFMLocalExtTable."

            REVISION     "201310230000Z"
            DESCRIPTION  "V1.43, added the hwCfmMaExtTable.
                                 added hwCfmMepTriggerPriority and hwCfmMepAISStatus in hwCfmMepTable.
                                 added down(2) in hwCfmMepIfTriggerType of hwCfmMepTable.
                                 added hwCFMMacStatusDefectTrap and hwCFMMacStatusDefectRecoveryTrap.
                                 added hwCFMIfTriggerDownTrap and hwCFMIfTriggerDownRecoveryTrap."

            REVISION     "201309130000Z"
            DESCRIPTION  "V1.42, modified the value range of hwOntCfmMepEthPortId from 1..8 to -1|1..8."

            REVISION     "201307290000Z"
            DESCRIPTION  "V1.41, added hwEfmLoopbackIfForwardRecv of hwEfmLoopbackTable."

            REVISION     "201307190000Z"
            DESCRIPTION  "V1.40, added hwOntY1731RemoteMepMacAddress in hwOntY1731TestIdTable."

            REVISION     "201307080000Z"
            DESCRIPTION  "V1.39, modified the description and the size list of hwOntCfmMdIndex and hwOntCfmMaIndex."

            REVISION     "201307030000Z"
            DESCRIPTION  "V1.38, added singleSLM(6) in hwY1731CmdType of hwY1731ConfigTable."

            REVISION     "201307010000Z"
            DESCRIPTION  "V1.37, modified the value range of hwEfmLoopbackTimeout from 1..1000 to 1..86400."

            REVISION     "201306250000Z"
            DESCRIPTION  "V1.36, modified the description of hwOntCfmMaNetCcmInterval, modified the Max access of hwOntCfmMdMhfCreation, hwOntCfmMdMhfIdPermission, hwOntCfmMaCompMhfCreation and hwOntCfmMaCompIdPermission."

            REVISION     "201306130000Z"
            DESCRIPTION  "V1.35, added the hwOntCfmMdTable, hwOntCfmMaTable, hwOntCfmMepTable, hwOntCfmGlobalParaTable, hwOntY1731TestIdTable and hwOntY1731ConfigTable."

            REVISION     "201305220000Z"
            DESCRIPTION  "V1.34, modified the value range of hwCfmMepOntid from -1..254 to -1..255."

            REVISION     "201302180000Z"
            DESCRIPTION  "V1.33, modified the copyright time of this MIB."

            REVISION     "201302170000Z"
            DESCRIPTION  "V1.32, modified the description of hwCfmMaintenanceAssociationTable, hwCfmMaintenanceAssociationEntry, hwCfmMepTransmitLbTestResultOK,
                         hwCfmMepVpi, hwCfmMepVci, hwEfmLoopbackStatus and hwEfmLoopbackIgnoreRx."

            REVISION     "201212110000Z"
            DESCRIPTION  "V1.31, added the hwY1731TestIdTable, hwY1731ConfigTable, hwY1731SingleLossStatTable and hwY1731TwoDelayStatTable."

            REVISION     "201211120000Z"
            DESCRIPTION  "V1.30, added the hwEfmLoopbackTable."

            REVISION     "201206260000Z"
            DESCRIPTION  "V1.29, modified the description of hwCfmSubIndex and hwCfmMaNetName."

            REVISION     "201206060000Z"
            DESCRIPTION  "V1.28, modified the description of hwCfmMepGemportid."

            REVISION     "201203300000Z"
            DESCRIPTION  "V1.27, deleted the hwCfmStackUpMPMac and hwCfmStackDownMPMac.
                                  Added the hwCfmMipMacAddress and hwCfmMipExtMacAddress.
                                  Modified the description and reference of hwCfmMepMacAddress.
                                  Modified the default value of hwCfmMaNetCcmInterval from 1s to 1min."

            REVISION     "201203030000Z"
            DESCRIPTION  "V1.26, modified the description of hwCfmMepHighestPrDefect and hwCfmMepDefects."

            REVISION     "201202150000Z"
            DESCRIPTION  "V1.25, modified the value range of hwCfmMepTransmitLbTestMessages from 0..12 to 0..1000."

            REVISION     "201201120000Z"
            DESCRIPTION  "V1.24, added the hwEthernetOAMEFMTraps.
                          Moved hwDot3OAMThresholdEventTrap, hwDot3OAMNonThresholdEventTrap and hwEFMLinkEventTrap from hwEthernetOAMTraps to hwEthernetOAMEFMTraps.
                          Modified the value range of hwCfmMaintenanceDomainIndexOfMA from 0..2 to 1..8.
                          Modified the value range of hwCfmMaintenanceAssociationIndex from 0..47 to 1..4096.
                          Modified the value range of hwCfmMepOntid from -1..255 to -1..254.
                          Modefied the value range of hwCfmMepTransmitLbTestInterval from 1..60 to 0..60.
                          Modified the description of hwCfmMepOntid, hwCfmMepGemIndex, hwCfmMepVlantag1, hwCfmMepVlantag2, hwCfmMepVpi and hwCfmMepVci.
                          "

            REVISION     "201112190000Z"
            DESCRIPTION  "V1.23, added the hwCfmMepTransmitLbTestDestMacAddress, hwCfmMepTransmitLbTestDestMepId, hwCfmMepTransmitLbTestDestIsMepId,
                          hwCfmMepTransmitLbTestMessages, hwCfmMepTransmitLbmTestVlanPriority, hwCfmMepTransmitLbmTestVlanDropEnable, hwCfmMepTransmitLbTestInterval,
                          hwCfmMepTransmitLbTestPatternType, hwCfmMepTransmitLbTestDataLength, hwCfmMepTransmitLbTestResultOK, hwCfmMepVpi, hwCfmMepVci,
                          hwCfmMepLbTestResultLbmOut, hwCfmMepLbTestResultLbrIn, hwCfmMepLbTestResultCRCErrorLbrIn, hwCfmMepLbTestResultBERLbrIn,
                          hwCfmMepLbTestResultOutOfOrderLbrIn, hwEthernetOAMLBTestCheckTrap.
                          Modified the description of hwCfmMipExtSubIndex."

            REVISION     "201111190000Z"
            DESCRIPTION  "V1.22, added the hwCfmMepRunStatus, hwCfmStackUpMPMac, hwCfmStackDownMPMac,
                          hwCfmMepTransmitLbmInterval, hwCfmMepTransmitLbmDataLength, hwCfmMepTransmitLbmTerminate, hwCfmMepLbResultOutOfOrderLbrIn
                          Modified hwCfmMepDefects(belongs hwCfmMepTable)value range, between 0 and 31.
                          Modified hwCfmMaNetFormat(belongs hwCfmMepTable)data type."

            REVISION     "201108160000Z"
            DESCRIPTION  "V1.21, added the hwCfmMipExtTable."

            REVISION     "201107110000Z"
            DESCRIPTION  "V1.20, modified the value range of hwCfmMepIfType from 1..3 to 1..4."

            REVISION     "201105230000Z"
            DESCRIPTION  "V1.19, modified the value range of hwCfmMepLtResultOK from 1..2 to 0..1."

            REVISION     "201104210000Z"
            DESCRIPTION  "V1.18, modified the description of leaves."

            REVISION     "201011050000Z"
            DESCRIPTION  "V1.17, modified the description of leaves."

            REVISION     "201007310000Z"
            DESCRIPTION  "V1.16, modified the description of hwCfmMepDirection, hwCfmMepCciEnabled, hwCfmGlobalStatus,
                          hwCfmMepFngAlarmTime, hwCfmMepFngResetTime, hwCfmMepTransmitLbmVlanDropEnable, hwCfmMepTransmitLtmResult,
                          hwCfmMepIfType, hwCfmMepIfTriggerType, hwEfmPortStatisticOperation, hwCfmRMepDetectEnabled, hwCfmMepLtResultOK.
                          Modified the description."

            REVISION     "201006260000Z"
            DESCRIPTION  "V1.15, modified the value range of hwCfmMepGemIndex from -1..127 to -1..1023."

            REVISION     "201006200000Z"
            DESCRIPTION  "V1.14, deleted the chinese characters in this file."

            REVISION     "201005310000Z"
            DESCRIPTION  "V1.13, added hwCfmMepLbResultLbmOut, hwCfmMepLbResultLbrIn and hwCfmMepLtResultOK for trap.
                          Modified the description of hwCfmMepTransmitLtmResult.
                          Modified binding node of hwEthernetOAMLTCheckTrap.
                          Modified binding node of hwEthernetOAMLBCheckTrap.
                          "

            REVISION     "201005220000Z"
            DESCRIPTION  "V1.12, modified the value range of hwCfmMepTransmitLbmVlanDropEnable and hwCfmMepTransmitLtmResult."

            REVISION     "201003220000Z"
            DESCRIPTION  "V1.11, modified enumeration format. Modify hwCfmMepDefects (belongs hwCfmMepTable) enumeration format.
                          hwCfmMepTransmitLbmMessages(belongs hwCfmMepTable)value range, between 0 and 1024.
                          Modified hwCfmMepOntid(belongs hwCfmMepTable)value range, between -1 and 255.
                          Modified hwCfmMepGemIndex(belongs hwCfmMepTable)value range, between -1 and 127.
                          Modified hwCfmMepVlantag1(belongs hwCfmMepTable)value range between 1 and 4095, or 65535.
                          Modified hwCfmMepVlantag2(belongs hwCfmMepTable)value range between 1 and 4095, or 65535.
                          Modified data type."

            REVISION     "201002020000Z"
            DESCRIPTION  "V1.10, modified data type and delete hwCfmLoopbackNumIn, hwCfmLinkTraceResult node etc."

            REVISION     "201001060000Z"
            DESCRIPTION  "V1.09, added hwEthernetOAMTrapsVbOids, hwEthernetOAMTraps and format the mib
                          file, modified data type and delete some defval value."

            REVISION     "200912260000Z"
            DESCRIPTION  "V1.08, added MIB discriptions in the creation of MEP."

            REVISION     "200911200000Z"
            DESCRIPTION  "V1.07, modified hwCfmVlanId(belongs tohwCfmMipTable) value range, between 1 and 4094. "

            REVISION     "200909110000Z"
            DESCRIPTION  "V1.06, added hwCfmMepIfType to hwcfmmeptable,hwCfmMepIfType indicates the type of the creation
                         of Maintenance association End Point (MEP)."

            REVISION     "200612070000Z"
            DESCRIPTION  "V1.00, Initial version"

            ::= { huaweiMgmt 101 }

        hwEthernetOAMMibObject OBJECT IDENTIFIER ::= { hwEthernetOAM 1 }

        hwCfmMaintenanceDomain OBJECT IDENTIFIER ::= { hwEthernetOAMMibObject 1 }
        hwCfmMaintenanceAssociation OBJECT IDENTIFIER ::= { hwEthernetOAMMibObject 2 }
        hwCfmMaintenanceAssociationEndPoint OBJECT IDENTIFIER ::= { hwEthernetOAMMibObject 3 }
        hwCfmRemoteMaintenanceAssociationEndPoint OBJECT IDENTIFIER ::= { hwEthernetOAMMibObject 4 }

        hwCfmMaintenanceDomainNextIndex OBJECT-TYPE
            SYNTAX Integer32 (0..2)
            MAX-ACCESS read-only
            STATUS current
            DESCRIPTION
                "Value to be used as the index of the MaintenanceDomain
                 table when the management entity wants to create a new row
                 in the table.
                "
            REFERENCE
                "802.1ag-d6.0"
            ::= { hwCfmMaintenanceDomain 1 }

        hwCfmMaintenanceDomainTable OBJECT-TYPE
            SYNTAX SEQUENCE OF HwCfmMaintenanceDomainEntry
            MAX-ACCESS not-accessible
            STATUS current
            DESCRIPTION
                "The MaintenanceDomain table. Each row in the table
                 represents a different maintenance domain.
                 A Maintenace domain is described in 802.1ag (3.22) as the
                 network or the part of the network for which faults in
                 connectivity are to be managed, belonging to a single
                 administration. The boundary of a Maintenance Domain is
                 defined by a set DSAPs, each of which may become a point of
                 connectivity to a Service Instance.
                 The index of this table is hwCfmMaintenanceDomainIndex.
                 Need bond hwCfmMaintenanceDomainIndex,hwCfmMaintenanceDomainNameFormat,
                 hwCfmMaintenanceDomainName,hwCfmMaintenanceDomainLevel and hwCfmMaintenanceDomainRowStatus
                 when create MD.
                 Need bond hwCfmMaintenanceDomainIndex and hwCfmMaintenanceDomainRowStatus when delete MD.
                "
            REFERENCE
                "802.1ag-d6.0"
            ::= { hwCfmMaintenanceDomain 2 }

        hwCfmMaintenanceDomainEntry OBJECT-TYPE
            SYNTAX HwCfmMaintenanceDomainEntry
            MAX-ACCESS not-accessible
            STATUS current
            DESCRIPTION
                "The MaintenanceDomain table. Each row in the table
                 represents a different maintenance domain.
                 A Maintenace domain is described in 802.1ag (3.22) as the
                 network or the part of the network for which faults in
                 connectivity are to be managed, belonging to a single
                 administration. The boundary of a Maintenance Domain is
                 defined by a set DSAPs, each of which may become a point of
                 connectivity to a Service Instance.
                 The index of this entry is hwCfmMaintenanceDomainIndex.
                 Need bond hwCfmMaintenanceDomainIndex,hwCfmMaintenanceDomainNameFormat,
                 hwCfmMaintenanceDomainName,hwCfmMaintenanceDomainLevel and hwCfmMaintenanceDomainRowStatus
                 when create MD.
                 Need bond hwCfmMaintenanceDomainIndex and hwCfmMaintenanceDomainRowStatus when delete MD.
                "
            REFERENCE
                "802.1ag-d6.0"
            INDEX { hwCfmMaintenanceDomainIndex }
            ::= { hwCfmMaintenanceDomainTable 1 }

        HwCfmMaintenanceDomainEntry ::=
            SEQUENCE
                {
                hwCfmMaintenanceDomainIndex
                    Integer32,
                hwCfmMaintenanceDomainNameFormat
                    INTEGER,
                hwCfmMaintenanceDomainName
                    OCTET STRING,
                hwCfmMaintenanceDomainLevel
                    INTEGER,
                hwCfmMaintenanceDomainRowStatus
                    RowStatus
                }

        hwCfmMaintenanceDomainIndex OBJECT-TYPE
            SYNTAX Integer32 (0..2)
            MAX-ACCESS read-only
            STATUS current
            DESCRIPTION
                "It is index of the maintenance domain table.
                 It needs to be bound when create MD,query MD and delete MD.
                "
            REFERENCE
                "802.1ag-d6.0"
            ::= { hwCfmMaintenanceDomainEntry 1 }

        hwCfmMaintenanceDomainNameFormat OBJECT-TYPE
            SYNTAX INTEGER
                {
                noName(1),
                dnsName(2),
                macInteger(3),
                string(4)
                }
            MAX-ACCESS read-write
            STATUS current
            DESCRIPTION
                "The type of CFM Maintenance Domain name.
                 In order to divide Maintanance Domain name from different types.
                 Format of the Maintenance Domain Name TLV.
                 Options:
                 1. noName(1)     -indicates the format compatibled ITU-T M.1400 Carrier Code and ISO 3166 country code
                 2. dnsName(2)    -indicates the format is DNS name
                 3. macInteger(3) -indicates the format is MAC address with 2-octec integer
                 4. string(4)     -indicates the format is ASCII 33 ~ ASCII 126, except \\ / : * ? \ < > | %
                "
            ::= { hwCfmMaintenanceDomainEntry 2 }

        hwCfmMaintenanceDomainName OBJECT-TYPE
            SYNTAX OCTET STRING  (SIZE (0..43))
            MAX-ACCESS read-write
            STATUS current
            DESCRIPTION
                "The Maintenance Domain name. Each Maintenance Domain has
                 unique name amongst all those used or available to a
                 service provider or operator, and to facilitate easy
                 identification of administrative responsibility for the
                 Maintenance Domain.
                 Maintenance Domain names can be represented in different
                 formats.
                "
            REFERENCE
                "802.1ag-d6.0"
            ::= { hwCfmMaintenanceDomainEntry 3 }

        hwCfmMaintenanceDomainLevel OBJECT-TYPE
            SYNTAX INTEGER
                {
                level0 (1),
                level1 (2),
                level2 (3),
                level3 (4),
                level4 (5),
                level5 (6),
                level6 (7),
                level7 (8)
                }
            MAX-ACCESS read-write
            STATUS current
            DESCRIPTION
                "The MA Level for a particular Maintenance Domain.
                 In order to allow administrations to configure different
                 Maintenance Domains in the same Bridge without having to
                 resort to detailed inter-organizational agreements as to
                 which MA Levels are available for use, an administrator of
                 a Maintenance Domain is expected to decide which of three
                 roles that Maintenance Domain will play: the 'Customer'
                 role, the 'Service Provider' role, or the 'Operator' role.
                 The administrator is free to assign an MA Level to a
                 Maintenance Domain within the range defined in the
                 CfmMaLevels textual convention according to the
                 Maintenance Domain's role. If two administrations ae
                 operating Maintenance Domains using the same role in one
                 Bridge,then they must agree to the MA Level each will
                 use.
                 Options:
                 1. level0(1) -indicates the MA Level for a particular Maintenance Domain
                               is level0
                 2. level1(2) -indicates the MA Level for a particular Maintenance Domain
                               is level1
                 3. level2(3) -indicates the MA Level for a particular Maintenance Domain
                               is level2
                 4. level3(4) -indicates the MA Level for a particular Maintenance Domain
                               is level3
                 5. level4(5) -indicates the MA Level for a particular Maintenance Domain
                               is level4
                 6. level5(6) -indicates the MA Level for a particular Maintenance Domain
                               is level5
                 7. level6(7) -indicates the MA Level for a particular Maintenance Domain
                               is level6
                 8. level7(8) -indicates the MA Level for a particular Maintenance Domain
                               is level7
                "
            REFERENCE
                "802.1ag-d6.0"
            ::= { hwCfmMaintenanceDomainEntry 4 }

        hwCfmMaintenanceDomainRowStatus OBJECT-TYPE
            SYNTAX RowStatus
            MAX-ACCESS read-create
            STATUS current
            DESCRIPTION
                "It indicates the status of this table's entry.
                 Options:
                 1. active(1)      -indicates the query operation
                 2. createAndGo(4) -indicates the creating operation
                 3. destroy(6)     -indicates the deleting operation
                "
            REFERENCE
                "802.1ag-d6.0"
            ::= { hwCfmMaintenanceDomainEntry 5 }

        hwCfmMaintenanceAssociationNextIndexTable OBJECT-TYPE
            SYNTAX SEQUENCE OF HwCfmMaintenanceAssociationNextIndexEntry
            MAX-ACCESS not-accessible
            STATUS current
            DESCRIPTION
                "It indicates Cfm Maintenance Association next index table.
                 It used for showing MA index which is free.
                 The index of this table is hwCfmMaintenanceDomainCurrentIndexOfMA.
                "
            REFERENCE
               "802.1ag-d6.0"
            ::= { hwCfmMaintenanceAssociation 1 }

        hwCfmMaintenanceAssociationNextIndexEntry OBJECT-TYPE
            SYNTAX HwCfmMaintenanceAssociationNextIndexEntry
            MAX-ACCESS not-accessible
            STATUS current
            DESCRIPTION
                "It indicates Cfm Maintenance Association next index table.
                 It used for showing MA index which is free.
                 The index of this entry is hwCfmMaintenanceDomainCurrentIndexOfMA.
                "
            REFERENCE
                "802.1ag-d6.0"
            INDEX { hwCfmMaintenanceDomainCurrentIndexOfMA }
            ::= { hwCfmMaintenanceAssociationNextIndexTable 1 }

        HwCfmMaintenanceAssociationNextIndexEntry ::=
            SEQUENCE
                {
                hwCfmMaintenanceDomainCurrentIndexOfMA
                    Integer32,
                hwCfmMaintenanceAssociationNextIndex
                    Integer32
                }

        hwCfmMaintenanceDomainCurrentIndexOfMA OBJECT-TYPE
            SYNTAX Integer32 (0..2)
            MAX-ACCESS read-only
            STATUS current
            DESCRIPTION
                "It is the index of the current MD which the MA belongs to.
                "
            REFERENCE
                "802.1ag-d6.0"
            ::= { hwCfmMaintenanceAssociationNextIndexEntry 1 }

        hwCfmMaintenanceAssociationNextIndex OBJECT-TYPE
            SYNTAX Integer32 (0..47)
            MAX-ACCESS read-only
            STATUS current
            DESCRIPTION
                "Value to be used as the index of the MaintenanceAssociation
                 table when the management entity wants to create a new row
                 in the table,and it is free,now.
                "
            REFERENCE
                "802.1ag-d6.0"
            ::= { hwCfmMaintenanceAssociationNextIndexEntry 2 }

       hwCfmMaintenanceAssociationTable OBJECT-TYPE
            SYNTAX SEQUENCE OF HwCfmMaintenanceAssociationEntry
            MAX-ACCESS not-accessible
            STATUS current
            DESCRIPTION
                "The Maintenance Association table. Each row in the table
                 represents a MA. A MA a set of MEPs, each configured with
                 the same MAID and MA Level. It is also a full mesh of
                 Maintenance Entities.
                 Creation of a Service Instance establishes a connectionless
                 association among the selected DSAPs. Configuring a
                 Maintenance association End Point (MEP) at each of the
                 DSAPs creates a Maintenance Association (MA) to monitor
                 that connectionless connectivity. The MA is identified by a
                 Short MA Name that is unique within the Maintenance Domain
                 and chosen to facilitate easy identification of the Service
                 Instance. Together, the Maintenance Domain Name and the
                 Short MA Name form the Maintenance Association Identifier
                 (MAID) that is carried in CFM Messages to identify
                 incorrect connectivity among Service Instances. A small
                 integer, the Maintenance association End Point Identifier
                 (MEPID), identifies each MEP among those configured on a
                 single MA (802.1ag clause 18.2).
                 The indexes of this table are hwCfmMaintenanceDomainIndexOfMA
                 and hwCfmMaintenanceAssociationIndex, first index is the index
                 of the Maintenance Domain table. The second index is the same
                 as the index of the dot1agCfmMaCompEntry for the same MA.
                 The writable objects in this table need to be persistent upon
                 reboot or restart of a device.
                "
            REFERENCE
                "802.1ag-d6.0"
            ::= { hwCfmMaintenanceAssociation 2 }

        hwCfmMaintenanceAssociationEntry OBJECT-TYPE
            SYNTAX HwCfmMaintenanceAssociationEntry
            MAX-ACCESS not-accessible
            STATUS current
            DESCRIPTION
                "The Maintenance Association table. Each row in the table
                 represents a MA. A MA a set of MEPs, each configured with
                 the same MAID and MA Level. It is also a full mesh of
                 Maintenance Entities.
                 Creation of a Service Instance establishes a connectionless
                 association among the selected DSAPs. Configuring a
                 Maintenance association End Point (MEP) at each of the
                 DSAPs creates a Maintenance Association (MA) to monitor
                 that connectionless connectivity. The MA is identified by a
                 Short MA Name that is unique within the Maintenance Domain
                 and chosen to facilitate easy identification of the Service
                 Instance. Together, the Maintenance Domain Name and the
                 Short MA Name form the Maintenance Association Identifier
                 (MAID) that is carried in CFM Messages to identify
                 incorrect connectivity among Service Instances. A small
                 integer, the Maintenance association End Point Identifier
                 (MEPID), identifies each MEP among those configured on a
                 single MA (802.1ag clause 18.2).
                 The indexes of this entry are hwCfmMaintenanceDomainIndexOfMA
                 and hwCfmMaintenanceAssociationIndex, first index is the index
                 of the Maintenance Domain table. The second index is the same
                 as the index of the dot1agCfmMaCompEntry for the same MA.
                 The writable objects in this table need to be persistent upon
                 reboot or restart of a device.
                "
            REFERENCE
                "802.1ag-d6.0"
            INDEX
                {
                hwCfmMaintenanceDomainIndexOfMA,
                hwCfmMaintenanceAssociationIndex
                }
            ::= { hwCfmMaintenanceAssociationTable 1 }

        HwCfmMaintenanceAssociationEntry ::=
            SEQUENCE
                {
                hwCfmMaintenanceDomainIndexOfMA
                    Integer32,
                hwCfmMaintenanceAssociationIndex
                    Integer32,
                hwCfmMaintenanceAssociationNameFormat
                    INTEGER,
                hwCfmMaintenanceAssociationName
                    OCTET STRING,
                hwCfmMaintenanceAssociationVlanID
                    Integer32,
                hwCfmMaintenanceAssociationCCInterval
                    INTEGER,
                hwCfmMaintenanceAssociationRemoteMEPCheckStatus
                    INTEGER,
                hwCfmMaintenanceAssociationRowStatus
                    RowStatus
                }

        hwCfmMaintenanceDomainIndexOfMA OBJECT-TYPE
            SYNTAX Integer32 (1..8)
            MAX-ACCESS read-only
            STATUS current
            DESCRIPTION
                "It indicates the index of an MD which the MA belongs to.
                 It is the index of the hwCfmMaintenanceAssociationTable.
                "
            REFERENCE
                "802.1ag-d6.0"
            ::= { hwCfmMaintenanceAssociationEntry 1 }

        hwCfmMaintenanceAssociationIndex OBJECT-TYPE
            SYNTAX Integer32 (1..4096)
            MAX-ACCESS read-only
            STATUS current
            DESCRIPTION
                "It is the index of the hwCfmMaintenanceAssociationTable.
                "
            REFERENCE
                "802.1ag-d6.0"
            ::= { hwCfmMaintenanceAssociationEntry 2 }

        hwCfmMaintenanceAssociationNameFormat OBJECT-TYPE
            SYNTAX INTEGER
                {
                vid         (1),
                string      (2),
                integer     (3),
                vpnid       (4),
                carriercode (32)
                }
            MAX-ACCESS read-write
            STATUS current
            DESCRIPTION
                "The type of CFM Maintenance Association name.
                 Format of the short MA Name TLV.
                 Options:
                 1. vid(1)          -indicates the type of CFM Maintenance Association name
                                     is vlanid
                 2. string(2)       -indicates the type of CFM Maintenance Association name
                                     is character string
                 3. integer(3)      -indicates the type of CFM Maintenance Association name
                                     is octect integer
                 4. vpnid(4)        -indicates the type of CFM Maintenance Association name
                                     is RFC 2685 VPN ID
                 5. carriercode(32) -indicates the type of CFM Maintenance Association name
                                     carriercode
                "
            REFERENCE
                "802.1ag-d6.0"
            ::= { hwCfmMaintenanceAssociationEntry 3 }

        hwCfmMaintenanceAssociationName OBJECT-TYPE
            SYNTAX OCTET STRING  (SIZE (0..43))
            MAX-ACCESS read-write
            STATUS current
            DESCRIPTION
                "The name of CFM Maintenance Association which is unique
                 within a Maintenance Domain.
                "
            REFERENCE
                "802.1ag-d6.0"
            ::= { hwCfmMaintenanceAssociationEntry 4 }

        hwCfmMaintenanceAssociationVlanID OBJECT-TYPE
            SYNTAX Integer32  (1..4094)
            MAX-ACCESS read-write
            STATUS current
            DESCRIPTION
                "The Vlan related to the CFM Maintenance Association Entity.
                "
            REFERENCE
                "802.1ag-d6.0"
            ::= { hwCfmMaintenanceAssociationEntry 5 }

        hwCfmMaintenanceAssociationCCInterval OBJECT-TYPE
            SYNTAX INTEGER
                {
                intervalNone    (1),
                interval300HZ   (2),
                interval10ms    (3),
                interval100ms   (4),
                interval1s      (5),
                interval10s     (6),
                interval1m      (7),
                interval10m     (8)
                }
            MAX-ACCESS read-write
            STATUS current
            DESCRIPTION
                "The Continuity Check Message's interval of CFM Maintenance Association Entity.
                 Indicates the interval at which CCMs are sent by a MEP.
                 Options:
                 1. intervalNone(1)  -no CCMs are sent (disabled)
                 2. interval300HZ(2) -CCMs are sent every 3 1/3 milliseconds(300Hz)
                 3. interval10ms(3)  -CCMs are sent every 10 milliseconds
                 4. interval100ms(4) -CCMs are sent every 100 milliseconds
                 5. interval1s(5)    -CCMs are sent every 1 second
                 6. interval10s(6)   -CCMs are sent every 10 seconds
                 7. interval1m(7)    -CCMs are sent every 1 millisecond
                 8. interval10m(8)   -CCMs are sent every 10 millisecond
                "
            REFERENCE
                "802.1ag-d6.0"
            ::= { hwCfmMaintenanceAssociationEntry 6 }

        hwCfmMaintenanceAssociationRemoteMEPCheckStatus OBJECT-TYPE
            SYNTAX INTEGER
                {
                enable(1),
                disable(2)
                }
            MAX-ACCESS read-write
            STATUS current
            DESCRIPTION
                "The RemoteMEP Check Status of CFM Maintenance Association Entity.
                 Options:
                 1. enable(1)  -indicates the RemoteMEP Check Status of CFM Maintenance
                                Association Entity is enabled
                 2. disable(2) -indicates the RemoteMEP Check Status of CFM Maintenance
                                Association Entity is disabled
                "
            REFERENCE
                "802.1ag-d6.0"
            ::= { hwCfmMaintenanceAssociationEntry 7 }

        hwCfmMaintenanceAssociationRowStatus OBJECT-TYPE
            SYNTAX RowStatus
            MAX-ACCESS read-create
            STATUS current
            DESCRIPTION
                "It indicates status of this table's entry.
                 Used for create MA or delete MA.
                 Options:
                 1. active(1)      -indicates the query operation
                 2. createAndGo(4) -indicates the creating operation
                 3. destroy(6)     -indicates the deleting operation
                "
            REFERENCE
                "802.1ag-d6.0"
            ::= { hwCfmMaintenanceAssociationEntry 8 }

        hwCfmMaintenanceAssociationEndPointNextIndexTable OBJECT-TYPE
            SYNTAX SEQUENCE OF HwCfmMaintenanceAssociationEndPointNextIndexEntry
            MAX-ACCESS not-accessible
            STATUS current
            DESCRIPTION
                "The Cfm Maintenance Association End Point next index table.
                 It uses for shou MEP index which is free.
                 The indexes of this table are hwCfmMaintenanceDomainCurrentIndexOfMEP
                 and hwCfmMaintenanceAssociationCurrentIndexOfMEP.
                "
            REFERENCE
               "802.1ag-d6.0"
            ::= { hwCfmMaintenanceAssociationEndPoint 1 }

        hwCfmMaintenanceAssociationEndPointNextIndexEntry OBJECT-TYPE
            SYNTAX HwCfmMaintenanceAssociationEndPointNextIndexEntry
            MAX-ACCESS not-accessible
            STATUS current
            DESCRIPTION
                "The Cfm Maintenance Association End Point next index table.
                 It uses for shou MEP index which is free.
                 The indexes of this entry are hwCfmMaintenanceDomainCurrentIndexOfMEP
                 and hwCfmMaintenanceAssociationCurrentIndexOfMEP.
                "
            REFERENCE
                "802.1ag-d6.0"
            INDEX
                {
                hwCfmMaintenanceDomainCurrentIndexOfMEP,
                hwCfmMaintenanceAssociationCurrentIndexOfMEP
                }
            ::= { hwCfmMaintenanceAssociationEndPointNextIndexTable 1 }

        HwCfmMaintenanceAssociationEndPointNextIndexEntry ::=
            SEQUENCE
                {
                hwCfmMaintenanceDomainCurrentIndexOfMEP
                    Integer32,
                hwCfmMaintenanceAssociationCurrentIndexOfMEP
                    Integer32,
                hwCfmMaintenanceAssociationEndPointNextIndex
                    Integer32
                }

        hwCfmMaintenanceDomainCurrentIndexOfMEP OBJECT-TYPE
            SYNTAX Integer32 (0..2)
            MAX-ACCESS read-only
            STATUS current
            DESCRIPTION
                "It indicates index of MD table which the current MEP belongs to.
                "
            REFERENCE
                "802.1ag-d6.0"
            ::= { hwCfmMaintenanceAssociationEndPointNextIndexEntry 1 }

        hwCfmMaintenanceAssociationCurrentIndexOfMEP OBJECT-TYPE
            SYNTAX Integer32 (0..47)
            MAX-ACCESS read-only
            STATUS current
            DESCRIPTION
                "It indicates index of MA table which the current MEP belongs to.
                "
            REFERENCE
                "802.1ag-d6.0"
            ::= { hwCfmMaintenanceAssociationEndPointNextIndexEntry 2 }

        hwCfmMaintenanceAssociationEndPointNextIndex OBJECT-TYPE
            SYNTAX Integer32 (0)
            MAX-ACCESS read-only
            STATUS current
            DESCRIPTION
                "Value to be used as the index of the MaintenanceAssociationEndPoint
                 table when the management entity wants to create a new row
                 in the table.
                "
            REFERENCE
                "802.1ag-d6.0"
            ::= { hwCfmMaintenanceAssociationEndPointNextIndexEntry 3 }

      hwCfmMaintenanceAssociationEndPointTable  OBJECT-TYPE
            SYNTAX SEQUENCE OF HwCfmMaintenanceAssociationEndPointEntry
            MAX-ACCESS not-accessible
            STATUS current
            DESCRIPTION
                "The MEP table. Each row in the table represents a different MEP.
                 A MEP (Maintenance association End Point) is an actively managed
                 functional component, associated with a specific DSAP of a Service
                 Instance, which can generate and receive CFM frames and track
                 any responses. It is an end point of a single Maintenance
                 Association, and terminates a separate Maintenance Entity for
                 each of the other MEPs in the same Maintenance Association (802.1ag clause 3.17).
                 The indexes of this table are hwCfmMaintenanceDomainIndexOfMEP,
                 hwCfmMaintenanceAssociationIndexOfMEP and hwCfmMaintenanceAssociationEndPointIndex,
                 being the first two the indices of the Maintenance Domain and MA tables, the reason
                 being that a MEP is allways related to an MA and Maintenance Domain.
                 SNMP SMI does not allow to stat in a MIB that an object in a table is an array.
                 The solution is to take the index (or indexes) of the first table (or tables)
                 and add one or more indexes.
                "
            REFERENCE
                "802.1ag-d6.0"
            ::= { hwCfmMaintenanceAssociationEndPoint 2 }

        hwCfmMaintenanceAssociationEndPointEntry OBJECT-TYPE
            SYNTAX HwCfmMaintenanceAssociationEndPointEntry
            MAX-ACCESS not-accessible
            STATUS current
            DESCRIPTION
                "The MEP table. Each row in the table represents a different MEP.
                 A MEP (Maintenance association End Point) is an actively managed
                 functional component, associated with a specific DSAP of a Service
                 Instance, which can generate and receive CFM frames and track
                 any responses. It is an end point of a single Maintenance
                 Association, and terminates a separate Maintenance Entity for
                 each of the other MEPs in the same Maintenance Association (802.1ag clause 3.17).
                 The indexes of this entry are hwCfmMaintenanceDomainIndexOfMEP,
                 hwCfmMaintenanceAssociationIndexOfMEP and hwCfmMaintenanceAssociationEndPointIndex,
                 being the first two the indices of the Maintenance Domain and MA tables, the reason
                 being that a MEP is allways related to an MA and Maintenance Domain.
                 SNMP SMI does not allow to stat in a MIB that an object in a table is an array.
                 The solution is to take the index (or indexes) of the first table (or tables)
                 and add one or more indexes.
                "
            REFERENCE
                "802.1ag-d6.0"
            INDEX
                {
                hwCfmMaintenanceDomainIndexOfMEP,
                hwCfmMaintenanceAssociationIndexOfMEP,
                hwCfmMaintenanceAssociationEndPointIndex
                }
            ::= { hwCfmMaintenanceAssociationEndPointTable 1 }

        HwCfmMaintenanceAssociationEndPointEntry ::=
            SEQUENCE
                {
                hwCfmMaintenanceDomainIndexOfMEP
                    Integer32,
                hwCfmMaintenanceAssociationIndexOfMEP
                    Integer32,
                hwCfmMaintenanceAssociationEndPointIndex
                    Integer32,
                hwCfmMaintenanceAssociationEndPointIdentifier
                    Integer32,
                hwCfmMaintenanceAssociationEndPointPortID
                    Integer32,
                hwCfmMaintenanceAssociationEndPointDirection
                    INTEGER,
                hwCfmMaintenanceAssociationEndPointAdminStatus
                    INTEGER,
                hwCfmMaintenanceAssociationEndPointPriority
                    Integer32,
                hwCfmMaintenanceAssociationEndPointCCStatus
                    INTEGER,
                hwCfmMaintenanceAssociationEndPointRowStatus
                    RowStatus,
                hwCfmMaintenanceAssociationEndPointUserVlanId
                    Integer32
                }

        hwCfmMaintenanceDomainIndexOfMEP OBJECT-TYPE
            SYNTAX Integer32 (0..2)
            MAX-ACCESS read-only
            STATUS current
            DESCRIPTION
                "It indicates index of MD table which the MEP belongs to.
                "
             REFERENCE
                "802.1ag-d6.0"

            ::= { hwCfmMaintenanceAssociationEndPointEntry 1 }

        hwCfmMaintenanceAssociationIndexOfMEP OBJECT-TYPE
            SYNTAX Integer32 (0..47)
            MAX-ACCESS read-only
            STATUS current
            DESCRIPTION
                "It indicates index of MA table which the MEP belongs to.
                "
             REFERENCE
                "802.1ag-d6.0"

            ::= { hwCfmMaintenanceAssociationEndPointEntry 2 }

        hwCfmMaintenanceAssociationEndPointIndex OBJECT-TYPE
            SYNTAX Integer32 (0)
            MAX-ACCESS read-only
            STATUS current
            DESCRIPTION
                "It indicates The MEP table index.
                "
             REFERENCE
                "802.1ag-d6.0"

            ::= { hwCfmMaintenanceAssociationEndPointEntry 3 }

        hwCfmMaintenanceAssociationEndPointIdentifier OBJECT-TYPE
            SYNTAX Integer32 (1..8191)
            MAX-ACCESS read-write
            STATUS current
            DESCRIPTION
                "Integer that is unique among all the MEPs in the same
                 MA. Other definition is: a small integer, unique over a
                 given Maintenance Association, identifying a specific
                 Maintenance association End Point.
                 MEP Identifier is also known as the MEPID.
                "
            REFERENCE
                "802.1ag-d6.0"

            ::= { hwCfmMaintenanceAssociationEndPointEntry 4 }

        hwCfmMaintenanceAssociationEndPointPortID OBJECT-TYPE
            SYNTAX Integer32
            MAX-ACCESS read-write
            STATUS current
            DESCRIPTION
                "It indicates Port number where this MEP is located in the Bridge.
                "
            REFERENCE
                "802.1ag-d6.0"
            ::= { hwCfmMaintenanceAssociationEndPointEntry 5 }

        hwCfmMaintenanceAssociationEndPointDirection OBJECT-TYPE
            SYNTAX INTEGER
                {
                outward(1),
                inward(2)
                }
            MAX-ACCESS read-write
            STATUS current
            DESCRIPTION
                "It indicates the direction in which the MEP faces on the Bridge port,
                 association (MEP or MIP) faces on the bridge port.
                 Options:
                 1. outward(1) -sends Continuity Check Messages away from the MAC Relay Entity.
                 2. inward(2)  -sends Continuity Check Messages towards the MAC Relay Entity
                "
            REFERENCE
                "802.1ag-d6.0"
            ::= { hwCfmMaintenanceAssociationEndPointEntry 6 }

        hwCfmMaintenanceAssociationEndPointAdminStatus OBJECT-TYPE
            SYNTAX INTEGER
                {
                enable(1),
                disable(2)
                }
            MAX-ACCESS read-write
            STATUS current
            DESCRIPTION
                "The administrative status of CFM Maintenance Association End Point Entity.
                 Options:
                 1. enable(1)  -indicates the administrative status of CFM Maintenance Association
                                End Point Entity is enable
                 2. disable(2) -indicates the administrative status of CFM Maintenance Association
                                End Point Entity is disable
                "
            REFERENCE
                "802.1ag-d6.0"
            ::= { hwCfmMaintenanceAssociationEndPointEntry 7 }

        hwCfmMaintenanceAssociationEndPointPriority OBJECT-TYPE
            SYNTAX Integer32  (0..7)
            MAX-ACCESS read-write
            STATUS current
            DESCRIPTION
                "It indicates the priority of Continuity Check Message.
                "
            REFERENCE
                "802.1ag-d6.0"
            ::= { hwCfmMaintenanceAssociationEndPointEntry 8 }

        hwCfmMaintenanceAssociationEndPointCCStatus OBJECT-TYPE
            SYNTAX INTEGER
                {
                enable(1),
                disable(2)
                }
            MAX-ACCESS read-write
            STATUS current
            DESCRIPTION
                "The Continuity Check status of CFM Maintenance Association End Point Entity.
                 Options:
                 1. enable(1)  -indicates the continuity Check status of CFM maintenance Association
                                End Point Entity is enabled
                 2. disable(2) -indicates the continuity Check status of CFM maintenance Association
                                End Point Entity is disabled
                "
            REFERENCE
                "802.1ag-d6.0"
            ::= { hwCfmMaintenanceAssociationEndPointEntry 9 }

        hwCfmMaintenanceAssociationEndPointRowStatus OBJECT-TYPE
            SYNTAX RowStatus
            MAX-ACCESS read-create
            STATUS current
            DESCRIPTION
                "It indicates status of this table's entry.
                 Options:
                 1. active(1)      -indicates the query operation
                 2. createAndGo(4) -indicates the creating operation
                 3. destroy(6)     -indicates the deleting operation
                "
            REFERENCE
                "802.1ag-d6.0"
            ::= { hwCfmMaintenanceAssociationEndPointEntry 10 }

        hwCfmMaintenanceAssociationEndPointUserVlanId OBJECT-TYPE
            SYNTAX Integer32 (1..4094)
            MAX-ACCESS read-write
            STATUS current
            DESCRIPTION
                "It indicates the user-vlan ID.
                "
            REFERENCE
                "802.1ag-d6.0"
            ::= { hwCfmMaintenanceAssociationEndPointEntry 11 }

        hwCfmRemoteMaintenanceAssociationEndPointNextIndexTable OBJECT-TYPE
            SYNTAX SEQUENCE OF HwCfmRemoteMaintenanceAssociationEndPointNextIndexEntry
            MAX-ACCESS not-accessible
            STATUS current
            DESCRIPTION
                "The Cfm Remote Maintenance Association End Point next index table.
                 The indexes of this table are hwCfmMaintenanceDomainCurrentIndexOfRMEP
                 and hwCfmMaintenanceAssociationCurrentIndexOfRMEP.
                "
            REFERENCE
                "802.1ag-d6.0"
            ::= { hwCfmRemoteMaintenanceAssociationEndPoint 1 }

        hwCfmRemoteMaintenanceAssociationEndPointNextIndexEntry OBJECT-TYPE
            SYNTAX HwCfmRemoteMaintenanceAssociationEndPointNextIndexEntry
            MAX-ACCESS not-accessible
            STATUS current
            DESCRIPTION
                "The Cfm Remote Maintenance Association End Point next index table.
                 The indexes of this entry are hwCfmMaintenanceDomainCurrentIndexOfRMEP
                 and hwCfmMaintenanceAssociationCurrentIndexOfRMEP.
                "
            REFERENCE
                "802.1ag-d6.0"
            INDEX
                {
                hwCfmMaintenanceDomainCurrentIndexOfRMEP,
                hwCfmMaintenanceAssociationCurrentIndexOfRMEP
                }
            ::= { hwCfmRemoteMaintenanceAssociationEndPointNextIndexTable 1 }

        HwCfmRemoteMaintenanceAssociationEndPointNextIndexEntry ::=
            SEQUENCE
                {
                hwCfmMaintenanceDomainCurrentIndexOfRMEP
                    Integer32,
                hwCfmMaintenanceAssociationCurrentIndexOfRMEP
                    Integer32,
                hwCfmRemoteMaintenanceAssociationEndPointNextIndex
                    Integer32
                }

        hwCfmMaintenanceDomainCurrentIndexOfRMEP OBJECT-TYPE
            SYNTAX Integer32 (0..2)
            MAX-ACCESS read-only
            STATUS current
            DESCRIPTION
                "It indicates index of an MD table the remote MEP belongs to.
                "
            REFERENCE
                "802.1ag-d6.0"
            ::= { hwCfmRemoteMaintenanceAssociationEndPointNextIndexEntry 1 }

        hwCfmMaintenanceAssociationCurrentIndexOfRMEP OBJECT-TYPE
            SYNTAX Integer32 (0..47)
            MAX-ACCESS read-only
            STATUS current
            DESCRIPTION
                "It indicates the index of an MA table the remote MEP belongs to.
                "
            REFERENCE
                "802.1ag-d6.0"
            ::= { hwCfmRemoteMaintenanceAssociationEndPointNextIndexEntry 2 }

        hwCfmRemoteMaintenanceAssociationEndPointNextIndex OBJECT-TYPE
            SYNTAX Integer32 (0..5)
            MAX-ACCESS read-only
            STATUS current
            DESCRIPTION
                "Value to be used as the index of the RemoteMaintenanceAssociationEndPoint
                 table when the management entity wants to create a new row
                 in the table.
                "
            REFERENCE
                "802.1ag-d6.0"
            ::= { hwCfmRemoteMaintenanceAssociationEndPointNextIndexEntry 3 }

        hwCfmRemoteMaintenanceAssociationEndPointTable  OBJECT-TYPE
            SYNTAX SEQUENCE OF HwCfmRemoteMaintenanceAssociationEndPointEntry
            MAX-ACCESS not-accessible
            STATUS current
            DESCRIPTION
                "The remote MEP table. Each row in the table represents a different
                 remote MEP within a Maintenance Association.
                 The indexes of this table are hwCfmMaintenanceDomainIndexOfRMEP, hwCfmMaintenanceAssociationIndexOfRMEP
                 and hwCfmRemoteMaintenanceAssociationEndPointIndex.
                "
            REFERENCE
                "802.1ag-d6.0"
            ::= { hwCfmRemoteMaintenanceAssociationEndPoint 2 }

        hwCfmRemoteMaintenanceAssociationEndPointEntry OBJECT-TYPE
            SYNTAX HwCfmRemoteMaintenanceAssociationEndPointEntry
            MAX-ACCESS not-accessible
            STATUS current
            DESCRIPTION
               "The remote MEP table. Each row in the table represents a different
                remote MEP within a Maintenance Association.
                The indexes of this entry are hwCfmMaintenanceDomainIndexOfRMEP, hwCfmMaintenanceAssociationIndexOfRMEP
                and hwCfmRemoteMaintenanceAssociationEndPointIndex.
               "
            REFERENCE
                "802.1ag-d6.0"

            INDEX
                {
                hwCfmMaintenanceDomainIndexOfRMEP,
                hwCfmMaintenanceAssociationIndexOfRMEP,
                hwCfmRemoteMaintenanceAssociationEndPointIndex
                }
            ::= { hwCfmRemoteMaintenanceAssociationEndPointTable 1 }

        HwCfmRemoteMaintenanceAssociationEndPointEntry ::=
            SEQUENCE
                {
                hwCfmMaintenanceDomainIndexOfRMEP
                    Integer32,
                hwCfmMaintenanceAssociationIndexOfRMEP
                    Integer32,
                hwCfmRemoteMaintenanceAssociationEndPointIndex
                    Integer32,
                hwCfmRemoteMaintenanceAssociationEndPointIdentifier
                    Integer32,
                hwCfmRemoteMaintenanceAssociationEndPointMacAddress
                    MacAddress,
                hwCfmRemoteMaintenanceAssociationEndPointRowStatus
                    RowStatus
                }

        hwCfmMaintenanceDomainIndexOfRMEP OBJECT-TYPE
            SYNTAX Integer32 (0..2)
            MAX-ACCESS read-only
            STATUS current
            DESCRIPTION
                "The MD table Index which the remote MEP belongs to.
                "
            REFERENCE
                "802.1ag-d6.0"
            ::= { hwCfmRemoteMaintenanceAssociationEndPointEntry 1 }

        hwCfmMaintenanceAssociationIndexOfRMEP OBJECT-TYPE
            SYNTAX Integer32 (0..47)
            MAX-ACCESS read-only
            STATUS current
            DESCRIPTION
               "The MA table Index which the remote MEP belongs to.
               "
            REFERENCE
                "802.1ag-d6.0"
            ::= { hwCfmRemoteMaintenanceAssociationEndPointEntry 2 }

        hwCfmRemoteMaintenanceAssociationEndPointIndex OBJECT-TYPE
            SYNTAX Integer32 (0..5)
            MAX-ACCESS read-only
            STATUS current
            DESCRIPTION
               "The Remote MEP table Index.
               "
            REFERENCE
                "802.1ag-d6.0"
            ::= { hwCfmRemoteMaintenanceAssociationEndPointEntry 3 }

        hwCfmRemoteMaintenanceAssociationEndPointIdentifier OBJECT-TYPE
            SYNTAX Integer32 (1..8191)
            MAX-ACCESS read-write
            STATUS current
            DESCRIPTION
                "Integer that is unique among all the Remote MEPs in the same
                 MA. MEP Identifier is also known as the RemoteMEPID.
                "
            REFERENCE
                "802.1ag-d6.0"
            ::= { hwCfmRemoteMaintenanceAssociationEndPointEntry 4 }

        hwCfmRemoteMaintenanceAssociationEndPointMacAddress OBJECT-TYPE
            SYNTAX MacAddress
            MAX-ACCESS read-only
            STATUS current
            DESCRIPTION
                "It indicates the MAC address of CFM Remote MEP.
                "
            REFERENCE
                "802.1ag-d6.0"
            ::= { hwCfmRemoteMaintenanceAssociationEndPointEntry 5 }

        hwCfmRemoteMaintenanceAssociationEndPointRowStatus OBJECT-TYPE
            SYNTAX RowStatus
            MAX-ACCESS read-create
            STATUS current
            DESCRIPTION
                "It indicates status of this table's entry.
                "
            REFERENCE
                "802.1ag-d6.0"
            ::= { hwCfmRemoteMaintenanceAssociationEndPointEntry 6 }

        hwCfmLoopBackTable   OBJECT-TYPE
            SYNTAX SEQUENCE OF HwCfmLoopBackEntry
            MAX-ACCESS not-accessible
            STATUS current
            DESCRIPTION
                "Cfm LoopBack Check table.
                 The indexes of this table are hwCfmLoopBackMaintenanceDomainIndex, hwCfmLoopBackMaintenanceAssociationIndex
                 and hwCfmLoopBackMaintenanceAssociationEndPointIndex.
                "
            REFERENCE
                "802.1ag-d6.0"
            ::= { hwEthernetOAMMibObject 5 }

        hwCfmLoopBackEntry OBJECT-TYPE
            SYNTAX HwCfmLoopBackEntry
            MAX-ACCESS not-accessible
            STATUS current
            DESCRIPTION
                "Cfm LoopBack Check table.
                 The indexes of this entry are hwCfmLoopBackMaintenanceDomainIndex, hwCfmLoopBackMaintenanceAssociationIndex
                 and hwCfmLoopBackMaintenanceAssociationEndPointIndex.
                "
            REFERENCE
                "802.1ag-d6.0"
            INDEX
                {
                hwCfmLoopBackMaintenanceDomainIndex,
                hwCfmLoopBackMaintenanceAssociationIndex,
                hwCfmLoopBackMaintenanceAssociationEndPointIndex
                }
            ::= { hwCfmLoopBackTable 1 }

        HwCfmLoopBackEntry ::=
            SEQUENCE
                {
                hwCfmLoopBackMaintenanceDomainIndex
                    Integer32,
                hwCfmLoopBackMaintenanceAssociationIndex
                    Integer32,
                hwCfmLoopBackMaintenanceAssociationEndPointIndex
                    Integer32,
                hwCfmLoopBackDstMacAddress
                    MacAddress,
                hwCfmLoopBackNumOut
                    Integer32,
                hwCfmLoopBackInterval
                    INTEGER,
                hwCfmLoopBackPriority
                    Integer32,
                hwCfmLoopBackRowStatus
                    RowStatus
                }

        hwCfmLoopBackMaintenanceDomainIndex OBJECT-TYPE
            SYNTAX Integer32 (0..2)
            MAX-ACCESS read-only
            STATUS current
            DESCRIPTION
                "The MDindex of the MEP is this LoopBack Message sent from.
                "
            REFERENCE
                "802.1ag-d6.0"
            ::= { hwCfmLoopBackEntry 1 }

        hwCfmLoopBackMaintenanceAssociationIndex OBJECT-TYPE
            SYNTAX Integer32 (0..47)
            MAX-ACCESS read-only
            STATUS current
            DESCRIPTION
                "The MAindex of the MEP is this LoopBack Message sent from
                "
            REFERENCE
                "802.1ag-d6.0"
            ::= { hwCfmLoopBackEntry 2 }

        hwCfmLoopBackMaintenanceAssociationEndPointIndex OBJECT-TYPE
            SYNTAX Integer32 (0)
            MAX-ACCESS read-only
            STATUS current
            DESCRIPTION
                "Which MEP is this LoopBack Message sent from.
                "
            REFERENCE
                "802.1ag-d6.0"
            ::= { hwCfmLoopBackEntry 3 }

        hwCfmLoopBackDstMacAddress OBJECT-TYPE
            SYNTAX MacAddress
            MAX-ACCESS read-write
            STATUS current
            DESCRIPTION
                "The mac-address of the Remote MEP or MIP is this LoopBack Messages sent to.
                "
            REFERENCE
                "802.1ag-d6.0"
            ::= { hwCfmLoopBackEntry 4 }

        hwCfmLoopBackNumOut OBJECT-TYPE
            SYNTAX Integer32 (1..10)
            MAX-ACCESS read-write
            STATUS current
            DESCRIPTION
                "The number of LoopBack Messages to send.
                "
            REFERENCE
                "802.1ag-d6.0"
            DEFVAL { 4 }
            ::= { hwCfmLoopBackEntry 5 }

        hwCfmLoopBackInterval OBJECT-TYPE
            SYNTAX INTEGER
                {
                interval100ms    (1),
                interval200ms    (2),
                interval300ms    (3),
                interval400ms    (4),
                interval500ms    (5),
                interval600ms    (6),
                interval700ms    (7),
                interval800ms    (8),
                interval900ms    (9),
                interval1000ms   (10),
                interval1100ms   (11),
                interval1200ms   (12),
                interval1300ms   (13),
                interval1400ms   (14),
                interval1500ms   (15),
                interval1600ms   (16),
                interval1700ms   (17),
                interval1800ms   (18),
                interval1900ms   (19),
                interval2000ms   (20)
                }
            MAX-ACCESS read-write
            STATUS current
            DESCRIPTION
                "The interval of LoopBack Messages to send.
                 Options:
                 1. interval100ms(1)    -the interval of sending LoopBack Messages is 100ms
                 2. interval200ms(2)    -the interval of sending LoopBack Messages is 200ms
                 3. interval300ms(3)    -the interval of sending LoopBack Messages is 300ms
                 4. interval400ms(4)    -the interval of sending LoopBack Messages is 400ms
                 5. interval500ms(5)    -the interval of sending LoopBack Messages is 500ms
                 6. interval600ms(6)    -the interval of sending LoopBack Messages is 600ms
                 7. interval700ms(7)    -the interval of sending LoopBack Messages is 700ms
                 8. interval800ms(8)    -the interval of sending LoopBack Messages is 800ms
                 9. interval900ms(9)    -the interval of sending LoopBack Messages is 900ms
                 10. interval1000ms(10) -the interval of sending LoopBack Messages is 1000ms
                 11. interval1100ms(11) -the interval of sending LoopBack Messages is 1100ms
                 12. interval1200ms(12) -the interval of sending LoopBack Messages is 1200ms
                 13. interval1300ms(13) -the interval of sending LoopBack Messages is 1300ms
                 14. interval1400ms(14) -the interval of sending LoopBack Messages is 1400ms
                 15. interval1500ms(15) -the interval of sending LoopBack Messages is 1500ms
                 16. interval1600ms(16) -the interval of sending LoopBack Messages is 1600ms
                 17. interval1700ms(17) -the interval of sending LoopBack Messages is 1700ms
                 18. interval1800ms(18) -the interval of sending LoopBack Messages is 1800ms
                 19. interval1900ms(19) -the interval of sending LoopBack Messages is 1900ms
                 20. interval2000ms(20) -the interval of sending LoopBack Messages is 2000ms
                "
            REFERENCE
                "802.1ag-d6.0"
            ::= { hwCfmLoopBackEntry 6 }

        hwCfmLoopBackPriority OBJECT-TYPE
            SYNTAX Integer32 (0..7)
            MAX-ACCESS read-write
            STATUS current
            DESCRIPTION
                "The priority of LoopBack Messages to send.
                "
            REFERENCE
                "802.1ag-d6.0"
            ::= { hwCfmLoopBackEntry 7 }

          hwCfmLoopBackRowStatus OBJECT-TYPE
            SYNTAX RowStatus
            MAX-ACCESS read-create
            STATUS current
            DESCRIPTION
                "Status of this table's entry.
                "
            REFERENCE
                "802.1ag-d6.0"

            ::= { hwCfmLoopBackEntry 8 }

        hwCfmLinkTraceTable   OBJECT-TYPE
            SYNTAX SEQUENCE OF HwCfmLinkTraceEntry
            MAX-ACCESS not-accessible
            STATUS current
            DESCRIPTION
                "The LinkTrace Check table.
                 The indexes of this table are hwCfmLinkTraceMaintenanceDomainIndex, hwCfmLinkTraceMaintenanceAssociationIndex
                 and hwCfmLinkTraceMaintenanceAssociationEndPointIndex.
                "
            REFERENCE
                "802.1ag-d6.0"

            ::= { hwEthernetOAMMibObject 6 }

        hwCfmLinkTraceEntry OBJECT-TYPE
            SYNTAX HwCfmLinkTraceEntry
            MAX-ACCESS not-accessible
            STATUS current
            DESCRIPTION
                "The LinkTrace Check table.
                 The indexes of this entry are hwCfmLinkTraceMaintenanceDomainIndex, hwCfmLinkTraceMaintenanceAssociationIndex
                 and hwCfmLinkTraceMaintenanceAssociationEndPointIndex.
                "
            REFERENCE
                "802.1ag-d6.0"
            INDEX
                {
                hwCfmLinkTraceMaintenanceDomainIndex,
                hwCfmLinkTraceMaintenanceAssociationIndex,
                hwCfmLinkTraceMaintenanceAssociationEndPointIndex
                }
            ::= { hwCfmLinkTraceTable 1 }

        HwCfmLinkTraceEntry ::=
            SEQUENCE
                {
                hwCfmLinkTraceMaintenanceDomainIndex
                    Integer32,
                hwCfmLinkTraceMaintenanceAssociationIndex
                    Integer32,
                hwCfmLinkTraceMaintenanceAssociationEndPointIndex
                    Integer32,
                hwCfmLinkTraceDstMacAddress
                    MacAddress,
                hwCfmLinkTracePriority
                    Integer32,
                hwCfmLinkTraceRowStatus
                    RowStatus,
                hwCfmLinkTraceTtl
                    Integer32
                }

        hwCfmLinkTraceMaintenanceDomainIndex OBJECT-TYPE
            SYNTAX Integer32 (0..2)
            MAX-ACCESS read-only
            STATUS current
            DESCRIPTION
                "The MDindex of the MEP is this LinkTrace Message sent from.
                "
            REFERENCE
                "802.1ag-d6.0"
            ::= { hwCfmLinkTraceEntry 1 }

        hwCfmLinkTraceMaintenanceAssociationIndex OBJECT-TYPE
            SYNTAX Integer32 (0..47)
            MAX-ACCESS read-only
            STATUS current
            DESCRIPTION
                "The MAindex of the MEP is this LinkTrace Message sent from.
                "
            REFERENCE
                "802.1ag-d6.0"
            ::= { hwCfmLinkTraceEntry 2 }

        hwCfmLinkTraceMaintenanceAssociationEndPointIndex OBJECT-TYPE
            SYNTAX Integer32 (0)
            MAX-ACCESS read-only
            STATUS current
            DESCRIPTION
                "Which Remote MEP is this LinkTrace Message sent from.
                "
            REFERENCE
                "802.1ag-d6.0"
            ::= { hwCfmLinkTraceEntry 3 }

        hwCfmLinkTraceDstMacAddress OBJECT-TYPE
            SYNTAX MacAddress
            MAX-ACCESS read-write
            STATUS current
            DESCRIPTION
                "The mac-address of the Remote MEP or MIP is this LinkTrace Message sent to.
                "
            REFERENCE
                "802.1ag-d6.0"
            ::= { hwCfmLinkTraceEntry 4 }

        hwCfmLinkTracePriority OBJECT-TYPE
            SYNTAX Integer32 (0..7)
            MAX-ACCESS read-write
            STATUS current
            DESCRIPTION
                "The Priority of the Remote MEP or MIP is this LinkTrace Message sent to.
                "
            REFERENCE
                "802.1ag-d6.0"
            ::= { hwCfmLinkTraceEntry 5 }

        hwCfmLinkTraceRowStatus OBJECT-TYPE
            SYNTAX RowStatus
            MAX-ACCESS read-create
            STATUS current
            DESCRIPTION
                "Status of this table's entry.
                 Options:
                 1. active(1)      -indicates the query operation
                 2. createAndGo(4) -indicates the creating operation
                 3. destroy(6)     -indicates the deleting operation
                "
            REFERENCE
                "802.1ag-d6.0"
            ::= { hwCfmLinkTraceEntry 6 }

        hwCfmLinkTraceTtl OBJECT-TYPE
            SYNTAX Integer32 (64..255)
            MAX-ACCESS read-write
            STATUS current
            DESCRIPTION
                "The TTL of the Remote MEP or MIP is this LinkTrace Message sent to.
                "
            REFERENCE
                "802.1ag-d6.0"
            ::= { hwCfmLinkTraceEntry 7 }

        hwCfmGlobalStatus   OBJECT-TYPE
            SYNTAX INTEGER
                {
                enable(1),
                disable(2)
                }
            MAX-ACCESS   read-write
            STATUS       current
            DESCRIPTION
                "Identifies the global status of the CFM function.
                 Options:
                 1. enable(1)  -indicates the global status of the CFM function is enable
                 2. disable(2) -indicates the global status of the CFM function is disable
                 Default: disable(2)
                "
            REFERENCE
                "802.1ag-d6.0"
            ::= { hwEthernetOAMMibObject 7 }

        hwCfmBaseMulticastMacAddress   OBJECT-TYPE
            SYNTAX       MacAddress
            MAX-ACCESS   read-write
            STATUS       current
            DESCRIPTION
                "Cfm base multi-cast MAC address.
                "
            REFERENCE
                "802.1ag-d6.0"
            ::= { hwEthernetOAMMibObject 8 }

        hwCfmSnmpAlarmGlobalStatus   OBJECT-TYPE
            SYNTAX INTEGER
                {
                enable(1),
                disable(2)
                }
            MAX-ACCESS   read-write
            STATUS       current
            DESCRIPTION
                "Indicates the host to NMS alarm status of the system.
                 Options:
                 1. enable(1)  -indicates the host of NMS alarm status of the system is enable
                 2. disable(2) -indicates the host of NMS alarm status of the system is disable
                 Default: enable(1)
                "
            REFERENCE
                "802.1ag-d6.0"
            ::= { hwEthernetOAMMibObject 9 }

        hwCfmRemoteMEPCheckGlobalStatus   OBJECT-TYPE
            SYNTAX INTEGER
                {
                enable(1),
                disable(2)
                }
            MAX-ACCESS   read-write
            STATUS       current
            DESCRIPTION
                "Describes the current RMEP detection status.
                 Options:
                 1. enable(1)  -indicates the current RMEP detection status is enable
                 2. disable(2) -indicates the current RMEP detection status is disable
                 Default: disable(2).
                "
            REFERENCE
                "802.1ag-d6.0"
            ::= { hwEthernetOAMMibObject 10 }

        hwCfmEtherType   OBJECT-TYPE
            SYNTAX Integer32 (1536..65535)
            MAX-ACCESS   read-write
            STATUS       current
            DESCRIPTION
                "Cfm ethertype.
                "
            REFERENCE
                "802.1ag-2007 for access network private"
            ::= { hwEthernetOAMMibObject 11 }

        hwCfmMepTable OBJECT-TYPE
            SYNTAX SEQUENCE OF HwCfmMepEntry
            MAX-ACCESS not-accessible
            STATUS current
            DESCRIPTION
                "Sets an MEP, including creating an MEP, deleting an MEP, and disabling the joint switchover switch of an MEP.
                 The indexes of this table are dot1agCfmMdIndex, dot1agCfmMaIndex and hwCfmMepIdentifier.
                "
            REFERENCE
                "802.1ag clauses 12.14.7 and 19.2"
            ::= { hwEthernetOAMMibObject 12 }

        hwCfmMepEntry OBJECT-TYPE
            SYNTAX     HwCfmMepEntry
            MAX-ACCESS not-accessible
            STATUS current
            DESCRIPTION
                "Sets an MEP, including creating an MEP, deleting an MEP, and disabling the joint switchover switch of an MEP.
                 The indexes of this entry are dot1agCfmMdIndex, dot1agCfmMaIndex and hwCfmMepIdentifier.
                "
            INDEX
                {
                dot1agCfmMdIndex,
                dot1agCfmMaIndex,
                hwCfmMepIdentifier
                }
            ::= { hwCfmMepTable 1 }

        HwCfmMepEntry ::=
            SEQUENCE
                {
                hwCfmMepIdentifier
                    Integer32,
                hwCfmMepIfIndex
                    Integer32,
                hwCfmMepDirection
                    Dot1agCfmMpDirection,
                hwCfmMepPrimaryVid
                    Unsigned32,
                hwCfmMepActive
                    TruthValue,
                hwCfmMepFngState
                    Integer32,
                hwCfmMepCciEnabled
                    TruthValue,
                hwCfmMepCcmLtmPriority
                    Unsigned32,
                hwCfmMepMacAddress
                    MacAddress,
                hwCfmMepLowPrDef
                    Integer32,
                hwCfmMepFngAlarmTime
                    Integer32,
                hwCfmMepFngResetTime
                    Integer32,
                hwCfmMepHighestPrDefect
                    Integer32,
                hwCfmMepDefects
                    BITS,
                hwCfmMepErrorCcmLastFailure
                    OCTET STRING,
                hwCfmMepXconCcmLastFailure
                    OCTET STRING,
                hwCfmMepCcmSequenceErrors
                    Counter32,
                hwCfmMepCciSentCcms
                    Counter32,
                hwCfmMepNextLbmTransId
                    Unsigned32,
                hwCfmMepLbrIn
                    Counter32,
                hwCfmMepLbrInOutOfOrder
                    Counter32,
                hwCfmMepLbrBadMsdu
                    Counter32,
                hwCfmMepLtmNextSeqNumber
                    Unsigned32,
                hwCfmMepUnexpLtrIn
                    Counter32,
                hwCfmMepLbrOut
                    Counter32,
                hwCfmMepTransmitLbmStatus
                    TruthValue,
                hwCfmMepTransmitLbmDestMacAddress
                    MacAddress,
                hwCfmMepTransmitLbmDestMepId
                    Integer32,
                hwCfmMepTransmitLbmDestIsMepId
                    INTEGER,
                hwCfmMepTransmitLbmMessages
                    Integer32,
                hwCfmMepTransmitLbmDataTlv
                    OCTET STRING,
                hwCfmMepTransmitLbmVlanPriority
                    Integer32,
                hwCfmMepTransmitLbmVlanDropEnable
                    INTEGER,
                hwCfmMepTransmitLbmResultOK
                    TruthValue,
                hwCfmMepTransmitLbmSeqNumber
                    Unsigned32,
                hwCfmMepTransmitLtmStatus
                    TruthValue,
                hwCfmMepTransmitLtmFlags
                    BITS,
                hwCfmMepTransmitLtmTargetMacAddress
                    MacAddress,
                hwCfmMepTransmitLtmTargetMepId
                    Integer32,
                hwCfmMepTransmitLtmTargetIsMepId
                    INTEGER,
                hwCfmMepTransmitLtmTtl
                    Unsigned32,
                hwCfmMepTransmitLtmResult
                    INTEGER,
                hwCfmMepTransmitLtmSeqNumber
                    Unsigned32,
                hwCfmMepTransmitLtmEgressIdentifier
                    OCTET STRING,
                hwCfmMepRowStatus
                    RowStatus,
                hwCfmMepGemportid
                    Unsigned32,
                hwCfmMepOntid
                    Integer32,
                hwCfmMepGemIndex
                    Integer32,
                hwCfmMepVlantag1
                    Integer32,
                hwCfmMepVlantag2
                    Integer32,
                hwCfmMepIfType
                    INTEGER,
                hwCfmMepIfTriggerType
                    INTEGER,
                hwCfmMepRunStatus
                    TruthValue,
                hwCfmMepTransmitLbmInterval
                    Integer32,
                hwCfmMepTransmitLbmDataLength
                    Integer32,
                hwCfmMepTransmitLbmTerminate
                    INTEGER,
                hwCfmMepTransmitLbTestDestMacAddress
                    MacAddress,
                hwCfmMepTransmitLbTestDestMepId
                    Integer32,
                hwCfmMepTransmitLbTestDestIsMepId
                    INTEGER,
                hwCfmMepTransmitLbTestMessages
                    Integer32,
                hwCfmMepTransmitLbmTestVlanPriority
                    Integer32,
                hwCfmMepTransmitLbmTestVlanDropEnable
                    INTEGER,
                hwCfmMepTransmitLbTestInterval
                    Integer32,
                hwCfmMepTransmitLbTestPatternType
                    INTEGER,
                hwCfmMepTransmitLbTestDataLength
                    Integer32,
                hwCfmMepTransmitLbTestResultOK
                    TruthValue,
                hwCfmMepVpi
                    Integer32,
                hwCfmMepVci
                    Integer32,
                hwCfmMepTriggerPriority
                    Integer32,
                hwCfmMepAISStatus
                    INTEGER
                }

        hwCfmMepIdentifier OBJECT-TYPE
            SYNTAX Integer32
            MAX-ACCESS accessible-for-notify
            STATUS current
            DESCRIPTION
                "Indicates the MEP index.
                 Range: 1-8191
                "
            REFERENCE
                "802.1ag clauses 3.19, 19.2 and 12.14.7"
            ::= { hwCfmMepEntry 1 }

        hwCfmMepIfIndex OBJECT-TYPE
            SYNTAX Integer32
            MAX-ACCESS read-create
            STATUS current
            DESCRIPTION
                "Indicates the flag of port bound to an MEP, and the value is obtained through
                 the ifIndex algorithm according to the shelf ID, slot ID, and port ID.
                 -1 indicates an invalid value for ifIndex.
                "
            REFERENCE
                "802.1ag clause 12.14.7.1.3:b"
            ::= { hwCfmMepEntry 2 }

        hwCfmMepDirection OBJECT-TYPE
            SYNTAX Dot1agCfmMpDirection
            MAX-ACCESS read-create
            STATUS current
            DESCRIPTION
                "Indicates the MEP direction.
                 Options:
                 1. down(1) -indicates the MEP direction is down
                 2. up(2)   -indicates the MEP direction is up
                "
            REFERENCE
                "802.1ag clauses 12.14.7.1.3:c and 19.2.
                 The value can be one of the following:
                 down(1) -Down direction.
                 up(2)   -Up direction.
                "
            ::= { hwCfmMepEntry 3 }

        hwCfmMepPrimaryVid OBJECT-TYPE
            SYNTAX Unsigned32(0..4094)
            MAX-ACCESS read-create
            STATUS current
            DESCRIPTION
                "Indicates the VLAN ID of the MEP.
                 Range: 0-4094
                 0 indicates that the MEP is not associated with any VLAN.
                "
            REFERENCE
                "802.1ag clauses 12.14.7.1.3:d"
            ::= { hwCfmMepEntry 4 }

        hwCfmMepActive OBJECT-TYPE
            SYNTAX TruthValue
            MAX-ACCESS read-create
            STATUS current
            DESCRIPTION
                "Indicates the enable status of the MEP.
                 Options:
                 1. true(1)  -indicates the MEP is enabled
                 2. false(2) -indicates the MEP is disabled
                 Default: true(1)
                "
            REFERENCE
                "802.1ag clauses 12.14.7.1.3:e and 20.9.1"
            DEFVAL { true }
             ::= { hwCfmMepEntry 5 }

        hwCfmMepFngState OBJECT-TYPE
            SYNTAX Integer32
            MAX-ACCESS read-only
            STATUS current
            DESCRIPTION
                "Indicates the fault status of an MEP. Currently, it is not supported and 0 is always returned.
                "
            REFERENCE
                "802.1ag clauses 12.14.7.1.3:f and 20.35"
             ::= { hwCfmMepEntry 6 }

        hwCfmMepCciEnabled OBJECT-TYPE
            SYNTAX TruthValue
            MAX-ACCESS read-create
            STATUS current
            DESCRIPTION
                "Indicates the CC message sending function status of the MEP.
                 Options:
                 1. true(1)  -indicates the CC message sending function of the MEP is enabled
                 2. false(2) -indicates the CC message sending function of the MEP is disabled
                 Default: true(1)
                "
            REFERENCE
                "802.1ag clauses 12.14.7.1.3:g and 20.10.1"
            DEFVAL { true }
            ::= { hwCfmMepEntry 7 }

        hwCfmMepCcmLtmPriority OBJECT-TYPE
            SYNTAX Unsigned32 (0..7)
            MAX-ACCESS read-create
            STATUS current
            DESCRIPTION
                "Indicates the level of CCMs/LTMs sent by the MEP.
                 Range: 0-7
                 Default: 7
                "
            REFERENCE
                "802.1ag clause 12.14.7.1.3:h"
            ::= { hwCfmMepEntry 8 }

        hwCfmMepMacAddress OBJECT-TYPE
            SYNTAX MacAddress
            MAX-ACCESS read-only
            STATUS current
            DESCRIPTION
                "Indicates the MAC address of the MEP.
                "
            REFERENCE
                "802.1ag clause J.6 MP addressing"
            ::= { hwCfmMepEntry 9 }

        hwCfmMepLowPrDef OBJECT-TYPE
            SYNTAX Integer32
            MAX-ACCESS read-create
            STATUS current
            DESCRIPTION
                "Indicates the lowest defect priority of the MEP.
                 Range: 1-6
                 Default: 2
                "
            REFERENCE
                "802.1ag clause 12.14.7.1.3:k and 20.9.5 and Table 20-1"
            DEFVAL { macRemErrXcon }
            ::= { hwCfmMepEntry 10}

        hwCfmMepFngAlarmTime OBJECT-TYPE
            SYNTAX Integer32
            MAX-ACCESS read-create
            STATUS current
            DESCRIPTION
                "Indicates the alarm waiting time of the MEP, in the unit of millisecond.
                 Range: 2500-10000
                 Unit: millisecond
                 Default: 2500
                "
            REFERENCE
                "802.1ag clauses 12.14.7.1.3:l and 20.33.3"
            ::= { hwCfmMepEntry 11 }

        hwCfmMepFngResetTime OBJECT-TYPE
            SYNTAX Integer32
            MAX-ACCESS read-create
            STATUS current
            DESCRIPTION
                "Indicates the recovery alarm waiting time of the MEP, in the unit of millisecond.
                 Range: 2500-10000
                 Unit: millisecond
                 Default: 10000
                "
            REFERENCE
                "802.1ag clauses 12.14.7.1.3:m and 20.33.4 "
            ::= { hwCfmMepEntry 12 }

        hwCfmMepHighestPrDefect OBJECT-TYPE
            SYNTAX Integer32
            MAX-ACCESS read-only
            STATUS current
            DESCRIPTION
                "Indicates the highest defect priority of the MEP.
                 Options:
                 1.none(0)                   -indicates no defects
                 2.defRDICCM(1)              -indicates the RDI defect
                 3.defMACstatus(2)           -indicates the port status defect
                 4.defRemoteCCM(3)           -indicates the remote CCM loss defect
                 5.defUnexpectedMepId(1025)  -indicates the unexpected mep id defect
                 6.defUnexpectedPeriod(1026) -indicates the unexpected period defect
                 7.defUnexpectedLevel(1028)  -indicates the unexpected level defect
                 8.defUnexpectedMaId(1029)   -indicates the unexpected ma id defect
                "
            REFERENCE
                "802.1ag clause 12.14.7.1.3:n 20.33.9 and Table 21-1"
            ::= { hwCfmMepEntry 13 }

        hwCfmMepDefects OBJECT-TYPE
            SYNTAX  BITS
                {
                bDefRDICCM(0),
                bDefMACStatus(1),
                bDefRemoteCCM(2),
                bDefErrorCCM(3),
                bDefXconCCM(4),
                reserved5(5),
                reserved6(6),
                reserved7(7),
                reserved8(8),
                reserved9(9),
                reserved10(10),
                reserved11(11),
                reserved12(12),
                reserved13(13),
                reserved14(14),
                reserved15(15),
                reserved16(16),
                reserved17(17),
                reserved18(18),
                reserved19(19),
                reserved20(20),
                reserved21(21),
                reserved22(22),
                reserved23(23),
                reserved24(24),
                reserved25(25),
                reserved26(26),
                bDefLock(27),
                bDefUnexpectedMepId(28),
                bDefUnexpectedPeriod(29),
                bDefUnexpectedLevel(30),
                bDefUnexpectedMaId(31)
                }
            MAX-ACCESS read-only
            STATUS current
            DESCRIPTION
                "Indicates the defect status of the MEP.
                 Options:
                 1. bDefRDICCM(0)            -indicates the RDI defect
                 2. bDefMACStatus(1)         -indicates the port status defect
                 3. bDefRemoteCCM(2)         -indicates the remote CCM loss defect
                 4. bDefErrorCCM(3)          -indicates the CCM error defect
                 5. bDefXconCCM(4)           -indicates the cross error defect
                 6. bDefLock(27)             -indicates the lock defect
                 7. bDefUnexpectedMepId(28)  -indicates the unexpected mep id defect
                 8. bDefUnexpectedPeriod(29) -indicates the unexpected period defect
                 9. bDefUnexpectedLevel(30)  -indicates the unexpected level defect
                 10.bDefUnexpectedMaId (31)  -indicates the unexpected ma id defect
                "
            REFERENCE
                ".1ag clauses 12.14.7.1.3:o, 12.14.7.1.3:p, 12.14.7.1.3:q,
                12.14.7.1.3:r, 12.14.7.1.3:s, 20.21.3, 20.23.3, 20.33.5,
                20.33.6, 20.33.7."
            ::= { hwCfmMepEntry 14 }

        hwCfmMepErrorCcmLastFailure OBJECT-TYPE
            SYNTAX OCTET STRING (SIZE(1..1522))
            MAX-ACCESS read-only
            STATUS current
            DESCRIPTION
                "Indicates the last CC error packet received by the MEP.
                "
            REFERENCE
                "802.1ag clauses 12.14.7.1.3:t and 20.21.2"
            ::= { hwCfmMepEntry 15 }

        hwCfmMepXconCcmLastFailure OBJECT-TYPE
            SYNTAX OCTET STRING (SIZE(1..1522))
            MAX-ACCESS read-only
            STATUS current
            DESCRIPTION
                "Indicates the last crossing error packet received by the MEP.
                "
            REFERENCE
                "802.1ag clauses 12.14.7.1.3:u and 20.23.2"
            ::= { hwCfmMepEntry 16 }

        hwCfmMepCcmSequenceErrors OBJECT-TYPE
            SYNTAX Counter32
            MAX-ACCESS read-only
            STATUS current
            DESCRIPTION
                "Indicates the number of packets with incorrect sequence number received by the MEP.
                "
            REFERENCE
                "802.1ag clauses 12.14.7.1.3:v and 20.16.12"
            ::= { hwCfmMepEntry 17 }

        hwCfmMepCciSentCcms OBJECT-TYPE
            SYNTAX Counter32
            MAX-ACCESS read-only
            STATUS current
            DESCRIPTION
                "Indicates the number of CCM packets sent by the MEP.
                "
            REFERENCE
                "802.1ag clauses 12.14.7.1.3:w and 20.10.2"
            ::= { hwCfmMepEntry 18 }

        hwCfmMepNextLbmTransId OBJECT-TYPE
            SYNTAX Unsigned32
            MAX-ACCESS read-only
            STATUS current
            DESCRIPTION
                "Indicates the SN of the next LBM sent by the MEP.
                "
            REFERENCE
                "802.1ag clauses 12.14.7.1.3:x and 20.28.2"
            ::= { hwCfmMepEntry 19 }

        hwCfmMepLbrIn OBJECT-TYPE
            SYNTAX Counter32
            MAX-ACCESS read-only
            STATUS current
            DESCRIPTION
                "Indicates the number of correct LBRs received by the MEP.
                "
            REFERENCE
                "802.1ag clause 12.14.7.1.3:y and 20.31.1"
            ::= { hwCfmMepEntry 20 }

        hwCfmMepLbrInOutOfOrder OBJECT-TYPE
            SYNTAX Counter32
            MAX-ACCESS read-only
            STATUS current
            DESCRIPTION
                "Indicates the number of LBRs with incorrect SNs received by the MEP.
                "
            REFERENCE
                "802.1ag clause 12.14.7.1.3:z and 20.31.1"
            ::= { hwCfmMepEntry 21 }

        hwCfmMepLbrBadMsdu OBJECT-TYPE
            SYNTAX Counter32
            MAX-ACCESS read-only
            STATUS current
            DESCRIPTION
                "Indicates the number of LBRs with incorrect source MAC addresses received by the MEP.
                "
            REFERENCE
                "802.1ag clause 12.14.7.1.3:aa 20.2.3"
            ::= { hwCfmMepEntry 22}

        hwCfmMepLtmNextSeqNumber OBJECT-TYPE
            SYNTAX Unsigned32
            MAX-ACCESS read-only
            STATUS current
            DESCRIPTION
                "Indicates the SN of the next LTM sent by the MEP.
                "
            REFERENCE
                "802.1ag clause 12.14.7.1.3:ab and 20.36.1"
            ::= { hwCfmMepEntry 23 }

        hwCfmMepUnexpLtrIn OBJECT-TYPE
            SYNTAX Counter32
            MAX-ACCESS read-only
            STATUS current
            DESCRIPTION
                "Indicates the number of invalid LTRs received by the MEP.
                "
            REFERENCE
                "802.1ag clause 12.14.7.1.3:ac 20.39.1"
            ::= { hwCfmMepEntry 24 }

        hwCfmMepLbrOut OBJECT-TYPE
            SYNTAX Counter32
            MAX-ACCESS read-only
            STATUS current
            DESCRIPTION
                "Indicates the number of LBRs sent by the MEP.
                "
            REFERENCE
                "802.1ag clause 12.14.7.1.3:ad and 20.26.2"
            ::= { hwCfmMepEntry 25 }

        hwCfmMepTransmitLbmStatus OBJECT-TYPE
            SYNTAX TruthValue
            MAX-ACCESS read-create
            STATUS current
            DESCRIPTION
                "Indicates the LB identifier of the MEP.
                "
            ::= { hwCfmMepEntry 26 }

        hwCfmMepTransmitLbmDestMacAddress OBJECT-TYPE
            SYNTAX MacAddress
            MAX-ACCESS read-create
            STATUS current
            DESCRIPTION
                "Indicates the destination MAC address of LB performed by the MEP.
                "
            REFERENCE
                "802.1ag clause 12.14.7.3.2:b"
            ::= { hwCfmMepEntry 27 }

        hwCfmMepTransmitLbmDestMepId OBJECT-TYPE
            SYNTAX Integer32
            MAX-ACCESS read-create
            STATUS current
            DESCRIPTION
                "Indicates the ID of the destination MEP that performs LB.
                "
            REFERENCE
                "802.1ag clause 12.14.7.3.2:b"
            ::= { hwCfmMepEntry 28 }

        hwCfmMepTransmitLbmDestIsMepId OBJECT-TYPE
            SYNTAX INTEGER
                {
                invalid  (0),
                true     (1),
                false    (2)
                }
            MAX-ACCESS read-create
            STATUS current
            DESCRIPTION
                "Indicates whether LB is performed by an MEP ID.
                 Options:
                 1. invalid(0) -indicates invalide value
                 2. true(1)    -indicates LB is performed by an MEP ID
                 3. false(2)   -indicates LB is not performed by an MEP ID
                "
            REFERENCE
                "802.1ag clause 12.14.7.3.2:b"
            ::= {hwCfmMepEntry 29 }

        hwCfmMepTransmitLbmMessages OBJECT-TYPE
            SYNTAX Integer32(0..1024)
            MAX-ACCESS read-create
            STATUS current
            DESCRIPTION
                "Indicates the number of LBMs sent by the MEP in LB.
                "
            REFERENCE
                "802.1ag clause 12.14.7.3.2:c"
            DEFVAL { 1 }
            ::= {hwCfmMepEntry 30 }

        hwCfmMepTransmitLbmDataTlv OBJECT-TYPE
            SYNTAX OCTET STRING (SIZE(0..1500))
            MAX-ACCESS read-create
            STATUS current
            DESCRIPTION
                "Indicates the DataTlv of the LBM sent by the MEP.
                "
            REFERENCE
                "802.1ag clause 12.14.7.3.2:d"
            ::= { hwCfmMepEntry 31 }

        hwCfmMepTransmitLbmVlanPriority OBJECT-TYPE
            SYNTAX Integer32(0..7)
            MAX-ACCESS read-create
            STATUS current
            DESCRIPTION
                "Indicates the priority of the LBM sent by the MEP.
                 Range: 0-7
                 The default value is the Tx priority of the CCM.
                "
            REFERENCE
                "802.1ag clause 12.14.7.3.2:e"
            ::= { hwCfmMepEntry 32 }

        hwCfmMepTransmitLbmVlanDropEnable OBJECT-TYPE
            SYNTAX INTEGER
                {
                true     (1),
                false    (2),
                invalid  (0)
                }
            MAX-ACCESS read-create
            STATUS current
            DESCRIPTION
                "Indicates the drop identifier of the LBM sent by the MEP.
                 Options:
                 1. true(1)    -indicates the drop identifier of the LBM
                                is sent by the MEP
                 2. false(2)   -indicates the drop identifier of the LBM
                                is not sent by the MEP
                 3. invalid(0) -indicates invalid value
                "
            REFERENCE
                "802.1ag clause 12.14.7.3.2:e"
            DEFVAL { true }
            ::= { hwCfmMepEntry 33 }

        hwCfmMepTransmitLbmResultOK OBJECT-TYPE
            SYNTAX TruthValue
            MAX-ACCESS read-only
            STATUS current
            DESCRIPTION
                "Indicates the result of LB performed by the MEP.
                 Options:
                 1. true(1)  -indicates the result of LB performed by the MEP is true
                 2. false(2) -indicates the result of LB performed by the MEP is false
                 Default: true(1).
                "
            REFERENCE
                "802.1ag clause 12.14.7.3.3:a "
            ::= { hwCfmMepEntry 34 }

        hwCfmMepTransmitLbmSeqNumber OBJECT-TYPE
            SYNTAX Unsigned32
            MAX-ACCESS read-only
            STATUS current
            DESCRIPTION
                "Indicates the SN of the first sent LBM for LB that is performed by the MEP.
                "
            REFERENCE
                "802.1ag clause 12.14.7.3.3:a"
            ::= { hwCfmMepEntry 35 }

        hwCfmMepTransmitLtmStatus OBJECT-TYPE
            SYNTAX TruthValue
            MAX-ACCESS read-only
            STATUS current
            DESCRIPTION
                "Indicates whether LT is being performed by the MEP.
                 Options:
                 1. true(1)  -indicates LT is performed by the MEP
                 2. false(2) -indicates LT is not performed by the MEP
                "
            ::= { hwCfmMepEntry 36 }

        hwCfmMepTransmitLtmFlags OBJECT-TYPE
            SYNTAX BITS {
                useFDBonly (0)
                }
            MAX-ACCESS read-create
            STATUS current
            DESCRIPTION
                "Indicates the flag that the LTM sent by the MEP is forwarded by querying the CCM database.
                 Options:
                 1. useFDBonly(0) -indicates the LTM sent by the MEP is forwarded by querying the CCM database
                "
            REFERENCE
                "802.1ag clause 12.14.7.4.2:b and 20.37.1"
            DEFVAL { {useFDBonly } }
            ::= { hwCfmMepEntry 37 }

        hwCfmMepTransmitLtmTargetMacAddress OBJECT-TYPE
            SYNTAX MacAddress
            MAX-ACCESS read-create
            STATUS current
            DESCRIPTION
                "Indicates the MAC address of the LTM sent by the MEP.
                "
            REFERENCE
                "802.1ag clause 12.14.7.4.2:c"
            ::= { hwCfmMepEntry 38 }

        hwCfmMepTransmitLtmTargetMepId OBJECT-TYPE
            SYNTAX Integer32
            MAX-ACCESS read-create
            STATUS current
            DESCRIPTION
                "Indicates the target MEP ID in the LTM sent by the MEP.
                "
            REFERENCE
                "802.1ag clause 12.14.7.4.2:c"
            ::= { hwCfmMepEntry 39 }

        hwCfmMepTransmitLtmTargetIsMepId OBJECT-TYPE
            SYNTAX INTEGER
                {
                invalid  (0),
                true     (1),
                false    (2)
                }
            MAX-ACCESS read-create
            STATUS current
            DESCRIPTION
                "Indicates whether LT is performed by an MEP ID.
                 Options:
                 1. invalid(0) -indicates invalid value
                 2. true(1)    -indicates LT is performed by an MEP ID
                 3. false(2)   -indicates LT is not performed by an MEP ID
                "
            REFERENCE
                "802.1ag clause 12.14.7.4.2:c"
            ::= { hwCfmMepEntry 40 }

        hwCfmMepTransmitLtmTtl OBJECT-TYPE
            SYNTAX Unsigned32 (0..255)
            MAX-ACCESS read-create
            STATUS current
            DESCRIPTION
                "Indicates the TTL in the transmitted TLM for LT that is performed by the MEP.
                 Range: 0-255
                 Default: 64
                "
            REFERENCE
                "802.1ag clause 12.14.7.4.2:d and 21.8.4"
            ::= { hwCfmMepEntry 41 }

        hwCfmMepTransmitLtmResult OBJECT-TYPE
            SYNTAX INTEGER
                {
                true     (1),
                false    (2),
                invalid  (0)
                }
            MAX-ACCESS read-only
            STATUS current
            DESCRIPTION
                "Indicates the result of the operation.
                 Options:
                 1. true(1)    -the Linktrace Message will be (or has been) sent
                 2. false(2)   -the Linktrace Message will not be sent
                 3. invalid(0) -invalid value
                 Default: true(1).
                "
            REFERENCE
                "802.1ag clause 12.14.7.4.3:a "
            ::= { hwCfmMepEntry 42 }

        hwCfmMepTransmitLtmSeqNumber OBJECT-TYPE
            SYNTAX Unsigned32
            MAX-ACCESS read-only
            STATUS current
            DESCRIPTION
                "Indicates the SN of the LTM sent by the MEP.
                "
            REFERENCE
                "802.1ag clause 12.14.7.4.3:a"
            ::= { hwCfmMepEntry 43 }

        hwCfmMepTransmitLtmEgressIdentifier OBJECT-TYPE
            SYNTAX OCTET STRING (SIZE(8))
            MAX-ACCESS read-create
            STATUS current
            DESCRIPTION
                "Indicates the egress information in the LTM sent by the MEP.
                 Range: a character string of 8 bytes.
                 Format: linktrace indicator or linktrace responder (2 bytes) + MAC address (6 bytes).
                "
            REFERENCE
                "802.1ag clause 12.14.7.4.3:b and 21.8.8"
            ::= { hwCfmMepEntry 44 }

        hwCfmMepRowStatus OBJECT-TYPE
            SYNTAX RowStatus
            MAX-ACCESS read-create
            STATUS current
            DESCRIPTION
                "Indicates the row status of the MEP.
                 Options:
                 1. active(1)      -indicates the query operation
                 2. createAndGo(4) -indicates the creating operation
                 3. destroy(6)     -indicates the deleting operation
                 In the query, active(1) is returned. To create an MEP, set the row status to
                 createAndGo(4). To delete an MEP, set the row status to destroy(6).
                "
            ::= { hwCfmMepEntry 45 }

        hwCfmMepGemportid OBJECT-TYPE
            SYNTAX Unsigned32
            MAX-ACCESS read-create
            STATUS current
            DESCRIPTION
                "Indicates the GemPortID of the GPON port, which conflicts with hwCfmMepOntid/ hwCfmMepGemIndex.
                 This leaf is applicable to the xPON distributing mode.
                 Range: 128-3999
                 4294967295 indicates an invalid value for Gemportid.
                "
            ::= { hwCfmMepEntry 46 }

        hwCfmMepOntid OBJECT-TYPE
            SYNTAX Integer32(-1..255)
            MAX-ACCESS read-create
            STATUS current
            DESCRIPTION
                "Indicates the OntId of the xPON port. It must be input together with hwCfmMepGemIndex but
                 these two leaves are mutually exclusive.
                 This leaf is applicable to the xPON profile mode.
                 Range: 0-255
                 -1 indicates an invalid value for OntId.
                "
            ::= { hwCfmMepEntry 47 }

        hwCfmMepGemIndex OBJECT-TYPE
            SYNTAX Integer32(-1..1023)
            MAX-ACCESS read-create
            STATUS current
            DESCRIPTION
                "Indicates the GemIndex of the GPON port. It must be input together with hwCfmMepOntid but
                 these two leaves are mutually exclusive.
                 This leaf is applicable to the xPON profile mode.
                 Range: 0-1023
                 -1 indicates an invalid value for GemIndex.
                "
            ::= { hwCfmMepEntry 48 }

        hwCfmMepVlantag1 OBJECT-TYPE
            SYNTAX Integer32(1..4095|65534|65535)
            MAX-ACCESS read-create
            STATUS current
            DESCRIPTION
                "Indicates vlantag1 in the CFM. It is a valid VLAN ID with the value range 1-4095.
                 65534 indicates that the MEP is unaware of VLAN tags.
                 65535 indicates that the MEP is associated with untagged VLAN.
                 Default: 65535
                "
            ::= { hwCfmMepEntry 49 }

         hwCfmMepVlantag2 OBJECT-TYPE
            SYNTAX Integer32(1..4095|65535)
            MAX-ACCESS read-create
            STATUS current
            DESCRIPTION
                "Indicates vlantag2 in the CFM. It is a valid VLAN ID with the value range 1-4095.
                65535 indicates an invalid value for vlantag2.
                "
            ::= { hwCfmMepEntry 50 }

        hwCfmMepIfType OBJECT-TYPE
            SYNTAX INTEGER
                {
                port(1),
                linkAggregationGroup(2),
                protectGroup(3),
                l2vpn(4)
                }
            MAX-ACCESS read-write
            STATUS current
            DESCRIPTION
                "Indicates the MEP port type.
                 Options:
                 1. port(1)                 -indicates a port
                 2. linkAggregationGroup(2) -indicates an aggregation group
                 3. protectGroup(3)         -indicates a protect group
                 4. l2vpn(4)                -indicates a Layer 2 virtual private network
                 Default: port(1)
                "
            ::= { hwCfmMepEntry 51}

       hwCfmMepIfTriggerType OBJECT-TYPE
            SYNTAX INTEGER
                {
                notify(1),
                down(2),
                disable(255)
                }
            MAX-ACCESS read-create
            STATUS current
            DESCRIPTION
                "Indicates the trigger function type of the MEP port.
                 Options:
                 1. notify(1)     -indicates the associated protection switching triggered by event notification
                 2. down(2)       -indicates that the port will be deactivated when trigger-if-down is enabled
                 3. disable(255)  -indicates trigger function is disabled
                 Default: disable(255)
                "
            ::= { hwCfmMepEntry 52}

        hwCfmMepRunStatus OBJECT-TYPE
            SYNTAX TruthValue
            MAX-ACCESS read-only
            STATUS current
            DESCRIPTION
                "Indicates the run status of the MEP.
                 1. true(1)  -indicates the MEP run status is up
                 2. false(2) -indicates the MEP run status is down
                "
            REFERENCE
                ""
             ::= { hwCfmMepEntry 53 }

        hwCfmMepTransmitLbmInterval OBJECT-TYPE
            SYNTAX Integer32 (0..60)
            UNITS "second"
            MAX-ACCESS read-create
            STATUS current
            DESCRIPTION
                "Indicates the interval of the LBMs are sent by a MEP.
                 Unit: second
                 Range: 0-60
                 Default: 0
                "
            ::= { hwCfmMepEntry 54 }

        hwCfmMepTransmitLbmDataLength OBJECT-TYPE
            SYNTAX Integer32 (0..1500)
            MAX-ACCESS read-write
            STATUS current
            DESCRIPTION
                "Indicates the length (length of tlv value) for datatlv of the LBM sent by a MEP.
                 Unit: byte
                 Range: 0-1500
                "
            ::= { hwCfmMepEntry 55 }

        hwCfmMepTransmitLbmTerminate OBJECT-TYPE
            SYNTAX INTEGER
                {
                invalid(-1),
                terminate(1)
                }
            MAX-ACCESS read-write
            STATUS current
            DESCRIPTION
                "Means to stop sending LBMs.
                 Options:
                 1. invalid(-1)  -indicates invalide value
                 2. terminate(1) -indicates stop sending LBMs
                "
            ::= { hwCfmMepEntry 56 }

        hwCfmMepTransmitLbTestDestMacAddress OBJECT-TYPE
            SYNTAX MacAddress
            MAX-ACCESS read-create
            STATUS current
            DESCRIPTION
                "Indicates the destination MAC address of the LB diagnostic test."
            ::= { hwCfmMepEntry 57 }

        hwCfmMepTransmitLbTestDestMepId OBJECT-TYPE
            SYNTAX Integer32
            MAX-ACCESS read-create
            STATUS current
            DESCRIPTION
                "Indicates the destination MEP ID of the LB diagnostic test."
            ::= { hwCfmMepEntry 58 }

        hwCfmMepTransmitLbTestDestIsMepId OBJECT-TYPE
            SYNTAX INTEGER
                {
                invalid(-1),
                true(1),
                false(2)
                }
            MAX-ACCESS read-create
            STATUS current
            DESCRIPTION
                "Indicates whether the LB diagnostic test is performed by an MEP ID.
                 Options:
                 1. invalid(-1) -indicates invalide value
                 2. true(1)    -indicates LB diagnostics test is performed by an MEP ID
                 3. false(2)   -indicates LB diagnostics test is not performed by an MEP ID"
            ::= { hwCfmMepEntry 59 }

        hwCfmMepTransmitLbTestMessages OBJECT-TYPE
            SYNTAX Integer32 (0..1000)
            MAX-ACCESS read-create
            STATUS current
            DESCRIPTION
                "Indicates the number of LBMs sent by the MEP in the LB diagnostic test.
                 Range: 1-1000
                 Default: 4
                 0 indicates an invalid value for the number.
                "
            ::= { hwCfmMepEntry 60 }

        hwCfmMepTransmitLbmTestVlanPriority OBJECT-TYPE
            SYNTAX Integer32 (0..7)
            MAX-ACCESS read-write
            STATUS current
            DESCRIPTION
                "Indicates the priority of the LBM sent by the MEP in the LB diagnostic test.
                 Range: 0-7
                 The default value is the Tx priority of the CCM.
                "
            ::= { hwCfmMepEntry 61 }

        hwCfmMepTransmitLbmTestVlanDropEnable OBJECT-TYPE
            SYNTAX INTEGER
                {
                invalid(-1),
                true(1),
                false(2)
                }
            MAX-ACCESS read-write
            STATUS current
            DESCRIPTION
                "Indicates the drop identifier of the LBM sent by the MEP in the LB diagnostic test.
                 Options:
                 1. invalid(-1) -indicates invalid value
                 2. true(1)     -indicates the drop identifier of the LBM
                                is sent by the MEP
                 3. false(2)    -indicates the drop identifier of the LBM
                                is not sent by the MEP
                "
            DEFVAL { true }
            ::= { hwCfmMepEntry 62 }

        hwCfmMepTransmitLbTestInterval OBJECT-TYPE
            SYNTAX Integer32 (0..60)
            MAX-ACCESS read-create
            STATUS current
            DESCRIPTION
                "Indicates the interval for a MEP to send LBMs in the LB diagnostic test.
                 Unit: second
                 Range: 1-60
                 Default: 1
                 0 indicates an invalid value for interval.
                "
            ::= { hwCfmMepEntry 63 }

        hwCfmMepTransmitLbTestPatternType OBJECT-TYPE
            SYNTAX INTEGER
                {
                invalid(-1),
                nullSignalWithOutCRC(0),
                nullSignalWithCRC(1),
                prbsWithOutCRC(2),
                prbsWithCRC(3)
                }
            MAX-ACCESS read-create
            STATUS current
            DESCRIPTION
                "Indicates the sequence pattern type of test tlv in the LBM sent by a MEP in the LB diagnostic test.
                 Options:
                 1. invalid(-1)             -indicates invalid value
                 2. nullSignalWithOutCRC(0) -indicates All-zero sequence withoutCRC
                 3. nullSignalWithCRC(1)    -indicates All-zero sequence withCRC
                 4. prbsWithOutCRC(2)       -indicates PRBS sequence withoutCRC
                 5. prbsWithCRC(3)          -indicates PRBS sequence withCRC
                 Default: nullSignalWithOutCRC(0)
                "
            ::= { hwCfmMepEntry 64 }

        hwCfmMepTransmitLbTestDataLength OBJECT-TYPE
            SYNTAX Integer32 (0..1500)
            MAX-ACCESS read-create
            STATUS current
            DESCRIPTION
                "Indicates the sequence length of test tlv in the LBM sent by a MEP in the LB diagnostic test.
                 Unit: byte
                 Range: 0-1500
                 Default: 100
                "
            ::= { hwCfmMepEntry 65 }

        hwCfmMepTransmitLbTestResultOK OBJECT-TYPE
            SYNTAX TruthValue
            MAX-ACCESS read-create
            STATUS current
            DESCRIPTION
                "Indicates the result of LB diagnostics test performed by the MEP.
                     Options:
                     1. true(1)  -indicates the result of LB diagnostics test performed by the MEP is true
                     2. false(2) -indicates the result of LB diagnostics test performed by the MEP is false
                     Default: true(1).
                    "
            ::= { hwCfmMepEntry 66 }

        hwCfmMepVpi OBJECT-TYPE
            SYNTAX Integer32 (-1..4095)
            MAX-ACCESS read-write
            STATUS current
            DESCRIPTION
                "Indicates the VPI value among the ATM/xDSL service port parameters. It must be input together with hwCfmMepVci.
                 Range: 0-4095
                 -1 indicates an invalid value for VPI.
                "
            ::= { hwCfmMepEntry 67 }

        hwCfmMepVci OBJECT-TYPE
            SYNTAX Integer32 (-1 | 32..65535)
            MAX-ACCESS read-write
            STATUS current
            DESCRIPTION
                "Indicates the VCI value among the ATM/xDSL service port parameters. It must be input together with hwCfmMepVpi.
                 Range: 32-65535
                 -1 indicates an invalid value for VCI.
                "
            ::= { hwCfmMepEntry 68 }

        hwCfmMepTriggerPriority OBJECT-TYPE
            SYNTAX Integer32(-1 | 2..5)
            MAX-ACCESS read-create
            STATUS current
            DESCRIPTION
                "Indicates the lowest alarm priority to enable trigger-if-down.
                 Range: -1,2-5
                 Default: 2
                 -1 indicates an invalid value for trigger-if-down priority.
                "
            DEFVAL { macRemErrXcon }
            ::= { hwCfmMepEntry 69 }

        hwCfmMepAISStatus OBJECT-TYPE
            SYNTAX INTEGER
                {
                enable(1),
                disable(2)
                }
            MAX-ACCESS read-write
            STATUS current
            DESCRIPTION
                "Indicates whether the AIS packet sending function is enabled.
                 Options:
                 1. enable(1)  -Indicates that the AIS packet sending function is enabled
                 2. disable(2) -Indicates that the AIS packet sending function is disabled
                 Default: disable(2)
                "
            ::= { hwCfmMepEntry 70 }

        hwEthernetOAMEFMMibObject OBJECT IDENTIFIER ::= { hwEthernetOAM 2 }

        hwEfmPortStatisticsMaintenanceTable OBJECT-TYPE
            SYNTAX SEQUENCE OF HwEfmPortStatisticsMaintenanceEntry
            MAX-ACCESS not-accessible
            STATUS current
            DESCRIPTION
                "Issues the command for collecting the packet statistics of the EFM port.
                 In this case, the statistics of the port can be cleared.
                 The index of this table is hwEfmPortIndex.
                "
            ::= { hwEthernetOAMEFMMibObject 1 }

        hwEfmPortStatisticsMaintenanceEntry OBJECT-TYPE
            SYNTAX HwEfmPortStatisticsMaintenanceEntry
            MAX-ACCESS not-accessible
            STATUS current
            DESCRIPTION
                "Issues the command for collecting the packet statistics of the EFM port.
                 In this case, the statistics of the port can be cleared.
                 The index of this entry is hwEfmPortIndex.
                "
            INDEX { hwEfmPortIndex }
            ::= { hwEfmPortStatisticsMaintenanceTable 1 }

        HwEfmPortStatisticsMaintenanceEntry ::=
            SEQUENCE
                {
                hwEfmPortIndex
                    Unsigned32,
                hwEfmPortStatisticOperation
                    INTEGER
                }

        hwEfmPortIndex OBJECT-TYPE
            SYNTAX Unsigned32
            MAX-ACCESS not-accessible
            STATUS current
            DESCRIPTION
                "Indicates the port index.
                 This leaf is of the ifIndex type.
                "
            ::= { hwEfmPortStatisticsMaintenanceEntry 1 }

        hwEfmPortStatisticOperation OBJECT-TYPE
            SYNTAX INTEGER { reset(1) }
            MAX-ACCESS read-write
            STATUS current
            DESCRIPTION
                "Indicates the operation that is performed for statistics of the specified port.
                 Currently, only the reset operation is supported.
                 Options:
                 1. reset(1) -reset the statistics of the specified port
                "
            ::= { hwEfmPortStatisticsMaintenanceEntry 2 }

        hwEfmLoopbackTable OBJECT-TYPE
            SYNTAX SEQUENCE OF HwEfmLoopbackEntry
            MAX-ACCESS not-accessible
            STATUS current
            DESCRIPTION
                "Indicates the loopback control parameter and status of the local link.
                 The index of this table is ifIndex.
                "
            ::= { hwEthernetOAMEFMMibObject 2 }

        hwEfmLoopbackEntry OBJECT-TYPE
            SYNTAX HwEfmLoopbackEntry
            MAX-ACCESS not-accessible
            STATUS current
            DESCRIPTION
                "Indicates the loopback control parameter and status of the local link.
                 The index of this entry is ifIndex.
                "
            INDEX { ifIndex }
            ::= { hwEfmLoopbackTable 1 }

        HwEfmLoopbackEntry ::=
            SEQUENCE
                {
                hwEfmLoopbackStatus
                    INTEGER,
                hwEfmLoopbackIgnoreRx
                    INTEGER,
                hwEfmLoopbackTimeout
                    Unsigned32,
                hwEfmLoopbackIfForwardRecv
                    TruthValue
                }

        hwEfmLoopbackStatus OBJECT-TYPE
            SYNTAX INTEGER
                {
                noLoopback(1),
                initiatingLoopback(2),
                remoteLoopback(3),
                terminatingLoopback(4),
                localLoopback(5),
                unknown(6)
                }
            MAX-ACCESS read-write
            STATUS current
            DESCRIPTION
                "Indicates the loopback status of the OAM entity.
                 The function of this object is the same as that of object dot3OamLoopbackStatus.
                 Options:
                 1. noLoopback(1)          -indicates no loopback in progress
                 2. initiatingLoopback(2)  -indicates the OAM client initiates a loopback
                 3. remoteLoopback(3)      -indicates the remote OAM entity is in loopback mode
                 4. terminatingLoopback(4) -indicates the local OAM client is in the process of terminating the remote loopback
                 5. localLoopback(5)       -indicates the local OAM entity is in loopback mode
                 6. unknown(6)             -indicates the parser and multiplexer combination is unexpected
                "
            ::= { hwEfmLoopbackEntry 1 }

        hwEfmLoopbackIgnoreRx OBJECT-TYPE
            SYNTAX INTEGER
                {
                ignore(1),
                process(2)
                }
            MAX-ACCESS read-write
            STATUS current
            DESCRIPTION
                "Indicates whether received OAM loopback commands are processed or ignored.
                 The function of this object is the same as that of object dot3OamLoopbackIgnoreRx.
                 Options:
                 1. ignore(1)  -indicates the received loopback commands are ignored
                 2. process(2) -indicates the received loopback commands are processed
                "
            ::= { hwEfmLoopbackEntry 2 }

        hwEfmLoopbackTimeout OBJECT-TYPE
            SYNTAX Unsigned32(1..86400|4294967295)
            MAX-ACCESS read-write
            STATUS current
            DESCRIPTION
                "Indicates the duration after which the loopback automatically stops.
                 Unit: sec
                 Range: 1-86400
                 Default: 4294967295
                 4294967295 is an invalid value, indicating that the loopback does not stop automatically.
                "
            ::= { hwEfmLoopbackEntry 3 }

        hwEfmLoopbackIfForwardRecv OBJECT-TYPE
            SYNTAX TruthValue
            MAX-ACCESS read-write
            STATUS current
            DESCRIPTION
                "Indicates whether the packets are discarded or forwarded in the receiving direction.
                 Options:
                 1. true(1)  -indicates the packets are forwarded in the receiving direction
                 2. false(2) -indicates the packets are discarded in the receiving direction
                 Default: false(2)
                "
            ::= { hwEfmLoopbackEntry 4 }
            
        hwEFMPeerExtTable OBJECT-TYPE
            SYNTAX SEQUENCE OF HwEFMPeerExtEntry
            MAX-ACCESS not-accessible
            STATUS current
            DESCRIPTION
                "Indicates the EFM remote status of stable and evaluation.
                 The index of this table is ifIndex.
                "
            ::= { hwEthernetOAMEFMMibObject 3 }

        hwEFMPeerExtEntry OBJECT-TYPE
            SYNTAX HwEFMPeerExtEntry
            MAX-ACCESS not-accessible
            STATUS current
            DESCRIPTION
                "Indicates the EFM remote status of stable and evaluation.
                 The index of this entry is ifIndex.
                "
            INDEX { ifIndex }
            ::= { hwEFMPeerExtTable 1 }

        HwEFMPeerExtEntry ::=
            SEQUENCE
                {
                hwEFMPeerExtStableEvaluating
                    Integer32
                }

        hwEFMPeerExtStableEvaluating OBJECT-TYPE
            SYNTAX      Integer32 (-1 | 0..3)
            MAX-ACCESS read-only
            STATUS current
            DESCRIPTION 
              "0x0: Remote DTE unsatisfied, discovery can not complete
               0x1: Remote DTE discovery process has not completed
               0x2: Remote DTE discovery process has completed
               0x3: Reserved. This value shall not be sent. If the value 0x3 is received,it should be ignored and the last received value can not be changed
                -1: Unknown state
              "
            REFERENCE   "IEEE 802.3ah 57.4.1"
            ::= { hwEFMPeerExtEntry 1 }
            
            
            
        hwEFMLocalExtTable OBJECT-TYPE
            SYNTAX SEQUENCE OF HwEFMLocalExtEntry
            MAX-ACCESS not-accessible
            STATUS current
            DESCRIPTION
                "Indicates the EFM local status of stable and evaluation.
                 The index of this table is ifIndex.
                "

            ::= { hwEthernetOAMEFMMibObject 4 }

        hwEFMLocalExtEntry OBJECT-TYPE
            SYNTAX HwEFMLocalExtEntry
            MAX-ACCESS not-accessible
            STATUS current
            DESCRIPTION
                "Indicates the EFM local status of stable and evaluation.
                 The index of this entry is ifIndex.
                "
            INDEX { ifIndex }
            ::= { hwEFMLocalExtTable 1 }

        HwEFMLocalExtEntry ::=
            SEQUENCE
                {
                hwEFMLocalExtStableEvaluating
                    Integer32
                }

        hwEFMLocalExtStableEvaluating OBJECT-TYPE
            SYNTAX      Integer32 (0..3)
            MAX-ACCESS read-only
            STATUS current
            DESCRIPTION 
              "0x0: Local DTE unstatisfied, Discoverty can not complete
               0x1: Local DTE Discovery process has not completed
               0x2: Local DTE Discovery process has completed
               0x3: Reserved. This value shall not be sent. If the value 0x3 is received,it should be ignored and the last received value can not be changed
              "
            REFERENCE   "IEEE 802.3ah 57.4.1"
            ::= { hwEFMLocalExtEntry 1 }  

        hwCfmMipTable OBJECT-TYPE
            SYNTAX SEQUENCE OF HwCfmMipEntry
            MAX-ACCESS not-accessible
            STATUS current
            DESCRIPTION
                "Describes the MIP information in the CFM and supports only the query operation on the MIP.
                 The indexes of this table are hwCfmIfIndex, hwCfmSubIndex and hwCfmVlanId.
                "
            REFERENCE
                "802.1ag clauses 12.14.7 and 19.2"
            ::= { hwEthernetOAMMibObject 13 }

        hwCfmMipEntry OBJECT-TYPE
            SYNTAX HwCfmMipEntry
            MAX-ACCESS not-accessible
            STATUS current
            DESCRIPTION
                "Describes the MIP information in the CFM and supports only the query operation on the MIP.
                 The indexes of this entry are hwCfmIfIndex, hwCfmSubIndex and hwCfmVlanId.
                "
            INDEX
                {
                hwCfmIfIndex,
                hwCfmSubIndex,
                hwCfmVlanId
                }
            ::= { hwCfmMipTable 1 }

        HwCfmMipEntry ::=
            SEQUENCE {
                hwCfmIfIndex
                   Integer32,
                hwCfmSubIndex
                   Integer32,
                hwCfmVlanId
                   Integer32,
                hwCfmMipLevel
                   Integer32,
                hwCfmMipMacAddress
                   MacAddress
                }

        hwCfmIfIndex OBJECT-TYPE
            SYNTAX Integer32
            MAX-ACCESS not-accessible
            STATUS current
            DESCRIPTION
                "Queries the ifIndex of the MIP port, consistent with the ifIndex of a Huawei MIB.
                "
            REFERENCE
                "802.1ag clauses 3.19, 19.2 and 12.14.7"
            ::= { hwCfmMipEntry 1 }

        hwCfmSubIndex OBJECT-TYPE
            SYNTAX Integer32
            MAX-ACCESS not-accessible
            STATUS current
            DESCRIPTION
                "Queries the sub-index of the MIP port. In the case of a GPON port, when the system
                 works in the GPON old mode, issues the GEM port ID; when the system works in the
                 GPON new mode, issues OntId for the low 16 bits and GemIndex for the high
                 16 bits. In the case of an ATM/xDSL port, issues VPI for the low 16 bits and VCI for the high
                 16 bits. In other cases, 4294967295 (0xFFFFFFFF) is issued.
                "
            REFERENCE
                "802.1ag clauses 3.19, 19.2 and 12.14.7"
            ::= { hwCfmMipEntry 2 }

        hwCfmVlanId OBJECT-TYPE
            SYNTAX Integer32(1..4094)
            MAX-ACCESS not-accessible
            STATUS current
            DESCRIPTION
                "Queries the VLAN of the MIP. It is a valid VLAN ID in the range of 1-4094.
                "
            REFERENCE
                "802.1ag clauses 3.19, 19.2 and 12.14.7"
            ::= { hwCfmMipEntry 3 }

        hwCfmMipLevel OBJECT-TYPE
            SYNTAX Integer32(0..7)
            MAX-ACCESS read-only
            STATUS current
            DESCRIPTION
                "Indicates the MIP level, in the range of 0-7.
                "
            REFERENCE
                "802.1ag clause 12.14.7.1.3:b"
            ::= { hwCfmMipEntry 4 }

        hwCfmMipMacAddress OBJECT-TYPE
            SYNTAX      MacAddress
            MAX-ACCESS  read-only
            STATUS      current
            DESCRIPTION
                "MAC address of the MIP."
            REFERENCE
                "802.1ag clause J.6 MP addressing"
            ::= { hwCfmMipEntry 5 }

        hwCfmMaNetTable OBJECT-TYPE
            SYNTAX SEQUENCE OF HwCfmMaNetEntry
            MAX-ACCESS not-accessible
            STATUS current
            DESCRIPTION
                "Configures an MA, including creating an MA, modifying an MA, deleting an MA, and
                 configuring the interval for an MA to send CCMs.
                 The indexes of this table are dot1agCfmMdIndex and hwCfmMaIndex.
                "
            REFERENCE
                "802.1ag clause 18.2"
            ::= {  hwEthernetOAMMibObject 14 }

        hwCfmMaNetEntry OBJECT-TYPE
            SYNTAX HwCfmMaNetEntry
            MAX-ACCESS not-accessible
            STATUS current
            DESCRIPTION
                "Configures an MA, including creating an MA, modifying an MA, deleting an MA, and
                 configuring the interval for an MA to send CCMs.
                 The indexes of this entry are dot1agCfmMdIndex and hwCfmMaIndex.
                "
             INDEX
                 {
                 dot1agCfmMdIndex,
                 hwCfmMaIndex
                 }
             ::= { hwCfmMaNetTable 1 }

        HwCfmMaNetEntry ::=
            SEQUENCE
                {
                hwCfmMaIndex
                    Unsigned32,
                hwCfmMaNetFormat
                    INTEGER,
                hwCfmMaNetName
                    Dot1agCfmMaintAssocName,
                hwCfmMaNetCcmInterval
                    Dot1agCfmCcmInterval,
                hwCfmRMepDetectEnabled
                    TruthValue,
                hwCfmMaNetRowStatus
                    RowStatus
                }

        hwCfmMaIndex OBJECT-TYPE
            SYNTAX Unsigned32(1..4096)
            MAX-ACCESS not-accessible
            STATUS current
            DESCRIPTION
                "MA index, indicating an operated MA.
                 Range: 1-4096
                "
            ::= { hwCfmMaNetEntry 1 }

        hwCfmMaNetFormat OBJECT-TYPE
            SYNTAX INTEGER
                {
                primaryVid(1),
                charString(2),
                unsignedInt16(3),
                rfc2865VpnId(4),
                iccBased(32)
                }
            MAX-ACCESS read-create
            STATUS current
            DESCRIPTION
                "Indicates the name type of an MA name.
                 Options:
                 1. primaryVid(1)    -indicates the name type of the MA name is primary VLAN ID
                 2. charString(2)    -indicates the name type of the MA name is char string
                 3. unsignedInt16(3) -indicates the name type of the MA name is unsigned int16
                 4. rfc2865VpnId(4)  -indicates the name type of the MA name is rfc2865VpnId
                 5. iccBased(32)    -indicates the name type of the MA name is ICC-based
                "
            REFERENCE
                "802.1ag clauses 21.6.5.4"
            ::= { hwCfmMaNetEntry 2 }

        hwCfmMaNetName OBJECT-TYPE
            SYNTAX Dot1agCfmMaintAssocName
            MAX-ACCESS read-create
            STATUS current
            DESCRIPTION
                "Indicates the name of an MA.
                 Range: 1-45 characters.
                "
            REFERENCE
                "802.1ag clauses 21.6.5.6, and Table 21-20"
            ::= { hwCfmMaNetEntry 3 }

        hwCfmMaNetCcmInterval OBJECT-TYPE
            SYNTAX Dot1agCfmCcmInterval
            MAX-ACCESS read-create
            STATUS current
            DESCRIPTION
                "Indicates the Tx interval of CCMs.
                 Options:
                 1. intervalInvalid(0) -indicates the Tx interval of CCMs is invalid
                 2. interval300Hz(1)   -indicates the Tx interval of CCMs is 300Hz
                 3. interval10ms(2)    -indicates the Tx interval of CCMs is 10ms
                 4. interval100ms(3)   -indicates the Tx interval of CCMs is 100ms
                 5. interval1s(4)      -indicates the Tx interval of CCMs is 1s
                 6. interval10s(5)     -indicates the Tx interval of CCMs is 10s
                 7. interval1min(6)    -indicates the Tx interval of CCMs is 1 minute
                 8. interval10min(7)   -indicates the Tx interval of CCMs is 10 minutes
                 Default: interval1min(6)
                "
            REFERENCE
                "802.1ag clause 12.14.6.1.3:e"
            DEFVAL { interval1min }
            ::= { hwCfmMaNetEntry 4 }

        hwCfmRMepDetectEnabled OBJECT-TYPE
            SYNTAX TruthValue
            MAX-ACCESS read-create
            STATUS current
            DESCRIPTION
                "Indicates the RMEP detection status of an MA.
                 Options:
                 1. true(1)  -indicates the RMEP detection of an MA is on
                 2. false(2) -indicates the RMEP detection of an MA is off
                 Default: true(1)
                "
            REFERENCE
                ""
            DEFVAL { true }
            ::= { hwCfmMaNetEntry 5 }

        hwCfmMaNetRowStatus OBJECT-TYPE
            SYNTAX RowStatus
            MAX-ACCESS read-create
            STATUS current
            DESCRIPTION
                "Row status, used to create, modify, and delete an MA.
                 Options:
                 1. active(1)      -indicates the query operation
                 2. createAndGo(4) -indicates the creating operation
                 3. destroy(6)     -indicates the deleting operation
                 In the query, active(1) is returned. To create an MA, set the row status to createAndGo(4).
                 To delete an MA, set the row status to destroy(6).
                "
            ::= { hwCfmMaNetEntry 6 }

         hwCfmMipExtTable OBJECT-TYPE
            SYNTAX SEQUENCE OF HwCfmMipExtEntry
            MAX-ACCESS not-accessible
            STATUS current
            DESCRIPTION
                "Describes the MIP information in the CFM and supports only the query operation on the MIP.
                 The indexes of this table are hwCfmMipExtIfIndex, hwCfmMipExtSubIndex, hwCfmMipExtVlanId, hwCfmMipExtIfType,
                 hwCfmMipExtVlantag1 and hwCfmMipExtVlantag2.
                "
            REFERENCE
                "802.1ag clauses 12.14.7 and 19.2"
            ::= { hwEthernetOAMMibObject 15 }

        hwCfmMipExtEntry OBJECT-TYPE
            SYNTAX HwCfmMipExtEntry
            MAX-ACCESS not-accessible
            STATUS current
            DESCRIPTION
                "Describes the MIP information in the CFM and supports only the query operation on the MIP.
                 The indexes of this entry are hwCfmMipExtIfIndex, hwCfmMipExtSubIndex, hwCfmMipExtVlanId, hwCfmMipExtIfType,
                 hwCfmMipExtVlantag1 and hwCfmMipExtVlantag2.
                "
            INDEX
                {
                hwCfmMipExtIfIndex,
                hwCfmMipExtSubIndex,
                hwCfmMipExtVlanId,
                hwCfmMipExtIfType,
                hwCfmMipExtVlantag1,
                hwCfmMipExtVlantag2
                }
            ::= { hwCfmMipExtTable 1 }

        HwCfmMipExtEntry ::=
            SEQUENCE {
                hwCfmMipExtIfIndex
                   Integer32,
                hwCfmMipExtSubIndex
                   Integer32,
                hwCfmMipExtVlanId
                   Integer32,
                hwCfmMipExtIfType
                   INTEGER,
                hwCfmMipExtVlantag1
                   Integer32,
                hwCfmMipExtVlantag2
                   Integer32,
                hwCfmMipExtLevel
                   Integer32,
                hwCfmMipExtMacAddress
                   MacAddress
                }

        hwCfmMipExtIfIndex OBJECT-TYPE
            SYNTAX Integer32
            MAX-ACCESS not-accessible
            STATUS current
            DESCRIPTION
                "Queries the ifIndex of the MIP port, consistent with the ifIndex of a Huawei MIB.
                "
            REFERENCE
                "802.1ag clauses 3.19, 19.2 and 12.14.7"
            ::= { hwCfmMipExtEntry 1 }

        hwCfmMipExtSubIndex OBJECT-TYPE
            SYNTAX Integer32
            MAX-ACCESS not-accessible
            STATUS current
            DESCRIPTION
                "Queries the sub-index of the MIP port. In the case of a GPON port, when the system
                 works in the GPON old mode, issues the GEM port ID; when the system works in the
                 GPON new mode, issues OntId for the low 16 bits and GemIndex for the high 16 bits.
                 In the case of an ATM/xDSL port, issues VPI for the low 16 bits and VCI for the high
                 16 bits. In other cases, a value with all Fs is issued.
                "
            REFERENCE
                "802.1ag clauses 3.19, 19.2 and 12.14.7"
            ::= { hwCfmMipExtEntry 2 }

        hwCfmMipExtVlanId OBJECT-TYPE
            SYNTAX Integer32(1..4094)
            MAX-ACCESS not-accessible
            STATUS current
            DESCRIPTION
                "Queries the VLAN of the MIP. It is a valid VLAN ID in the range of 1-4094.
                "
            REFERENCE
                "802.1ag clauses 3.19, 19.2 and 12.14.7"
            ::= { hwCfmMipExtEntry 3 }

        hwCfmMipExtIfType OBJECT-TYPE
            SYNTAX INTEGER
                {
                port(1),
                l2vpn(2)
                }
            MAX-ACCESS not-accessible
            STATUS current
            DESCRIPTION
                "Indicates the MIP port type.
                 Options:
                 1. port(1)                 -indicates a port
                 4. l2vpn(2)                -indicates a Layer 2 virtual private network
                "
            ::= { hwCfmMipExtEntry 4 }

        hwCfmMipExtVlantag1 OBJECT-TYPE
            SYNTAX Integer32(-1|1..4095|65534)
            MAX-ACCESS not-accessible
            STATUS current
            DESCRIPTION
                "Indicates vlantag1 in the CFM.
                 It is a valid VLAN ID with the value range 1-4095.
                 -1 indicates an invalid value for vlantag1.
                 65534 indicates that the MIP is unaware of VLAN tags.
                "
            ::= { hwCfmMipExtEntry 5 }

        hwCfmMipExtVlantag2 OBJECT-TYPE
            SYNTAX Integer32(-1|1..4095)
            MAX-ACCESS not-accessible
            STATUS current
            DESCRIPTION
                "Indicates vlantag2 in the CFM. Vlantag2 is the user-side inner VLAN.
                 It is a valid VLAN ID with the value range 1-4095.
                 -1 indicates an invalid value for vlantag2.
                "
            ::= { hwCfmMipExtEntry 6 }

        hwCfmMipExtLevel OBJECT-TYPE
            SYNTAX Integer32(0..7)
            MAX-ACCESS read-only
            STATUS current
            DESCRIPTION
                "Indicates the MIP level, in the range of 0-7.
                "
            REFERENCE
                "802.1ag clause 12.14.7.1.3:b"
            ::= { hwCfmMipExtEntry 7 }

        hwCfmMipExtMacAddress OBJECT-TYPE
            SYNTAX      MacAddress
            MAX-ACCESS  read-only
            STATUS      current
            DESCRIPTION
                "MAC address of the MIP."
            REFERENCE
                "802.1ag clause J.6 MP addressing"
            ::= { hwCfmMipExtEntry 8 }

         hwY1731TestIdTable OBJECT-TYPE
            SYNTAX SEQUENCE OF HwY1731TestIdEntry
            MAX-ACCESS not-accessible
            STATUS current
            DESCRIPTION
                "This table specifies the information for PM instance.
                 The index of this table is hwY1731TestId.
                "
            ::= { hwEthernetOAMMibObject 16 }

        hwY1731TestIdEntry OBJECT-TYPE
            SYNTAX HwY1731TestIdEntry
            MAX-ACCESS not-accessible
            STATUS current
            DESCRIPTION
                "This table specifies the information for PM instance.
                 The index of this entry is hwY1731TestId.
                "
            INDEX { hwY1731TestId }
            ::= { hwY1731TestIdTable 1 }

        HwY1731TestIdEntry ::=
            SEQUENCE {
                hwY1731TestId
                   Unsigned32,
                hwY1731LocalMdIndex
                   Integer32,
                hwY1731LocalMaIndex
                   Integer32,
                hwY1731LocalMepId
                   Integer32,
                hwY1731RemoteIsMepId
                   TruthValue,
                hwY1731RemoteMepId
                   Integer32,
                hwY1731RemoteMepMacAddress
                   MacAddress,
                hwY1731OnwardMacAddress
                   MacAddress,
                hwY1731BackwardMacAddress
                   MacAddress,
                hwY1731IsUpdateOnwardMacAddress
                   TruthValue,
                hwY1731IsUpdateBackwardMacAddress
                   TruthValue,
                hwY1731TX8021p
                   Integer32,
                hwY1731RX8021p
                   Integer32,
                hwY1731TestIdRowStatus
                   RowStatus,
                hwY1731TaskType
                   BITS,
                hwY1731TaskIfActive 
                   BITS,
                hwY1731TaskIsContinue
                   BITS                
                }

        hwY1731TestId OBJECT-TYPE
            SYNTAX     Unsigned32 (65536..4294967293)
            MAX-ACCESS not-accessible
            STATUS     current
            DESCRIPTION
                "Indicates the PM instance ID.
                 Range: 65536-4294967293
                "
            ::= { hwY1731TestIdEntry 1 }

        hwY1731LocalMdIndex OBJECT-TYPE
            SYNTAX     Integer32 (1..8)
            MAX-ACCESS read-create
            STATUS     current
            DESCRIPTION
                "Indicates the local MD index.
                 Range: 1-8
                "
            ::= { hwY1731TestIdEntry 2 }

        hwY1731LocalMaIndex OBJECT-TYPE
            SYNTAX     Integer32 (1..4096)
            MAX-ACCESS read-create
            STATUS     current
            DESCRIPTION
                "Indicates the local MA index.
                 Range: 1-4096
                "
            ::= { hwY1731TestIdEntry 3 }

        hwY1731LocalMepId OBJECT-TYPE
            SYNTAX     Integer32 (1..8191)
            MAX-ACCESS read-create
            STATUS     current
            DESCRIPTION
                "Indicates the local MEP ID.
                 Range: 1-8191
                "
            ::= { hwY1731TestIdEntry 4 }

        hwY1731RemoteIsMepId OBJECT-TYPE
            SYNTAX     TruthValue
            MAX-ACCESS read-create
            STATUS     current
            DESCRIPTION
                "Indicates the way of specifies the remote MEP.
                 Options:
                 1. true(1)  -indicates the remote MEP by the remote MEP ID
                 2. false(2) -indicates the remote MEP by the MAC address of remote MEP
                "
            ::= { hwY1731TestIdEntry 5 }

        hwY1731RemoteMepId OBJECT-TYPE
            SYNTAX     Integer32 (-1 | 1..8191)
            MAX-ACCESS read-create
            STATUS     current
            DESCRIPTION
                 "Indicates the remote MEP ID.
                 Range: -1, 1-8191
                 -1: indicates invalid value.
                "
            ::= { hwY1731TestIdEntry 6 }

        hwY1731RemoteMepMacAddress OBJECT-TYPE
            SYNTAX     MacAddress
            MAX-ACCESS read-create
            STATUS     current
            DESCRIPTION
                "Indicates the MAC address of remote MEP.
                "
            ::= { hwY1731TestIdEntry 7 }

        hwY1731OnwardMacAddress OBJECT-TYPE
            SYNTAX     MacAddress
            MAX-ACCESS read-create
            STATUS     current
            DESCRIPTION
                "Indicates the onward MAC address of the MEP.
                "
            ::= { hwY1731TestIdEntry 8 }

        hwY1731BackwardMacAddress OBJECT-TYPE
            SYNTAX     MacAddress
            MAX-ACCESS read-create
            STATUS     current
            DESCRIPTION
                "Indicates the backward MAC address of the MEP.
                "
            ::= { hwY1731TestIdEntry 9 }

        hwY1731IsUpdateOnwardMacAddress OBJECT-TYPE
            SYNTAX     TruthValue
            MAX-ACCESS read-create
            STATUS     current
            DESCRIPTION
                "Indicates the onward MAC learning mode.
                 Options:
                 1. true(1)  -indicates the onward MAC learning mode is update
                 2. false(2) -indicates the onward MAC learning mode is not update
                 Default: false(2)
                "
            ::= { hwY1731TestIdEntry 10 }

        hwY1731IsUpdateBackwardMacAddress OBJECT-TYPE
            SYNTAX     TruthValue
            MAX-ACCESS read-create
            STATUS     current
            DESCRIPTION
                "Indicates the backward MAC learning mode.
                 Options:
                 1. true(1)  -indicates the backward MAC learning mode is update
                 2. false(2) -indicates the backward MAC learning mode is not update
                 Default: false(2)
                "
            ::= { hwY1731TestIdEntry 11 }

        hwY1731TX8021p OBJECT-TYPE
            SYNTAX     Integer32 (-1..7)
            MAX-ACCESS read-create
            STATUS     current
            DESCRIPTION
                "Indicates the send 802.1p value.
                 Range: -1-7
                 -1: indicates the send priority of the packets is not considered.
                "
            ::= { hwY1731TestIdEntry 12 }

        hwY1731RX8021p OBJECT-TYPE
            SYNTAX     Integer32 (-1..7)
            MAX-ACCESS read-create
            STATUS     current
            DESCRIPTION
                "Indicates the receive 802.1p value.
                 Range: -1-7
                 -1: indicates the receive priority of the packets is not considered.
                "
            ::= { hwY1731TestIdEntry 13 }

        hwY1731TestIdRowStatus OBJECT-TYPE
            SYNTAX     RowStatus
            MAX-ACCESS read-create
            STATUS     current
            DESCRIPTION
                "Indicates the row status of the PM instance.
                 Options:
                 1. active(1)      -indicates the query operation
                 2. createAndGo(4) -indicates the creating operation
                 3. destroy(6)     -indicates the deleting operation
                 In the query, active(1) is returned. To create an PM instance, set the row status to
                 createAndGo(4). To delete an PM instance, set the row status to destroy(6).
                "
            ::= { hwY1731TestIdEntry 14 }   
                    
        hwY1731TaskType OBJECT-TYPE
            SYNTAX BITS
                {
                bDefsingleLM(0),
                bDefdualLM(1),
                bDefonewayDM(2),
                bDeftwowayDM(3),
                bDeftest(4),
                bDefsingleSLM(5),
                bDefreserved6(6),
                bDefreserved7(7),
                bDefreserved8(8),
                bDefreserved9(9),
                bDefreserved10(10),
                bDefreserved11(11),
                bDefreserved12(12),
                bDefreserved13(13),
                bDefreserved14(14),
                bDefreserved15(15),
                bDefreserved16(16),
                bDefreserved17(17),
                bDefreserved18(18),
                bDefreserved19(19),
                bDefreserved20(20),
                bDefreserved21(21),
                bDefreserved22(22),
                bDefreserved23(23),
                bDefreserved24(24),
                bDefreserved25(25),
                bDefreserved26(26),
                bDefreserved27(27),
                bDefreserved28(28),
                bDefreserved29(29),
                bDefreserved30(30),
                bDefreserved31(31)
                }
            MAX-ACCESS read-only
            STATUS     current
            DESCRIPTION
                "Indicates the task type of the PM instance.
                 Options:
                 1. bDefsingleLM(0)  -indicates the single-ended loss measurement
                 2. bDefdualLM(1)    -indicates the dual-ended loss measurement
                 3. bDefonewayDM(2)  -indicates the one-way time delay measurement
                 4. bDeftwowayDM(3)  -indicates the two-way time delay measurement
                 5. bDeftest(4)      -indicates the test loss measurement
                 6. bDefsingleSLM(5) -indicates the single-ended synthetic loss measurement
                 Other bits are reserved. For each bit, 1 indicates that the PM task is valid, 
                 and 0 indicates that the PM task is invalid. 
                 Default: 0.    
                "
            ::= { hwY1731TestIdEntry 15 }
           
        hwY1731TaskIfActive OBJECT-TYPE
            SYNTAX BITS
                {
                bDefsingleLMIfActive(0),
                bDefdualLMIfActive(1),
                bDefonewayDMIfActive(2),
                bDeftwowayDMIfActive(3),
                bDeftestIfActive(4),
                bDefsingelSLMIfActive(5),
                bDefreserved6(6),
                bDefreserved7(7),
                bDefreserved8(8),
                bDefreserved9(9),
                bDefreserved10(10),
                bDefreserved11(11),
                bDefreserved12(12),
                bDefreserved13(13),
                bDefreserved14(14),
                bDefreserved15(15),
                bDefreserved16(16),
                bDefreserved17(17),
                bDefreserved18(18),
                bDefreserved19(19),
                bDefreserved20(20),
                bDefreserved21(21),
                bDefreserved22(22),
                bDefreserved23(23),
                bDefreserved24(24),
                bDefreserved25(25),
                bDefreserved26(26),
                bDefreserved27(27),
                bDefreserved28(28),
                bDefreserved29(29),
                bDefreserved30(30),
                bDefreserved31(31)
                }
            MAX-ACCESS read-only
            STATUS     current
            DESCRIPTION
                "Indicates the role of the PM task.
                 Options:
                 1. bDefsingleLMIfActive(0)  -indicates the role of the single-ended loss measurement
                 2. bDefdualLMIfActive(1)    -indicates the role of the dual-ended loss measurement
                 3. bDefonewayDMIfActive(2)  -indicates the role of the one-way time delay measurement
                 4. bDeftwowayDMIfActive(3)  -indicates the role of the two-way time delay measurement
                 5. bDeftestIfActive(4)      -indicates the role of the test loss measurement
                 6. bDefsingelSLMIfActive(5) -indicates the role of the single-ended synthetic loss measurement
                 Other bits are reserved. For each bit, when the corresponding bit of hwY1731TaskType is 1, 
                 1 indicates that the role of the PM task is sender, and 0 indicates that the role of the PM task is receiver.
                 Default: 0.  
                "
            ::= { hwY1731TestIdEntry 16 }
            
        hwY1731TaskIsContinue OBJECT-TYPE
            SYNTAX BITS
                {
                bDefsingleLMIsContinue(0),
                bDefdualLMIsContinue(1),
                bDefonewayDMIsContinue(2),
                bDeftwowayDMIsContinue(3),
                bDeftestIsContinue(4),
                bDefsingelSLMIsContinue(5),
                bDefreserved6(6),
                bDefreserved7(7),
                bDefreserved8(8),
                bDefreserved9(9),
                bDefreserved10(10),
                bDefreserved11(11),
                bDefreserved12(12),
                bDefreserved13(13),
                bDefreserved14(14),
                bDefreserved15(15),
                bDefreserved16(16),
                bDefreserved17(17),
                bDefreserved18(18),
                bDefreserved19(19),
                bDefreserved20(20),
                bDefreserved21(21),
                bDefreserved22(22),
                bDefreserved23(23),
                bDefreserved24(24),
                bDefreserved25(25),
                bDefreserved26(26),
                bDefreserved27(27),
                bDefreserved28(28),
                bDefreserved29(29),
                bDefreserved30(30),
                bDefreserved31(31)
                }
            MAX-ACCESS read-only
            STATUS     current
            DESCRIPTION
                "Indicates the operating mode of the PM task.
                 Options:
                 1. bDefsingleLM(0)  -indicates the operating mode of the single-ended loss measurement
                 2. bDefdualLM(1)    -indicates the operating mode of the dual-ended loss measurement
                 3. bDefonewayDM(2)  -indicates the operating mode of the one-way time delay measurement
                 4. bDeftwowayDM(3)  -indicates the operating mode of the two-way time delay measurement
                 5. bDeftest(4)      -indicates the operating mode of the test loss measurement
                 6. bDefsingleSLM(5) -indicates the operating mode of the single-ended synthetic loss measurement
                 Other bits are reserved. For each bit, when the corresponding bit of hwY1731TaskType is 1, 
                 1 indicates that the PM task runs according to demand, and 0 indicates that the PM task runs continuously. 
                 Default: 0.   
                "
            ::= { hwY1731TestIdEntry 17 }
            
         hwY1731ConfigTable  OBJECT-TYPE      
            SYNTAX SEQUENCE OF HwY1731ConfigEntry
            MAX-ACCESS not-accessible
            STATUS current
            DESCRIPTION
                "This table specifies the information for PM Task.
                 The indexes of this table are hwY1731TestId and hwY1731CmdType.
                "
            ::= { hwEthernetOAMMibObject 17 }

        hwY1731ConfigEntry OBJECT-TYPE
            SYNTAX HwY1731ConfigEntry
            MAX-ACCESS not-accessible
            STATUS current
            DESCRIPTION
                "This table specifies the information for PM Task.
                 The indexes of this entry are hwY1731TestId and hwY1731CmdType.
                "
            INDEX
                {
                hwY1731TestId,
                hwY1731CmdType
                }
            ::= { hwY1731ConfigTable  1 }

        HwY1731ConfigEntry ::=
            SEQUENCE {
                hwY1731CmdType
                   INTEGER,
                hwY1731IsContinue
                   TruthValue,
                hwY1731CmdEnable
                   TruthValue,
                hwY1731IfActive
                   TruthValue,
                hwY1731Interval
                   INTEGER,
                hwY1731Count
                   Unsigned32
                }

        hwY1731CmdType OBJECT-TYPE
            SYNTAX INTEGER
            {
                singleLM(1),
                dualLM(2),
                onewayDM(3),
                twowayDM(4),
                test(5),
                singleSLM(6)
            }
            MAX-ACCESS not-accessible
            STATUS current
            DESCRIPTION
                "Indicates the type of the PM task.
                 Options:
                 1. singleLM(1)   -indicates the type of the PM task is single-ended loss measurement
                 2. dualLM(2)     -indicates the type of the PM task is dual-ended loss measurement
                 3. onewayDM(3)   -indicates the type of the PM task is one-way time delay measurement
                 4. twowayDM(4)   -indicates the type of the PM task is two-way time delay measurement
                 5. test(5)       -indicates the type of the PM task is test loss measurement
                 6. singleSLM(6)  -indicates the type of the PM task is single-ended synthetic loss measurement
                "
            ::= { hwY1731ConfigEntry 1 }

        hwY1731IsContinue OBJECT-TYPE
            SYNTAX     TruthValue
            MAX-ACCESS read-write
            STATUS     current
            DESCRIPTION
                "Indicates the operating mode of the PM task.
                 Options:
                 1. true(1)  -indicates the PM task run continuously
                 2. false(2) -indicates the PM task run according to demand
                 Default: false(2)
                "
            ::= { hwY1731ConfigEntry 2 }

        hwY1731CmdEnable OBJECT-TYPE
            SYNTAX     TruthValue
            MAX-ACCESS read-write
            STATUS     current
            DESCRIPTION
                "Indicates the operating of the PM task.
                 Options:
                 1. true(1)  -indicates the start operation
                 2. false(2) -indicates the stop operation
                "
            ::= { hwY1731ConfigEntry 3 }

        hwY1731IfActive OBJECT-TYPE
            SYNTAX     TruthValue
            MAX-ACCESS read-write
            STATUS     current
            DESCRIPTION
                "Indicates the role of the PM task.
                 Options:
                 1. true(1)  -indicates the role of the PM task is sender
                 2. false(2) -indicates the role of the PM task is receiver
                 "
            ::= { hwY1731ConfigEntry 4 }

        hwY1731Interval OBJECT-TYPE
            SYNTAX INTEGER
            {
                intervalInvalid(1),
                interval1000ms(2),
                interval10000ms(3)
            }
            MAX-ACCESS read-write
            STATUS current
            DESCRIPTION
                "Indicates the interval time for sending PDU packets.
                 Options:
                 1. intervalInvalid(1)    -indicates invalid value
                 2. interval1000ms(2)     -indicates interval is 1000, in the unit of millisecond
                 3. interval10000ms(3)    -indicates interval is 10000, in the unit of millisecond
                "
            ::= { hwY1731ConfigEntry 5 }

        hwY1731Count OBJECT-TYPE
            SYNTAX     Unsigned32 (1..1000 | 4294967295)
            MAX-ACCESS read-write
            STATUS     current
            DESCRIPTION
                "Indicates the count of sending packets.
                 Range: 1-1000, 4294967295
                 4294967295: indicates invalid value.
               "
            ::= { hwY1731ConfigEntry 6 }

         hwY1731SingleLossStatTable OBJECT-TYPE
            SYNTAX SEQUENCE OF HwY1731SingleLossStatEntry
            MAX-ACCESS not-accessible
            STATUS current
            DESCRIPTION
                "Indicates the single-ended LM test statistics.
                 The indexes of this table are hwY1731SinLMTestId, hwY1731SinLMSeq.
                "
            ::= { hwEthernetOAMMibObject 18 }

        hwY1731SingleLossStatEntry OBJECT-TYPE
            SYNTAX HwY1731SingleLossStatEntry
            MAX-ACCESS not-accessible
            STATUS current
            DESCRIPTION
                "Indicates the single-ended LM test statistics.
                 The indexes of this entry are hwY1731SinLMTestId, hwY1731SinLMSeq.
                "
            INDEX
                {
                hwY1731SinLMTestId,
                hwY1731SinLMSeq
                }
            ::= { hwY1731SingleLossStatTable 1 }

        HwY1731SingleLossStatEntry ::=
            SEQUENCE {
                hwY1731SinLMTestId
                   Unsigned32,
                hwY1731SinLMSeq
                   Unsigned32,
                hwY1731SinLMTimeStamp
                   Unsigned32,
                hwY1731SinLMErrInfo
                   INTEGER,
                hwY1731SinLMLocal
                   Unsigned32,
                hwY1731SinLMLocalRatio
                   Unsigned32,
                hwY1731SinLMRemote
                   Unsigned32,
                hwY1731SinLMRemoteRatio
                   Unsigned32
                }

        hwY1731SinLMTestId OBJECT-TYPE
            SYNTAX     Unsigned32 (65536..4294967293)
            MAX-ACCESS not-accessible
            STATUS     current
            DESCRIPTION
                "Indicates the test ID of statistics for single-ended LM.
                "
            ::= { hwY1731SingleLossStatEntry 1 }

        hwY1731SinLMSeq OBJECT-TYPE
            SYNTAX     Unsigned32 (1..4294967294)
            MAX-ACCESS not-accessible
            STATUS     current
            DESCRIPTION
                "Indicates the sequence of statistics for single-ended LM.
                "
            ::= { hwY1731SingleLossStatEntry 2 }

        hwY1731SinLMTimeStamp OBJECT-TYPE
            SYNTAX     Unsigned32 (0..4294967295)
            MAX-ACCESS read-only
            STATUS     current
            DESCRIPTION
                "Indicates the time stamp of statistics for single-ended LM.
                "
            ::= { hwY1731SingleLossStatEntry 3 }

        hwY1731SinLMErrInfo OBJECT-TYPE
            SYNTAX INTEGER
                {
                noErr(1),
                lmErr(2),
                lmRatioErr(3),
                dmErr(4),
                overturn(5)
                }
            MAX-ACCESS read-only
            STATUS current
            DESCRIPTION
                "Indicates the LM error type.
                 Options:
                 1. noErr(1)                     -No error
                 2. lmErr(2)                     -indicates the statistics for single-ended LM are incorrect
                 3. lmRatioErr(3)                -indicates the statistics for average single-ended LM ratio are incorrect
                 4. dmErr(4)                     -indicates the statistics for two-way DM are incorrect
                 5. overturn(5)                  -indicates the value exceeds the threshold and therefore a reverse occurs
                "
            ::= { hwY1731SingleLossStatEntry 4 }

        hwY1731SinLMLocal OBJECT-TYPE
            SYNTAX     Unsigned32 (0..4294967295)
            MAX-ACCESS read-only
            STATUS     current
            DESCRIPTION
                "Indicates the statistics for near-end single-ended LM.
                "
            ::= { hwY1731SingleLossStatEntry 5 }

        hwY1731SinLMLocalRatio OBJECT-TYPE
            SYNTAX Unsigned32 (0..100000000)
            MAX-ACCESS read-only
            STATUS current
            DESCRIPTION
                "Indicates the ratio of statistics for near-end single-ended LM, unit:10^(-8).
                "
            ::= { hwY1731SingleLossStatEntry 6 }

        hwY1731SinLMRemote OBJECT-TYPE
            SYNTAX     Unsigned32 (0..4294967295)
            MAX-ACCESS read-only
            STATUS     current
            DESCRIPTION
                "Indicates the statistics for far-end single-ended LM.
                "
            ::= { hwY1731SingleLossStatEntry 7 }

        hwY1731SinLMRemoteRatio OBJECT-TYPE
            SYNTAX      Unsigned32 (0..100000000)
            MAX-ACCESS  read-only
            STATUS      current
            DESCRIPTION
                "Indicates the ratio of statistics for far-end single-ended LM, unit:10^(-8).
                "
            ::= { hwY1731SingleLossStatEntry 8 }

         hwY1731TwoDelayStatTable OBJECT-TYPE
            SYNTAX SEQUENCE OF HwY1731TwoDelayStatEntry
            MAX-ACCESS not-accessible
            STATUS current
            DESCRIPTION
                "Indicates the two-way DM test statistics.
                 The indexes of this table are hwY1731TwoDMTestId, hwY1731TwoDMSeq.
                "
            ::= { hwEthernetOAMMibObject 19 }

        hwY1731TwoDelayStatEntry OBJECT-TYPE
            SYNTAX HwY1731TwoDelayStatEntry
            MAX-ACCESS not-accessible
            STATUS current
            DESCRIPTION
                "Indicates the two-way DM test statistics.
                 The indexes of this entry are hwY1731TwoDMTestId, hwY1731TwoDMSeq.
                "
            INDEX
                {
                hwY1731TwoDMTestId,
                hwY1731TwoDMSeq
                }
            ::= { hwY1731TwoDelayStatTable 1 }

        HwY1731TwoDelayStatEntry ::=
            SEQUENCE {
                hwY1731TwoDMTestId
                   Unsigned32,
                hwY1731TwoDMSeq
                   Unsigned32,
                hwY1731TwoDMTimeStamp
                   Unsigned32,
                hwY1731TwoDMErrInfo
                   INTEGER,
                hwY1731TwoDMRemoteDelay
                   Integer32,
                hwY1731TwoDMRemoteJitter
                   Integer32,
                hwY1731TwoDMLocalDelay
                   Integer32,
                hwY1731TwoDMLocalJitter
                   Integer32,
                hwY1731TwoDMDelay
                   Integer32,
                hwY1731TwoDMJitter
                   Integer32
                }

        hwY1731TwoDMTestId OBJECT-TYPE
            SYNTAX     Unsigned32 (65536..4294967293)
            MAX-ACCESS not-accessible
            STATUS     current
            DESCRIPTION
                "Indicates the test ID of statistics for two-way DM.
                "
            ::= { hwY1731TwoDelayStatEntry 1 }

        hwY1731TwoDMSeq OBJECT-TYPE
            SYNTAX     Unsigned32 (1..4294967294)
            MAX-ACCESS not-accessible
            STATUS     current
            DESCRIPTION
                "Indicates the sequence of statistics for two-way DM.
                "
            ::= { hwY1731TwoDelayStatEntry 2 }

        hwY1731TwoDMTimeStamp OBJECT-TYPE
            SYNTAX     Unsigned32 (0..4294967295)
            MAX-ACCESS read-only
            STATUS     current
            DESCRIPTION
                "Indicates the time stamp of statistics for two-way DM.
                "
            ::= { hwY1731TwoDelayStatEntry 3 }

        hwY1731TwoDMErrInfo OBJECT-TYPE
            SYNTAX INTEGER
                {
                noErr(1),
                lmErr(2),
                lmRatioErr(3),
                dmErr(4),
                overturn(5)
                }
            MAX-ACCESS read-only
            STATUS current
            DESCRIPTION
                "Indicates the DM error type.
                 Options:
                 1. noErr(1)                     -No error
                 2. lmErr(2)                     -indicates the statistics for single-ended LM are incorrect
                 3. lmRatioErr(3)                -indicates the statistics for average single-ended LM ratio are incorrect
                 4. dmErr(4)                     -indicates the statistics for two-way DM are incorrect
                 5. overturn(5)                  -indicates the value exceeds the threshold and therefore a reverse occurs
                "
            ::= { hwY1731TwoDelayStatEntry 4 }

        hwY1731TwoDMRemoteDelay OBJECT-TYPE
            SYNTAX     Integer32 (-2147483648..2147483647)
            MAX-ACCESS read-only
            STATUS     current
            DESCRIPTION
                "Indicates the delay of statistics for one-way-far DM, unit:us.
                "
            ::= { hwY1731TwoDelayStatEntry 5 }

        hwY1731TwoDMRemoteJitter OBJECT-TYPE
            SYNTAX     Integer32 (0..2147483647)
            MAX-ACCESS read-only
            STATUS     current
            DESCRIPTION
                "Indicates the jitter of statistics for one-way-far DM, unit:us.
                "
            ::= { hwY1731TwoDelayStatEntry 6 }

        hwY1731TwoDMLocalDelay OBJECT-TYPE
            SYNTAX     Integer32 (-2147483648..2147483647)
            MAX-ACCESS read-only
            STATUS     current
            DESCRIPTION
                "Indicates the delay of statistics for one-way-near DM, unit:us.
                "
            ::= { hwY1731TwoDelayStatEntry 7 }

        hwY1731TwoDMLocalJitter OBJECT-TYPE
            SYNTAX     Integer32 (0..2147483647)
            MAX-ACCESS read-only
            STATUS     current
            DESCRIPTION
                "Indicates the jitter of statistics for one-way-near DM, unit:us."
            ::= { hwY1731TwoDelayStatEntry 8 }

        hwY1731TwoDMDelay OBJECT-TYPE
            SYNTAX     Integer32 (-2147483648..2147483647)
            MAX-ACCESS read-only
            STATUS     current
            DESCRIPTION
                "Indicates the delay of statistics for two-way DM, unit:us.
                "
            ::= { hwY1731TwoDelayStatEntry 9 }

        hwY1731TwoDMJitter OBJECT-TYPE
            SYNTAX     Integer32 (0..2147483647)
            MAX-ACCESS read-only
            STATUS     current
            DESCRIPTION
                "Indicates the jitter of statistics for two-way DM, unit:us."
            ::= { hwY1731TwoDelayStatEntry 10 }

        hwEthernetOAMTrapsVbOids OBJECT IDENTIFIER ::= { hwEthernetOAM 3 }

        hwCfmLinkTraceMipMacAddress OBJECT-TYPE
            SYNTAX MacAddress
            MAX-ACCESS accessible-for-notify
            STATUS current
            DESCRIPTION
                "Indicates the  middle mac-address of middle nodes in LinkTrace operation.
                "
            ::= { hwEthernetOAMTrapsVbOids 1 }

        hwEFMEventType OBJECT-TYPE
            SYNTAX OCTET STRING
            MAX-ACCESS accessible-for-notify
            STATUS current
            DESCRIPTION
                "Indicates the type of EFM event.
                "
            ::= { hwEthernetOAMTrapsVbOids 2 }

        hwEFMEventLocation OBJECT-TYPE
            SYNTAX OCTET STRING
            MAX-ACCESS accessible-for-notify
            STATUS current
            DESCRIPTION
                "Indicates the location of EFM event.
                "
            ::= { hwEthernetOAMTrapsVbOids 3 }

        hwCfmMepLbResultLbmOut OBJECT-TYPE
            SYNTAX Counter32
            MAX-ACCESS accessible-for-notify
            STATUS current
            DESCRIPTION
                "Indicates the number of LBMs sent by the MEP per one loopback.
                "
            ::= { hwEthernetOAMTrapsVbOids 4 }

        hwCfmMepLbResultLbrIn OBJECT-TYPE
            SYNTAX Counter32
            MAX-ACCESS accessible-for-notify
            STATUS current
            DESCRIPTION
                "Indicates the number of correct LBRs received by the MEP per one loopback.
                "
            ::= { hwEthernetOAMTrapsVbOids 5 }

        hwCfmMepLtResultOK OBJECT-TYPE
            SYNTAX Integer32(0..1)
            MAX-ACCESS accessible-for-notify
            STATUS current
            DESCRIPTION
                "Indicates the result of LT performed by the MEP.
                 Options:
                 1. true(0)   -the Linktrace succeed
                 2. false(1)  -the Linktrace fail
                 Default: true(0)
                "
            ::= { hwEthernetOAMTrapsVbOids 6 }

        hwCfmMepLbResultOutOfOrderLbrIn OBJECT-TYPE
            SYNTAX Integer32
            MAX-ACCESS accessible-for-notify
            STATUS current
            DESCRIPTION
                "Indicates the number of out-of-order LBRs received by the MEP per loopback."
            ::= { hwEthernetOAMTrapsVbOids 7 }


        hwCfmMepLbTestResultLbmOut OBJECT-TYPE
            SYNTAX Counter32
            MAX-ACCESS accessible-for-notify
            STATUS current
            DESCRIPTION
                "Indicates the number of LBMs sent by the MEP in each LB diagnostic test."
            ::= { hwEthernetOAMTrapsVbOids 8 }

        hwCfmMepLbTestResultLbrIn OBJECT-TYPE
            SYNTAX Counter32
            MAX-ACCESS accessible-for-notify
            STATUS current
            DESCRIPTION
                "Indicates the number of correct LBRs received by the MEP in each LB diagnostic test."
            ::= { hwEthernetOAMTrapsVbOids 9 }

        hwCfmMepLbTestResultCRCErrorLbrIn OBJECT-TYPE
            SYNTAX Counter32
            MAX-ACCESS accessible-for-notify
            STATUS current
            DESCRIPTION
                "Indicates the number of CRC error LBRs received by the MEP in each LB diagnostic test."
            ::= { hwEthernetOAMTrapsVbOids 10 }

        hwCfmMepLbTestResultBERLbrIn OBJECT-TYPE
            SYNTAX Counter32
            MAX-ACCESS accessible-for-notify
            STATUS current
            DESCRIPTION
                "Indicates the number of bit error LBRs received by the MEP in each LB diagnostic test."
            ::= { hwEthernetOAMTrapsVbOids 11 }

        hwCfmMepLbTestResultOutOfOrderLbrIn OBJECT-TYPE
            SYNTAX Counter32
            MAX-ACCESS accessible-for-notify
            STATUS current
            DESCRIPTION
                "Indicates the number of out-of-order LBRs received by the MEP in each LB diagnostic test."
            ::= { hwEthernetOAMTrapsVbOids 12 }

        hwEthernetOAMTraps OBJECT IDENTIFIER ::= { hwEthernetOAM 4 }

        hwEthernetOAMCommonTraps OBJECT IDENTIFIER ::= { hwEthernetOAMTraps 1 }

        hwEthernetOAMCommonTrapsPrefix OBJECT IDENTIFIER ::= { hwEthernetOAMCommonTraps 0 }

        hwEthernetOAMLBCheckTrap NOTIFICATION-TYPE
             OBJECTS
                 {
                 dot1agCfmMdIndex,
                 dot1agCfmMaIndex,
                 hwCfmMepIdentifier,
                 hwCfmMepTransmitLbmDestMacAddress,
                 hwCfmMepLbResultLbrIn,
                 hwCfmMepLbResultLbmOut,
                 hwCfmMepLbResultOutOfOrderLbrIn
                 }
             STATUS current
             DESCRIPTION
                 "The trap is generated when LoopBack operation happens.
                  The hwCfmLoopbackNumIn indicates the number of LBR receives,defined in hwEthernetOAMTrapsVbOids.
                 "
             ::= { hwEthernetOAMCommonTraps 0 1 }

        hwEthernetOAMLTStepCheckTrap NOTIFICATION-TYPE
            OBJECTS
                {
                dot1agCfmMdIndex,
                dot1agCfmMaIndex,
                hwCfmMepIdentifier,
                hwCfmMepTransmitLtmTargetMacAddress,
                hwCfmMepTransmitLtmTtl,
                hwCfmLinkTraceMipMacAddress
                }
            STATUS current
            DESCRIPTION
                "The trap is generated when LinkTrace operation happens at middle nodes.
                 The hwCfmLinkTraceMipMacAddress indicates the mac-address of middle nodes in LinkTrace operation,
                 defined in hwEthernetOAMTrapsVbOids.
                 Indicates the result of LinkTrace operation
                "
            ::= { hwEthernetOAMCommonTraps 0 2 }

        hwEthernetOAMLTCheckTrap NOTIFICATION-TYPE
            OBJECTS
                {
                dot1agCfmMdIndex,
                dot1agCfmMaIndex,
                hwCfmMepIdentifier,
                hwCfmMepTransmitLtmTargetMacAddress,
                hwCfmMepTransmitLtmTtl,
                hwCfmLinkTraceMipMacAddress,
                hwCfmMepLtResultOK
                }
            STATUS current
            DESCRIPTION
                "The trap is generated when LinkTrace operation Finish.
                 The hwCfmLinkTraceMipMacAddress indicates the mac-address of middle nodes in LinkTrace operation,
                 defined in hwEthernetOAMTrapsVbOids.
                 The hwCfmLinkTraceResult indicates the result of LinkTrace operation,
                 defined in hwEthernetOAMTrapsVbOids.
                "
            ::= { hwEthernetOAMCommonTraps 0 3 }

        hwEthernetOAMLBTestCheckTrap NOTIFICATION-TYPE
            OBJECTS {
                dot1agCfmMdIndex,
                dot1agCfmMaIndex,
                hwCfmMepIdentifier,
                hwCfmMepTransmitLbTestDestMacAddress,
                hwCfmMepLbTestResultLbrIn,
                hwCfmMepLbTestResultLbmOut,
                hwCfmMepLbTestResultCRCErrorLbrIn,
                hwCfmMepLbTestResultBERLbrIn,
                hwCfmMepLbTestResultOutOfOrderLbrIn
                }
            STATUS current
            DESCRIPTION
                "The trap is sent when the LB diagnostic test is ended."
            ::= { hwEthernetOAMCommonTraps 0 6 }

        hwEthernetOAMAlarmTraps OBJECT IDENTIFIER ::= { hwEthernetOAMTraps 2 }

        hwCFMAlarmTraps OBJECT IDENTIFIER ::= { hwEthernetOAMAlarmTraps 1 }

        hwCFMAlarmTrapsPrefix OBJECT IDENTIFIER ::= { hwCFMAlarmTraps 0 }

        hwCFMRmepDefectTrap NOTIFICATION-TYPE
            OBJECTS
                {
                dot1agCfmMdIndex,
                dot1agCfmMaIndex,
                hwCfmMepIdentifier
                }
            STATUS   current
            DESCRIPTION
                 "The SNMP trap that is generated when CCM lose occurs.
                 "
            ::= { hwCFMAlarmTraps 0 1 }

        hwCFMErrorCcmDefectTrap NOTIFICATION-TYPE
            OBJECTS
                {
                dot1agCfmMdIndex,
                dot1agCfmMaIndex,
                hwCfmMepIdentifier
                }
            STATUS   current
            DESCRIPTION
                 "The SNMP trap that is generated when CCM error occurs.
                 "
            ::= { hwCFMAlarmTraps 0 2 }

        hwCFMXconCcmDefectTrap NOTIFICATION-TYPE
            OBJECTS
                {
                dot1agCfmMdIndex,
                dot1agCfmMaIndex,
                hwCfmMepIdentifier
                }
            STATUS   current
            DESCRIPTION
                "The SNMP trap that is generated when CCM Xcon error occurs.
                "
            ::= { hwCFMAlarmTraps 0 3 }

        hwCFMRDIDefectTrap NOTIFICATION-TYPE
            OBJECTS
                {
                dot1agCfmMdIndex,
                dot1agCfmMaIndex,
                hwCfmMepIdentifier
                }
            STATUS   current
            DESCRIPTION
                 "The SNMP trap that is generated when CCM RDI error occurs.
                 "
            ::= { hwCFMAlarmTraps 0 4 }

        hwCFMRmepDefectRecoveryTrap  NOTIFICATION-TYPE
            OBJECTS
                {
                dot1agCfmMdIndex,
                dot1agCfmMaIndex,
                hwCfmMepIdentifier
                }
            STATUS   current
            DESCRIPTION
                "The SNMP trap that is generated when CCM RDI loss occurs.
                "
            ::= { hwCFMAlarmTraps 0 5}

        hwCFMErrorCcmDefectRecoveryTrap  NOTIFICATION-TYPE
            OBJECTS
                {
                dot1agCfmMdIndex,
                dot1agCfmMaIndex,
                hwCfmMepIdentifier
                }
            STATUS   current
            DESCRIPTION
                "The SNMP trap that is generated when CCM error recovers.
                "
            ::= { hwCFMAlarmTraps 0 6}

        hwCFMXconCcmDefectRecoveryTrap  NOTIFICATION-TYPE
            OBJECTS
                {
                dot1agCfmMdIndex,
                dot1agCfmMaIndex,
                hwCfmMepIdentifier
                }
            STATUS   current
            DESCRIPTION
                 "The SNMP trap that is generated when CCM Xcon error recovers.
                 "
            ::= { hwCFMAlarmTraps 0 7}

        hwCFMRDIDefectRecoveryTrap  NOTIFICATION-TYPE
            OBJECTS
                {
                dot1agCfmMdIndex,
                dot1agCfmMaIndex,
                hwCfmMepIdentifier
                }
            STATUS   current
            DESCRIPTION
                "The SNMP trap that is generated when CCM RDI error recovers.
                "
            ::= { hwCFMAlarmTraps 0 8}

        hwCFMMacStatusDefectTrap  NOTIFICATION-TYPE
            OBJECTS
                {
                dot1agCfmMdIndex,
                dot1agCfmMaIndex,
                hwCfmMepIdentifier
                }
            STATUS   current
            DESCRIPTION
                "The SNMP trap that is generated when at least one remote MEP's interface is not up.
                "
            ::= { hwCFMAlarmTraps 0 9}

        hwCFMMacStatusDefectRecoveryTrap  NOTIFICATION-TYPE
            OBJECTS
                {
                dot1agCfmMdIndex,
                dot1agCfmMaIndex,
                hwCfmMepIdentifier
                }
            STATUS   current
            DESCRIPTION
                "The SNMP trap that is generated when all remote MEPs' interfaces become up.
                "
            ::= { hwCFMAlarmTraps 0 10}

        hwCFMIfTriggerDownTrap  NOTIFICATION-TYPE
            OBJECTS
                {
                dot1agCfmMdIndex,
                dot1agCfmMaIndex,
                hwCfmMepIdentifier,
                hwFrameIndex,
                hwSlotIndex,
                hwPortIndex
                }
            STATUS   current
            DESCRIPTION
                "The SNMP trap that is generated when port is deactivated due to the faulty ETHOAM link.
                "
            ::= { hwCFMAlarmTraps 0 11}

        hwCFMIfTriggerDownRecoveryTrap  NOTIFICATION-TYPE
            OBJECTS
                {
                dot1agCfmMdIndex,
                dot1agCfmMaIndex,
                hwCfmMepIdentifier,
                hwFrameIndex,
                hwSlotIndex,
                hwPortIndex
                }
            STATUS   current
            DESCRIPTION
                "The SNMP trap that is generated when port is activated because the ETHOAM link fault is rectified.
                "
            ::= { hwCFMAlarmTraps 0 12}


        hwCFMSystemAlarmTrap  NOTIFICATION-TYPE
                    STATUS   current
                        DESCRIPTION
                            "The SNMP trap that is generated when the system generates a number of Ethernet OAM connectivity check alarms.
                            "
                    ::= { hwCFMAlarmTraps 0 13}

        hwCFMSystemAlarmRecoveryTrap  NOTIFICATION-TYPE
                    STATUS   current
                        DESCRIPTION
                            "The SNMP trap that is generated when a number of Ethernet OAM connectivity check alarms are cleared.
                            "
                    ::= { hwCFMAlarmTraps 0 14}

        hwEthernetOAMEFMTraps OBJECT IDENTIFIER ::= { hwEthernetOAM 5 }

        hwEFMAlarmTraps OBJECT IDENTIFIER ::= { hwEthernetOAMEFMTraps 1 }

        hwEFMAlarmTrapsPrefix OBJECT IDENTIFIER ::= { hwEFMAlarmTraps 0 }

        hwDot3OAMThresholdEventTrap NOTIFICATION-TYPE
            OBJECTS
                {
                dot3OamEventLogIndex,
                ifIndex,
                dot3OamEventLogTimestamp,
                dot3OamEventLogOui,
                dot3OamEventLogType,
                dot3OamEventLogLocation,
                dot3OamEventLogWindowHi,
                dot3OamEventLogWindowLo,
                dot3OamEventLogThresholdHi,
                dot3OamEventLogThresholdLo,
                dot3OamEventLogValue,
                dot3OamEventLogRunningTotal,
                dot3OamEventLogEventTotal
                }
            STATUS  current
            DESCRIPTION
                "A hwdot3OAMThresholdEventTrap notification is sent when a local or
                 remote threshold crossing event is detected.  A local
                 threshold crossing event is detected by the local entity,
                 while a remote threshold crossing event is detected by the
                 reception of an Ethernet OAM Event Notification OAMPDU
                 indicating a threshold event.

                 This notification should not be sent more than once per
                 second.

                 The OAM entity can be derived from extracting the ifIndex from
                 the variable bindings.  The objects in the notification
                 correspond to the values in a row instance of in the
                 dot3OamEventLogTable.

                 The management entity should periodically check
                 dot3OamEventLogTable to detect any missed events."
            ::= { hwEFMAlarmTraps 0 1 }

        hwDot3OAMNonThresholdEventTrap NOTIFICATION-TYPE
            OBJECTS {
                dot3OamEventLogIndex,
                ifIndex,
                dot3OamEventLogTimestamp,
                dot3OamEventLogOui,
                dot3OamEventLogType,
                dot3OamEventLogLocation,
                dot3OamEventLogEventTotal
                }
            STATUS  current
            DESCRIPTION
                "A hwdot3OAMNonThresholdEventTrap notification is sent when a local
                 or remote non-threshold crossing event is detected.  A local
                 event is detected by the local entity, while a remote event is
                 detected by the reception of an Ethernet OAM Event
                 Notification OAMPDU indicating a non-threshold crossing event.

                 This notification should not be sent more than once per
                 second.

                 The OAM entity can be derived from extracting the ifIndex from
                 the variable bindings.  The objects in the notification
                 correspond to the values in a row instance of the
                 dot3OamEventLogTable.

                 The management entity should periodically check
                 dot3OamEventLogTable to detect any missed events."
            ::= { hwEFMAlarmTraps 0 2 }

        hwEFMLinkEventTrap  NOTIFICATION-TYPE
            OBJECTS
                {
                hwFrameIndex,
                hwSlotIndex,
                hwPortIndex,
                hwEFMEventType,
                hwEFMEventLocation
                }
            STATUS   current
            DESCRIPTION
                "The SNMP trap that is generated when Ethernet OAM event defined in 802.3ah.
                 The hwEFMEventType indicates the event type of EFM,defined in hwEthernetOAMEFMTraps.
                 The hwEFMEventLocation indicates the location of EFM event,defined in hwEthernetOAMEFMTraps.
                "
            ::= { hwEFMAlarmTraps 0 3}

-- ******************************************************************
-- The Maintenance Domain Table for ONT
-- ******************************************************************
        hwOntCfmMdTable OBJECT-TYPE
            SYNTAX SEQUENCE OF HwOntCfmMdEntry
            MAX-ACCESS not-accessible
            STATUS current
            DESCRIPTION
                "Configures an MD for ONT, including creating and deleting an MD.
                The index of this table is hwOntCfmMdIndex.
                "
            REFERENCE
                "802.1ag clauses 3.22 and 18.1"
            ::= { hwEthernetOAMMibObject 20 }

        hwOntCfmMdEntry OBJECT-TYPE
            SYNTAX HwOntCfmMdEntry
            MAX-ACCESS not-accessible
            STATUS current
            DESCRIPTION
                "Configures an MD for ONT, including creating and deleting an MD.
                The index of this entry is hwOntCfmMdIndex.
                "
            INDEX {hwOntCfmMdIndex }
            ::= { hwOntCfmMdTable 1 }

        HwOntCfmMdEntry ::=
            SEQUENCE
                {
                hwOntCfmMdIndex
                    Integer32,
                hwOntCfmMdFormat
                    Dot1agCfmMaintDomainNameType,
                hwOntCfmMdName
                    Dot1agCfmMaintDomainName,
                hwOntCfmMdLevel
                    Dot1agCfmMDLevel,
                hwOntCfmMdMhfCreation
                    Dot1agCfmMhfCreation,
                hwOntCfmMdMhfIdPermission
                    Dot1agCfmIdPermission,
                hwOntCfmMdRowStatus
                    RowStatus
                }

        hwOntCfmMdIndex OBJECT-TYPE
            SYNTAX Integer32(-1|1..8)
            MAX-ACCESS not-accessible
            STATUS current
            DESCRIPTION
                "The index to the Maintenance Domain table.
                Referential integrity is required, i.e., the index needs to be
                persistent upon a reboot or restart of a device. The index
                can never be reused for other Maintenance Domain. This is to
                facilitate access control based on OID.
                -1: indicates that the MD index is assigned by the device.
                "
            ::= { hwOntCfmMdEntry 1 }

        hwOntCfmMdFormat OBJECT-TYPE
            SYNTAX Dot1agCfmMaintDomainNameType
            MAX-ACCESS read-create
            STATUS current
            DESCRIPTION
                "The type (and thereby format) of the Maintenance Domain Name."
            REFERENCE
                "802.1ag clause 21.6.5.1"
            ::= { hwOntCfmMdEntry 2 }

        hwOntCfmMdName OBJECT-TYPE
            SYNTAX Dot1agCfmMaintDomainName
            MAX-ACCESS read-create
            STATUS current
            DESCRIPTION
                "The Maintenance Domain name. The type/format of this object
                is determined by the value of the dot1agCfmMdNameType object.
                Each Maintenance Domain has unique name amongst all those
                used or available to a service provider or operator. It
                facilitates easy identification of administrative
                responsibility for each Maintenance Domain.
                Clause 3.24 defines a Maintenance Domain name as the
                identifier, unique over the domain for which CFM is to
                protect against accidental concatenation of Service
                Instances, of a particular Maintenance Domain.
                "
            REFERENCE
                "802.1ag clauses 3.24, 12.14.5, and 21.6.5.3"
            ::= { hwOntCfmMdEntry 3 }

        hwOntCfmMdLevel OBJECT-TYPE
            SYNTAX Dot1agCfmMDLevel
            MAX-ACCESS read-create
            STATUS current
            DESCRIPTION
                "The Maintenance Domain Level."
            REFERENCE
                "802.1ag clause 12.14.5.1.3:b"
            ::= { hwOntCfmMdEntry 4 }

        hwOntCfmMdMhfCreation OBJECT-TYPE
            SYNTAX Dot1agCfmMhfCreation
            MAX-ACCESS read-write
            STATUS current
            DESCRIPTION
                "Enumerated value indicating whether the management entity can
                create MHFs (MIP Half Function) for this Maintenance Domain.
                Since, in this variable, there is no encompassing Maintenance
                Domain, the value defMHFdefer is not allowed.
                "
            REFERENCE
                "802.1ag clause 12.14.5.1.3:c"
            DEFVAL { defMHFnone }
            ::= { hwOntCfmMdEntry 5 }

        hwOntCfmMdMhfIdPermission OBJECT-TYPE
            SYNTAX Dot1agCfmIdPermission
            MAX-ACCESS read-write
            STATUS current
            DESCRIPTION
                "Enumerated value indicating what, if anything, is to be
                included in the Sender ID TLV (21.5.3) transmitted by MPs
                configured in this Maintenance Domain. Since, in this
                variable, there is no encompassing Maintenance Domain, the
                value sendIdDefer is not allowed.
                "
            REFERENCE
                "802.1ag clause 12.14.5.1.3:d"
            DEFVAL { sendIdNone }
            ::= { hwOntCfmMdEntry 6 }

        hwOntCfmMdRowStatus OBJECT-TYPE
            SYNTAX RowStatus
            MAX-ACCESS read-create
            STATUS current
            DESCRIPTION
                "The status of the row.
                The writable columns in a row can not be changed if the row
                is active. All columns must have a valid value before a row
                can be activated.
                "
            ::= { hwOntCfmMdEntry 7 }

-- ******************************************************************
-- The Maintenance Association (MA) Network Table for ONT
-- ******************************************************************
        hwOntCfmMaTable OBJECT-TYPE
            SYNTAX SEQUENCE OF HwOntCfmMaEntry
            MAX-ACCESS not-accessible
            STATUS current
            DESCRIPTION
                "Configures an MA for ONT, including creating an MA, modifying an MA, deleting an MA, and
                configuring the interval for an MA to send CCMs.
                The indexes of this table are hwOntCfmMdIndex and hwOntCfmMaIndex.
                "
            REFERENCE
                "802.1ag clause 18.2"
            ::= { hwEthernetOAMMibObject 21 }

        hwOntCfmMaEntry OBJECT-TYPE
            SYNTAX HwOntCfmMaEntry
            MAX-ACCESS not-accessible
            STATUS current
            DESCRIPTION
                "Configures an MA for ONT, including creating an MA, modifying an MA, deleting an MA, and
                configuring the interval for an MA to send CCMs.
                The indexes of this entry are hwOntCfmMdIndex and hwOntCfmMaIndex."
            INDEX {hwOntCfmMdIndex, hwOntCfmMaIndex }
            ::= { hwOntCfmMaTable 1 }

        HwOntCfmMaEntry ::=
            SEQUENCE
                {
                hwOntCfmMaIndex
                    Integer32,
                hwOntCfmMaNetFormat
                    INTEGER,
                hwOntCfmMaNetName
                    Dot1agCfmMaintAssocName,
                hwOntCfmMaNetCcmInterval
                    Dot1agCfmCcmInterval,
                hwOntCfmMaCompMhfCreation
                    Dot1agCfmMhfCreation,
                hwOntCfmMaCompIdPermission
                    Dot1agCfmIdPermission,
                hwOntCfmMaNetRowStatus
                    RowStatus
                }

        hwOntCfmMaIndex OBJECT-TYPE
            SYNTAX Integer32(-1|1..4096)
            MAX-ACCESS not-accessible
            STATUS current
            DESCRIPTION
                "MA index, indicating an operated MA.
                -1: indicates that the MA index is assigned by the device.
                "
            ::= { hwOntCfmMaEntry 1 }

        hwOntCfmMaNetFormat OBJECT-TYPE
            SYNTAX INTEGER
                {
                primaryVid(1),
                charString(2),
                unsignedInt16(3),
                rfc2865VpnId(4),
                iccBased(32)
                }
            MAX-ACCESS read-create
            STATUS current
            DESCRIPTION
                "Indicates the name type of an MA name.
                 Options:
                 1. primaryVid(1)    -indicates the name type of the MA name is primary VLAN ID
                 2. charString(2)    -indicates the name type of the MA name is char string
                 3. unsignedInt16(3) -indicates the name type of the MA name is unsigned int16
                 4. rfc2865VpnId(4)  -indicates the name type of the MA name is rfc2865VpnId
                 5. iccBased(32)    -indicates the name type of the MA name is ICC-based
                "
            REFERENCE
                "802.1ag clauses 21.6.5.4"
            ::= { hwOntCfmMaEntry 2 }

        hwOntCfmMaNetName OBJECT-TYPE
            SYNTAX Dot1agCfmMaintAssocName
            MAX-ACCESS read-create
            STATUS current
            DESCRIPTION
                "Indicates the name of an MA.
                 Range: 1-45 characters.
                "
            REFERENCE
                "802.1ag clauses 21.6.5.6, and Table 21-20"
            ::= { hwOntCfmMaEntry 3 }

        hwOntCfmMaNetCcmInterval OBJECT-TYPE
            SYNTAX Dot1agCfmCcmInterval
            MAX-ACCESS read-create
            STATUS current
            DESCRIPTION
                "Indicates the Tx interval of CCMs.
                 Options:
                 1. intervalInvalid(0) -indicates the Tx interval of CCMs is invalid
                 2. interval300Hz(1)   -indicates the Tx interval of CCMs is 300Hz
                 3. interval10ms(2)    -indicates the Tx interval of CCMs is 10ms
                 4. interval100ms(3)   -indicates the Tx interval of CCMs is 100ms
                 5. interval1s(4)      -indicates the Tx interval of CCMs is 1s
                 6. interval10s(5)     -indicates the Tx interval of CCMs is 10s
                 7. interval1min(6)    -indicates the Tx interval of CCMs is 1 minute
                 8. interval10min(7)   -indicates the Tx interval of CCMs is 10 minutes
                 Default: interval1min(6)
                "
            REFERENCE
                "802.1ag clause 12.14.6.1.3:e"
            DEFVAL { interval1min }
            ::= { hwOntCfmMaEntry 4 }

        hwOntCfmMaCompMhfCreation OBJECT-TYPE
            SYNTAX Dot1agCfmMhfCreation
            MAX-ACCESS read-write
            STATUS current
            DESCRIPTION
                "Indicates if the Management entity can create MHFs (MIP Half
                Function) for this MA.
                "
            REFERENCE
                "802.1ag clause 12.14.6.1.3:c"
            DEFVAL { defMHFnone }
            ::= { hwOntCfmMaEntry 5 }

        hwOntCfmMaCompIdPermission OBJECT-TYPE
            SYNTAX Dot1agCfmIdPermission
            MAX-ACCESS read-write
            STATUS current
            DESCRIPTION
                "Enumerated value indicating what, if anything, is to be
                included in the Sender ID TLV (21.5.3) transmitted by MPs
                configured in this MA.
                "
            REFERENCE
                "802.1ag clause 12.14.6.1.3:d"
            DEFVAL { sendIdNone }
            ::= { hwOntCfmMaEntry 6 }

        hwOntCfmMaNetRowStatus OBJECT-TYPE
            SYNTAX RowStatus
            MAX-ACCESS read-create
            STATUS current
            DESCRIPTION
                "The status of the row.
                The writable columns in a row can not be changed if the row
                is active. All columns must have a valid value before a row
                can be activated.
                "
            ::= { hwOntCfmMaEntry 7 }

-- ******************************************************************
-- The Maintenance Association End Point Table for ONT
-- ******************************************************************
        hwOntCfmMepTable OBJECT-TYPE
            SYNTAX SEQUENCE OF HwOntCfmMepEntry
            MAX-ACCESS not-accessible
            STATUS current
            DESCRIPTION
                "Sets a MEP for ONT, including creating a MEP, deleting a MEP, and disabling the joint switchover switch of a MEP.
                 The indexes of this table are hwOntCfmMdIndex, hwOntCfmMaIndex and hwOntCfmMepId.
                "
            REFERENCE
                "802.1ag clauses 12.14.7 and 19.2"
            ::= { hwEthernetOAMMibObject 22 }

        hwOntCfmMepEntry OBJECT-TYPE
            SYNTAX HwOntCfmMepEntry
            MAX-ACCESS not-accessible
            STATUS current
            DESCRIPTION
                "Sets a MEP for ONT, including creating a MEP, deleting a MEP, and disabling the joint switchover switch of a MEP.
                 The indexes of this entry are hwOntCfmMdIndex, hwOntCfmMaIndex and hwOntCfmMepId.
                "
            INDEX
                {
                hwOntCfmMdIndex,
                hwOntCfmMaIndex,
                hwOntCfmMepId
                }
            ::= { hwOntCfmMepTable 1 }

        HwOntCfmMepEntry ::=
            SEQUENCE
                {
                hwOntCfmMepId
                    Integer32,
                hwOntCfmMepIfIndex
                    Integer32,
                hwOntCfmMepOntid
                    Integer32,
                hwOntCfmMepIsIphost
                    TruthValue,
                hwOntCfmMepEthPortId
                    Integer32,
                hwOntCfmMepDirection
                    Dot1agCfmMpDirection,
                hwOntCfmMepVlanid
                    Unsigned32,
                hwOntCfmMepActive
                    TruthValue,
                hwOntCfmMepCciEnabled
                    TruthValue,
                hwOntCfmMepCcmLtmPriority
                    Unsigned32,
                hwOntCfmMepCcmRemoteMepid
                    Integer32,
                hwOntCfmMepMacAddress
                    MacAddress,
                hwOntCfmMepRowStatus
                    RowStatus
                }

        hwOntCfmMepId OBJECT-TYPE
            SYNTAX Integer32
            MAX-ACCESS not-accessible
            STATUS current
            DESCRIPTION
                "Indicates the MEP index.
                 Range: 1-8191
                "
            REFERENCE
                "802.1ag clauses 3.19, 19.2 and 12.14.7"
            ::= { hwOntCfmMepEntry 1 }

        hwOntCfmMepIfIndex OBJECT-TYPE
            SYNTAX Integer32
            MAX-ACCESS read-create
            STATUS current
            DESCRIPTION
                "Indicates the flag of port bound to the MEP, and the value is obtained through
                 the ifIndex algorithm according to the shelf ID, slot ID, and port ID.
                 -1 indicates an invalid value for ifIndex.
                "
            REFERENCE
                "802.1ag clause 12.14.7.1.3:b"
            ::= { hwOntCfmMepEntry 2 }

        hwOntCfmMepOntid OBJECT-TYPE
            SYNTAX Integer32
            MAX-ACCESS read-create
            STATUS current
            DESCRIPTION
                "Indicates the ONT ID of the XPON port.
                "
            ::= { hwOntCfmMepEntry 3 }

        hwOntCfmMepIsIphost OBJECT-TYPE
            SYNTAX TruthValue
            MAX-ACCESS read-create
            STATUS current
            DESCRIPTION
                "Indicates the port type of the MEP.
                 Options:
                 1. true(1)  -indicates the IPHOST port
                 2. false(2) -indicates the ETH port
                "
            REFERENCE
                "802.1ag clauses 12.14.7.1.3:e and 20.9.1"
             ::= { hwOntCfmMepEntry 4 }

        hwOntCfmMepEthPortId OBJECT-TYPE
            SYNTAX Integer32
            MAX-ACCESS read-create
            STATUS current
            DESCRIPTION
                "Indicates the ETH port ID of the MEP.                
                 -1 indicates an invalid value for ETH port ID.
                "
            ::= { hwOntCfmMepEntry 5 }

        hwOntCfmMepDirection OBJECT-TYPE
            SYNTAX Dot1agCfmMpDirection
            MAX-ACCESS read-create
            STATUS current
            DESCRIPTION
                "Indicates the MEP direction.
                 Options:
                 1. down(1) -indicates the MEP direction is down
                 2. up(2)   -indicates the MEP direction is up
                "
            REFERENCE
                "802.1ag clauses 12.14.7.1.3:c and 19.2.
                 The value can be one of the following:
                 down(1) -Down direction.
                 up(2)   -Up direction.
                "
            ::= { hwOntCfmMepEntry 6 }

        hwOntCfmMepVlanid OBJECT-TYPE
            SYNTAX Unsigned32(1..4094|65534|65535)
            MAX-ACCESS read-create
            STATUS current
            DESCRIPTION
                "Indicates the VLAN ID of the MEP.
                 65534 indicates that the MEP is not associated with any VLAN.
                 65535 indicates that the MEP is unaware of VLAN.
                "
            REFERENCE
                "802.1ag clauses 12.14.7.1.3:d"
            ::= { hwOntCfmMepEntry 7 }

        hwOntCfmMepActive OBJECT-TYPE
            SYNTAX TruthValue
            MAX-ACCESS read-create
            STATUS current
            DESCRIPTION
                "Indicates the enable status of the MEP.
                 Options:
                 1. true(1)  -indicates the MEP is enabled
                 2. false(2) -indicates the MEP is disabled
                 Default: true(1)
                "
            REFERENCE
                "802.1ag clauses 12.14.7.1.3:e and 20.9.1"
            DEFVAL { true }
             ::= { hwOntCfmMepEntry 8 }

        hwOntCfmMepCciEnabled OBJECT-TYPE
            SYNTAX TruthValue
            MAX-ACCESS read-create
            STATUS current
            DESCRIPTION
                "Indicates the CC message sending function status of the MEP.
                 Options:
                 1. true(1)  -indicates the CC message sending function of the MEP is enabled
                 2. false(2) -indicates the CC message sending function of the MEP is disabled
                 Default: true(1)
                "
            REFERENCE
                "802.1ag clauses 12.14.7.1.3:g and 20.10.1"
            DEFVAL { true }
            ::= { hwOntCfmMepEntry 9 }

        hwOntCfmMepCcmLtmPriority OBJECT-TYPE
            SYNTAX Unsigned32(0..7)
            MAX-ACCESS read-create
            STATUS current
            DESCRIPTION
                "Indicates the level of CCMs/LTMs sent by the MEP.
                 Range: 0-7
                 Default: 7
                "
            REFERENCE
                "802.1ag clause 12.14.7.1.3:h"
            DEFVAL { 7 }
            ::= { hwOntCfmMepEntry 10 }

        hwOntCfmMepCcmRemoteMepid OBJECT-TYPE
            SYNTAX Integer32
            MAX-ACCESS read-create
            STATUS current
            DESCRIPTION
                "Indicates the Remote MEP index of the MEP.
                 Range: 1-8191
                "
            ::= { hwOntCfmMepEntry 11 }

        hwOntCfmMepMacAddress OBJECT-TYPE
            SYNTAX MacAddress
            MAX-ACCESS read-only
            STATUS current
            DESCRIPTION
                "Indicates the MAC address of the MEP.
                "
            REFERENCE
                "802.1ag clause J.6 MP addressing"
            ::= { hwOntCfmMepEntry 12 }

        hwOntCfmMepRowStatus OBJECT-TYPE
            SYNTAX RowStatus
            MAX-ACCESS read-create
            STATUS current
            DESCRIPTION
                "Indicates the row status of the MEP.
                 Options:
                 1. active(1)      -indicates the query operation
                 2. createAndGo(4) -indicates the creating operation
                 3. destroy(6)     -indicates the deleting operation
                 In the query, active(1) is returned. To create an MEP, set the row status to
                 createAndGo(4). To delete an MEP, set the row status to destroy(6).
                "
            ::= { hwOntCfmMepEntry 13 }

-- ******************************************************************
-- ONT global para table
-- ******************************************************************
        hwOntCfmGlobalParaTable OBJECT-TYPE
            SYNTAX SEQUENCE OF HwOntCfmGlobalParaEntry
            MAX-ACCESS not-accessible
            STATUS current
            DESCRIPTION
                "Set the global CFM or PM para of ONT.
                The indexes of this table are hwOntCfmIfIndex, hwOntCfmOntid.
                "
            ::= { hwEthernetOAMMibObject 23 }

        hwOntCfmGlobalParaEntry OBJECT-TYPE
            SYNTAX     HwOntCfmGlobalParaEntry
            MAX-ACCESS not-accessible
            STATUS current
            DESCRIPTION
                "Set the global CFM or PM para of ONT.
                 The indexes of this entry are hwOntCfmIfIndex, hwOntCfmOntid.
                "
            INDEX
                {
                hwOntCfmIfIndex,
                hwOntCfmOntid
                }
            ::= { hwOntCfmGlobalParaTable 1 }

        HwOntCfmGlobalParaEntry ::=
            SEQUENCE
                {
                hwOntCfmIfIndex
                    Integer32,
                hwOntCfmOntid
                    Integer32,
                hwOntCfmGlobalStatus
                    TruthValue
                }

        hwOntCfmIfIndex OBJECT-TYPE
            SYNTAX Integer32
            MAX-ACCESS not-accessible
            STATUS current
            DESCRIPTION
                "Indicates the flag of port bound to the MEP, and the value is obtained through
                 the ifIndex algorithm according to the shelf ID, slot ID, and port ID.
                 -1 indicates an invalid value for ifIndex.
                "
            REFERENCE
                "802.1ag clause 12.14.7.1.3:b"
            ::= { hwOntCfmGlobalParaEntry 1 }

        hwOntCfmOntid OBJECT-TYPE
            SYNTAX Integer32
            MAX-ACCESS not-accessible
            STATUS current
            DESCRIPTION
                "Indicates the ONT ID of the XPON port."
            ::= { hwOntCfmGlobalParaEntry 2 }

        hwOntCfmGlobalStatus OBJECT-TYPE
            SYNTAX TruthValue
            MAX-ACCESS read-create
            STATUS current
            DESCRIPTION
                "Indicates the CFM switch of the ONT.
                 Options:
                 1. true(1)  -indicates the CFM switch of the ONT is enabled
                 2. false(2) -indicates the CFM switch of the ONT is disabled
                 Default: true(1)
                "
            DEFVAL { true }
            ::= { hwOntCfmGlobalParaEntry 3 }

-- ******************************************************************
-- ONT PM intsance table
-- ******************************************************************
         hwOntY1731TestIdTable OBJECT-TYPE
            SYNTAX SEQUENCE OF HwOntY1731TestIdEntry
            MAX-ACCESS not-accessible
            STATUS current
            DESCRIPTION
                "This table specifies the information for PM instance on ONT.
                 The index of this table is hwOntY1731TestId.
                "
            ::= { hwEthernetOAMMibObject 24 }

        hwOntY1731TestIdEntry OBJECT-TYPE
            SYNTAX HwOntY1731TestIdEntry
            MAX-ACCESS not-accessible
            STATUS current
            DESCRIPTION
                "This table specifies the information for PM instance on ONT.
                 The index of this entry is hwOntY1731TestId.
                "
            INDEX { hwOntY1731TestId }
            ::= { hwOntY1731TestIdTable 1 }

        HwOntY1731TestIdEntry ::=
            SEQUENCE {
                hwOntY1731TestId
                   Unsigned32,
                hwOntY1731LocalMdIndex
                   Integer32,
                hwOntY1731LocalMaIndex
                   Integer32,
                hwOntY1731LocalMepId
                   Integer32,
                hwOntY1731BackwardMacAddress
                   MacAddress,
                hwOntY1731IsUpdateBackwardMacAddress
                   TruthValue,
                hwOntY1731TX8021p
                   Integer32,
                hwOntY1731RCV8021p
                   Integer32,
                hwOntY1731TestIdRowStatus
                   RowStatus,
                hwOntY1731RemoteMepMacAddress
                   MacAddress,
                hwOntY1731TaskType
                   BITS,
                hwOntY1731TaskIfActive 
                   BITS,
                hwOntY1731TaskIsContinue
                   BITS
                }

        hwOntY1731TestId OBJECT-TYPE
            SYNTAX     Unsigned32 (1..4294967293)
            MAX-ACCESS not-accessible
            STATUS     current
            DESCRIPTION
                "Indicates the PM instance ID on ONT.
                 Range: 1-4294967293
                "
            ::= { hwOntY1731TestIdEntry 1 }

        hwOntY1731LocalMdIndex OBJECT-TYPE
            SYNTAX     Integer32 (1..8)
            MAX-ACCESS read-create
            STATUS     current
            DESCRIPTION
                "Indicates the local MD index.
                 Range: 1-8
                "
            ::= { hwOntY1731TestIdEntry 2 }

        hwOntY1731LocalMaIndex OBJECT-TYPE
            SYNTAX     Integer32 (1..4096)
            MAX-ACCESS read-create
            STATUS     current
            DESCRIPTION
                "Indicates the local MA index.
                 Range: 1-4096
                "
            ::= { hwOntY1731TestIdEntry 3 }

        hwOntY1731LocalMepId OBJECT-TYPE
            SYNTAX     Integer32 (1..8191)
            MAX-ACCESS read-create
            STATUS     current
            DESCRIPTION
                "Indicates the local MEP ID.
                 Range: 1-8191
                "
            ::= { hwOntY1731TestIdEntry 4 }

        hwOntY1731BackwardMacAddress OBJECT-TYPE
            SYNTAX     MacAddress
            MAX-ACCESS read-create
            STATUS     current
            DESCRIPTION
                "Indicates the backward MAC address of the MEP.
                "
            ::= { hwOntY1731TestIdEntry 5 }

        hwOntY1731IsUpdateBackwardMacAddress OBJECT-TYPE
            SYNTAX     TruthValue
            MAX-ACCESS read-create
            STATUS     current
            DESCRIPTION
                "Indicates the onward MAC learning mode.
                 Options:
                 1. true(1)  -indicates the onward MAC learning mode is update
                 2. false(2) -indicates the onward MAC learning mode is not update
                "
            ::= { hwOntY1731TestIdEntry 6 }

        hwOntY1731TX8021p OBJECT-TYPE
            SYNTAX     Integer32 (-1..7)
            MAX-ACCESS read-create
            STATUS     current
            DESCRIPTION
                "Indicates the send 802.1p value.
                 Range: -1-7
                 -1: indicates the send priority of the packets is not considered.
                "
            ::= { hwOntY1731TestIdEntry 7 }

        hwOntY1731RCV8021p OBJECT-TYPE
            SYNTAX     Integer32 (-1..7)
            MAX-ACCESS read-create
            STATUS     current
            DESCRIPTION
                "Indicates the receive 802.1p value.
                 Range: -1-7
                 -1: indicates the receive priority of the packets is not considered.
                "
            ::= { hwOntY1731TestIdEntry 8 }

        hwOntY1731TestIdRowStatus OBJECT-TYPE
            SYNTAX     RowStatus
            MAX-ACCESS read-create
            STATUS     current
            DESCRIPTION
                "Indicates the row status of the PM instance.
                 Options:
                 1. active(1)      -indicates the query operation
                 2. createAndGo(4) -indicates the creating operation
                 3. destroy(6)     -indicates the deleting operation
                 In the query, active(1) is returned. To create an PM instance, set the row status to
                 createAndGo(4). To delete an PM instance, set the row status to destroy(6).
                "
            ::= { hwOntY1731TestIdEntry 9 }

        hwOntY1731RemoteMepMacAddress OBJECT-TYPE
            SYNTAX     MacAddress
            MAX-ACCESS read-create
            STATUS     current
            DESCRIPTION
                "Indicates the MAC address of the remote MEP.
                "
            ::= { hwOntY1731TestIdEntry 10 }
            
        hwOntY1731TaskType OBJECT-TYPE
            SYNTAX BITS
                {
                bDefsingleLM(0),
                bDefdualLM(1),
                bDefonewayDM(2),
                bDeftwowayDM(3),
                bDeftest(4),
                bDefsingleSLM(5),
                bDefreserved6(6),
                bDefreserved7(7),
                bDefreserved8(8),
                bDefreserved9(9),
                bDefreserved10(10),
                bDefreserved11(11),
                bDefreserved12(12),
                bDefreserved13(13),
                bDefreserved14(14),
                bDefreserved15(15),
                bDefreserved16(16),
                bDefreserved17(17),
                bDefreserved18(18),
                bDefreserved19(19),
                bDefreserved20(20),
                bDefreserved21(21),
                bDefreserved22(22),
                bDefreserved23(23),
                bDefreserved24(24),
                bDefreserved25(25),
                bDefreserved26(26),
                bDefreserved27(27),
                bDefreserved28(28),
                bDefreserved29(29),
                bDefreserved30(30),
                bDefreserved31(31)
                }
            MAX-ACCESS read-only
            STATUS     current
            DESCRIPTION
                "Indicates the task type of the PM instance.
                 Options:
                 1. bDefsingleLM(0)  -indicates the single-ended loss measurement
                 2. bDefdualLM(1)    -indicates the dual-ended loss measurement
                 3. bDefonewayDM(2)  -indicates the one-way time delay measurement
                 4. bDeftwowayDM(3)  -indicates the two-way time delay measurement
                 5. bDeftest(4)      -indicates the test loss measurement
                 6. bDefsingleSLM(5) -indicates the single-ended synthetic loss measurement
                 Other bits are reserved. For each bit, 1 indicates that the PM task is valid, 
                 and 0 indicates that the PM task is invalid. 
                 Default: 0.    
                "
            ::= { hwOntY1731TestIdEntry 11 }
           
        hwOntY1731TaskIfActive OBJECT-TYPE
            SYNTAX BITS
                {
                bDefsingleLMIfActive(0),
                bDefdualLMIfActive(1),
                bDefonewayDMIfActive(2),
                bDeftwowayDMIfActive(3),
                bDeftestIfActive(4),
                bDefsingelSLMIfActive(5),
                bDefreserved6(6),
                bDefreserved7(7),
                bDefreserved8(8),
                bDefreserved9(9),
                bDefreserved10(10),
                bDefreserved11(11),
                bDefreserved12(12),
                bDefreserved13(13),
                bDefreserved14(14),
                bDefreserved15(15),
                bDefreserved16(16),
                bDefreserved17(17),
                bDefreserved18(18),
                bDefreserved19(19),
                bDefreserved20(20),
                bDefreserved21(21),
                bDefreserved22(22),
                bDefreserved23(23),
                bDefreserved24(24),
                bDefreserved25(25),
                bDefreserved26(26),
                bDefreserved27(27),
                bDefreserved28(28),
                bDefreserved29(29),
                bDefreserved30(30),
                bDefreserved31(31)
                }
            MAX-ACCESS read-only
            STATUS     current
            DESCRIPTION
                "Indicates the role of the PM task.
                 Options:
                 1. bDefsingleLMIfActive(0)  -indicates the role of the single-ended loss measurement
                 2. bDefdualLMIfActive(1)    -indicates the role of the dual-ended loss measurement
                 3. bDefonewayDMIfActive(2)  -indicates the role of the one-way time delay measurement
                 4. bDeftwowayDMIfActive(3)  -indicates the role of the two-way time delay measurement
                 5. bDeftestIfActive(4)      -indicates the role of the test loss measurement
                 6. bDefsingelSLMIfActive(5) -indicates the role of the single-ended synthetic loss measurement
                 Other bits are reserved. For each bit, when the corresponding bit of hwOntY1731TaskType is 1, 
                 1 indicates that the role of the PM task is sender, and 0 indicates that the role of the PM task is receiver.
                 Default: 0.  
                "
            ::= { hwOntY1731TestIdEntry 12 }
            
        hwOntY1731TaskIsContinue OBJECT-TYPE
            SYNTAX BITS
                {
                bDefsingleLMIsContinue(0),
                bDefdualLMIsContinue(1),
                bDefonewayDMIsContinue(2),
                bDeftwowayDMIsContinue(3),
                bDeftestIsContinue(4),
                bDefsingelSLMIsContinue(5),
                bDefreserved6(6),
                bDefreserved7(7),
                bDefreserved8(8),
                bDefreserved9(9),
                bDefreserved10(10),
                bDefreserved11(11),
                bDefreserved12(12),
                bDefreserved13(13),
                bDefreserved14(14),
                bDefreserved15(15),
                bDefreserved16(16),
                bDefreserved17(17),
                bDefreserved18(18),
                bDefreserved19(19),
                bDefreserved20(20),
                bDefreserved21(21),
                bDefreserved22(22),
                bDefreserved23(23),
                bDefreserved24(24),
                bDefreserved25(25),
                bDefreserved26(26),
                bDefreserved27(27),
                bDefreserved28(28),
                bDefreserved29(29),
                bDefreserved30(30),
                bDefreserved31(31)
                }
            MAX-ACCESS read-only
            STATUS     current
            DESCRIPTION
                "Indicates the operating mode of the PM task.
                 Options:
                 1. bDefsingleLM(0)  -indicates the operating mode of the single-ended loss measurement
                 2. bDefdualLM(1)    -indicates the operating mode of the dual-ended loss measurement
                 3. bDefonewayDM(2)  -indicates the operating mode of the one-way time delay measurement
                 4. bDeftwowayDM(3)  -indicates the operating mode of the two-way time delay measurement
                 5. bDeftest(4)      -indicates the operating mode of the test loss measurement
                 6. bDefsingleSLM(5) -indicates the operating mode of the single-ended synthetic loss measurement
                 Other bits are reserved. For each bit, when the corresponding bit of hwOntY1731TaskType is 1, 
                 1 indicates that the PM task runs according to demand, and 0 indicates that the PM task runs continuously. 
                 Default: 0.   
                "
            ::= { hwOntY1731TestIdEntry 13 }

-- ******************************************************************
-- ONT PM config table
-- ******************************************************************
         hwOntY1731ConfigTable  OBJECT-TYPE
            SYNTAX SEQUENCE OF HwOntY1731ConfigEntry
            MAX-ACCESS not-accessible
            STATUS current
            DESCRIPTION
                "This table specifies the information for PM Task.
                 The indexes of this table are hwOntY1731TestId and hwOntY1731CmdType.
                "
            ::= { hwEthernetOAMMibObject 25 }

        hwOntY1731ConfigEntry OBJECT-TYPE
            SYNTAX HwOntY1731ConfigEntry
            MAX-ACCESS not-accessible
            STATUS current
            DESCRIPTION
                "This table specifies the information for PM Task.
                 The indexes of this entry are hwOntY1731TestId and hwOntY1731CmdType.
                "
            INDEX
                {
                hwOntY1731TestId,
                hwOntY1731CmdType
                }
            ::= { hwOntY1731ConfigTable  1 }

        HwOntY1731ConfigEntry ::=
            SEQUENCE {
                hwOntY1731CmdType
                   INTEGER,
                hwOntY1731CmdEnable
                   TruthValue,
                hwOntY1731IfActive
                   TruthValue
                }

        hwOntY1731CmdType OBJECT-TYPE
            SYNTAX INTEGER
            {
                singleLM(1),
                dualLM(2),
                onewayDM(3),
                twowayDM(4),
                test(5)
            }
            MAX-ACCESS not-accessible
            STATUS current
            DESCRIPTION
                "Indicates the type of the PM task.
                 Options:
                 1. singleLM(1)   -indicates the type of the PM task is single-ended loss measurement
                 2. dualLM(2)     -indicates the type of the PM task is dual-ended loss measurement
                 3. onewayDM(3)   -indicates the type of the PM task is one-way time delay measurement
                 4. twowayDM(4)   -indicates the type of the PM task is two-way time delay measurement
                 5. test(5)       -indicates the type of the PM task is test loss measurement
                "
            ::= { hwOntY1731ConfigEntry 1 }

        hwOntY1731CmdEnable OBJECT-TYPE
            SYNTAX     TruthValue
            MAX-ACCESS read-write
            STATUS     current
            DESCRIPTION
                "Indicates the operating of the PM task.
                 Options:
                 1. true(1)  -indicates the start operation
                 2. false(2) -indicates the stop operation
                "
            ::= { hwOntY1731ConfigEntry 2 }

        hwOntY1731IfActive OBJECT-TYPE
            SYNTAX     TruthValue
            MAX-ACCESS read-write
            STATUS     current
            DESCRIPTION
                "Indicates the role of the PM task.
                 Options:
                 1. true(1)  -indicates the role of the PM task is sender
                 2. false(2) -indicates the role of the PM task is receiver
                 "
            ::= { hwOntY1731ConfigEntry 3 }

        hwCfmMaExtTable OBJECT-TYPE
            SYNTAX SEQUENCE OF HwCfmMaExtEntry
            MAX-ACCESS not-accessible
            STATUS current
            DESCRIPTION
                "Indicates an MA extension table.
                 The indexes of this table are dot1agCfmMdIndex and dot1agCfmMaIndex.
                "

            ::= { hwEthernetOAMMibObject 26 }

        hwCfmMaExtEntry OBJECT-TYPE
            SYNTAX HwCfmMaExtEntry
            MAX-ACCESS not-accessible
            STATUS current
            DESCRIPTION
                "Indicates an MA extension table.
                 The indexes of this entry are dot1agCfmMdIndex and dot1agCfmMaIndex.
                "
            INDEX
                {
                 dot1agCfmMdIndex,
                 dot1agCfmMaIndex
                }
            ::= { hwCfmMaExtTable 1 }

        HwCfmMaExtEntry ::=
            SEQUENCE
                {
                hwCfmMaClientLevel
                    Integer32,
                hwCfmMaAISInterval
                    INTEGER
                }

        hwCfmMaClientLevel OBJECT-TYPE
            SYNTAX Integer32(0..7 | 255)
            MAX-ACCESS read-write
            STATUS current
            DESCRIPTION
                "Indicates the client level at which an AIS packet is sent by an MEP.
                 Default: 255
                 255 is used to delete client level of MA.
                "
            REFERENCE
                "Y.1731-7.4.1"
            ::= { hwCfmMaExtEntry 1 }

        hwCfmMaAISInterval OBJECT-TYPE
            SYNTAX INTEGER
                {
                interval1s(1),
                interval1m(2)
                }
            MAX-ACCESS read-write
            STATUS current
            DESCRIPTION
                "Indicates the interval at which an AIS packet is sent by an MEP.
                 Options:
                 1. interval1s(1)    -The AIS packet is sent per second
                 2. interval1m(2)    -The AIS packet is sent per minute
                 Default:interval1s(1)
                "
            REFERENCE
                "Y.1731-7.4.1"
            ::= { hwCfmMaExtEntry 2 }

   END
