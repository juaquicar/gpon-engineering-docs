-- ============================================================================
-- Copyright (C) 2010 by  HUAWEI TECHNOLOGIES. All rights reserved.
-- Description: The MIB is used for defining Huawei's IMA management MIB objects. 
-- Reference:  
-- Version: V3.09
-- ============================================================================
    HUAWEI-IMA-EXT-MIB DEFINITIONS ::= BEGIN

        IMPORTS
            imaGroupTable, imaGroupIndex, imaGroupEntry
                FROM IMA-MIB
            OBJECT-TYPE, MODULE-IDENTITY, Gauge32,Unsigned32, Counter32, NOTIFICATION-TYPE
                FROM SNMPv2-SMI
            TruthValue
                FROM SNMPv2-TC
            hwFrameIndex, hwSlotIndex
                FROM HUAWEI-DEVICE-MIB
            hwIma
                FROM HUAWEI-MIB;

        hwImaMibObjects MODULE-IDENTITY
            LAST-UPDATED "201009280000Z"
            ORGANIZATION
                "Huawei Technologies Co.,Ltd."
            CONTACT-INFO                                      
                         "Huawei Industrial Base              
                          Bantian, Longgang                   
                          Shenzhen 518129                     
                          People's Republic of China          
                          Website: http://www.huawei.com      
                          Email: support@huawei.com           
                         "                                    
            DESCRIPTION
                "The MIB is used for defining Huawei's IMA management MIB objects."

    --  Revision history

		REVISION    "201009280000Z" 
		DESCRIPTION "V3.08, change in this revision:  
                             modify the description of the whole MIB file.
                            "

		REVISION    "201007300000Z" 
		DESCRIPTION "V3.07, change in this revision:  
                             Extend the leaf value of hwimaGroupCRC4Cfg to '-1'.
                            "
             	     
                REVISION    "201005240900Z" 
                DESCRIPTION "V3.06, change in this revision:  
                             Add leaves imaGroupTS and hwimaGroupTSCfg to support the timeslot configuration function of an IMA group.
             	            "	
             	            
                REVISION    "201004090900Z" 
                DESCRIPTION "V3.05, change in this revision:  
                             Modify chinese character.
             	            "	
             	
                REVISION    "201001120900Z" 
                DESCRIPTION "V3.04, change in this revision:  
              	             Add the definition of the trap node,include
              	             hwimaBandwidthChangeAlarmTrap,
                             hwimaGroupStatusChangeAlarmTrap,
                             and hwimaLinkStatusChangeAlarmTrap.
             	            "
             	
                REVISION    "200912280900Z" 
                DESCRIPTION "V3.03, change in this revision:  
              	             Add Huawei private leaf node.
                             The public object and private object are separated, and the private object is newly added.
              	            "
                REVISION    "200912180900Z" 
                DESCRIPTION "V3.02, change in this revision:  
              	             Add the define of imaGroupUNINNImode.
             	            "		
		
		REVISION    "200911230900Z" 
		DESCRIPTION "V3.01, change in this revision:  
              	             Change the description of leaf node imaGroupCRC4.
             	            "
             	          	
		REVISION    "200304280900Z" 
		DESCRIPTION "V3.00, change in this revision: 
              	             Remove the description in Chinese, and keep it in English
	                     all through the file.
             	            "   
 
		REVISION    "200303080900Z" 
 		DESCRIPTION "V2.00, change in this revision:
              	             Add the define of imaGroupEntry.
             	            "

 		REVISION    "200301280900Z" 
 		DESCRIPTION "V1.00, initial version."
 		::= { hwIma  1}									
			
																			
        imaGroupVersion OBJECT-TYPE
            SYNTAX   INTEGER
                {
                v10(1),
                v11(2)
                }
            MAX-ACCESS  read-create
            STATUS      current
            DESCRIPTION
                "IMA Version.
                 Options:
                 1. v10(1)  - version 1.0
                 2. v11(2)  - version 1.1
                "
        ::= { imaGroupEntry 65536 }

        imaGroupScramble OBJECT-TYPE
            SYNTAX      TruthValue
            MAX-ACCESS  read-write
            STATUS      current
            DESCRIPTION
                "If scramble of IMA group is set on or off.
                 Function of the scrambling mode of the IMA group.
                "
        ::= { imaGroupEntry 65537 }

        imaGroupCRC4    OBJECT-TYPE
            SYNTAX      TruthValue
            MAX-ACCESS  read-write
            STATUS      current
            DESCRIPTION
                "If CRC4 or ESF of IMA group is set on or off.
                 Function of the CRC4 mode of the IMA group.
                " 
        ::= { imaGroupEntry 65538 }

        imaGroupTxClock OBJECT-TYPE
            SYNTAX      INTEGER
                        {
                        none(1),
                        system(2),
                        line(3)
                    }
            MAX-ACCESS      read-write
            STATUS      current
            DESCRIPTION
                "Transmition clock of an IMA group.
                 Options:
                 1. none(1)   - none
                 2. system(2) - System clock mode
                 3. line(3)   - Line clock mode
                "
        ::= { imaGroupEntry 65539 }

        imaGroupTxCellCount OBJECT-TYPE
            SYNTAX      Counter32
            MAX-ACCESS  read-only
            STATUS      current
            DESCRIPTION
                "IMA group sent cells count."
        ::= { imaGroupEntry 65540 }

        imaGroupRxCellCount OBJECT-TYPE
            SYNTAX      Counter32
            MAX-ACCESS  read-only
            STATUS      current
            DESCRIPTION
                "IMA group received cells count."
        ::= { imaGroupEntry 65541 }

        imaGroupUNINNImode OBJECT-TYPE
            SYNTAX  INTEGER
                {
                    uni(1),                    
                    nni(2)                    
                }
            MAX-ACCESS  read-write
            STATUS      current
            DESCRIPTION
                "IMA group UNI/NNI mode. The default value is uni(1). 
                 Options:
                 1. uni(1)  - UNI mode
                 2. nni(2)  - NNI mode
                "
        ::= { imaGroupEntry 65542 }

        imaGroupTS   OBJECT-TYPE
            SYNTAX      Unsigned32
            MAX-ACCESS  read-write
            STATUS      current
            DESCRIPTION
                "The IMA group timeslot configuration."
        ::= { imaGroupEntry 65543 }
   		
     -- hwImaMibObjects
     -- hwImaMibObjects OBJECT IDENTIFIER ::= { hwIma  1}
     
     -- hwimaGroupCfgTable
        hwimaGroupCfgTable OBJECT-TYPE
            SYNTAX  SEQUENCE OF HwimaGroupCfgEntry
            MAX-ACCESS  not-accessible
            STATUS  current
            DESCRIPTION 
                "The IMA group configuration table.
                 The index of this table is imaGroupIndex.
                "
            ::= { hwImaMibObjects 1 }
        
        hwimaGroupCfgEntry OBJECT-TYPE
            SYNTAX  HwimaGroupCfgEntry
            MAX-ACCESS  not-accessible
            STATUS  current
            DESCRIPTION 
                "The IMA group configuration table.
                 The index of this entry is imaGroupIndex.
                "
            INDEX { imaGroupIndex }
            ::= { hwimaGroupCfgTable 1 }
        
        HwimaGroupCfgEntry ::=
            SEQUENCE {
                 hwimaGroupVersionCfg                      INTEGER,
                 hwimaGroupScrambleCfg                     TruthValue,
                 hwimaGroupCRC4Cfg                         INTEGER,
                 hwimaGroupTxClockCfg                      INTEGER,
                 hwimaGroupTxCellCountCfg                  Counter32,
                 hwimaGroupRxCellCountCfg                  Counter32,
                 hwimaGroupUNINNImodeCfg                   INTEGER,
                 hwimaGroupTSCfg                           Unsigned32
            }
																						
        hwimaGroupVersionCfg OBJECT-TYPE
            SYNTAX  INTEGER {
                                v10(1),
                                v11(2)
                            }
            MAX-ACCESS  read-create
            STATUS      current
            DESCRIPTION
                    "IMA Version.
                     Options:
                     1. v10(1)  - version 1.0
                     2. v11(2)  - version 1.1
                    "
            ::= { hwimaGroupCfgEntry 1 }
        
        hwimaGroupScrambleCfg OBJECT-TYPE
            SYNTAX  TruthValue
            MAX-ACCESS read-write
            STATUS     current
            DESCRIPTION
                    "If scramble of IMA group is set on or off."
            ::= { hwimaGroupCfgEntry 2 }
        
       hwimaGroupCRC4Cfg  OBJECT-TYPE
           SYNTAX  INTEGER {
                                true(1),
                                false(2),
                                invalid(-1)
                           }
           MAX-ACCESS read-write
           STATUS     current
           DESCRIPTION
       			"If CRC4 or ESF of IMA group is set on or off.
       			 Options:
                         1. true(1)  - CRC flag is true
                         2. false(2) - CRC flag is false
                         3. invalid(-1) - Invalid value
       			"
           ::= { hwimaGroupCfgEntry 3 }

        hwimaGroupTxClockCfg OBJECT-TYPE
            SYNTAX  INTEGER {
                                 none(1),
                                 system(2),
                                 line(3)
                            }
            MAX-ACCESS read-write
            STATUS     current
            DESCRIPTION
                    "Transmition clock of an IMA group.
                     Options:
                     1. none(1)   - none
                     2. system(2) - System clock mode
                     3. line(3)   - Line clock mode
                    "
            ::= { hwimaGroupCfgEntry 4 }

        hwimaGroupTxCellCountCfg OBJECT-TYPE
            SYNTAX    Counter32
            MAX-ACCESS read-only
            STATUS     current
            DESCRIPTION
                    "IMA group sent cells count."
            ::= { hwimaGroupCfgEntry 5}
        
        hwimaGroupRxCellCountCfg OBJECT-TYPE
            SYNTAX  Counter32
            MAX-ACCESS read-only
            STATUS     current
            DESCRIPTION
                    "IMA group received cells count."
            ::= { hwimaGroupCfgEntry 6 }
        
        hwimaGroupUNINNImodeCfg OBJECT-TYPE
            SYNTAX INTEGER {
                               uni(1),  
                               nni(2)  
                           }
            MAX-ACCESS read-write
            STATUS current
            DESCRIPTION
                   "IMA group UNI/NNI mode. The default value is uni(1). 
                    Options:
                    1. uni(1)  - UNI mode
                    2. nni(2)  - NNI mode
                   "
            ::= { hwimaGroupCfgEntry 7 }
         
        hwimaGroupTSCfg      OBJECT-TYPE
                SYNTAX      Unsigned32
                MAX-ACCESS  read-write
                STATUS      current
                DESCRIPTION
                    "The IMA group timeslot configuration."
            ::= { hwimaGroupCfgEntry 8 }
        -- Trap
        hwimaTraps       OBJECT IDENTIFIER ::= { hwImaMibObjects 2 }
        hwimaTrapsVbOids OBJECT IDENTIFIER ::= { hwImaMibObjects 3 }
        
        hwimaCommonTraps OBJECT IDENTIFIER ::= { hwimaTraps 1 }
        hwimaAlarmTraps  OBJECT IDENTIFIER ::= { hwimaTraps 2 }
        hwimaAlarmTrapsPrefix  OBJECT IDENTIFIER ::= { hwimaAlarmTraps 0 }
        
        
        hwImaAvailableTxbandwidth OBJECT-TYPE
            SYNTAX      Gauge32
            UNITS        "kbps"
            MAX-ACCESS  accessible-for-notify
            STATUS      current
            DESCRIPTION
                  "The current cell rate provided by this IMA group in the transmitted direction,
                   considering all the transmit links in the Active state.
                   Unit: kbps
                  "
        ::= { hwimaTrapsVbOids 1 }
        
        hwImaAvailableRxbandwidth OBJECT-TYPE
            SYNTAX      Gauge32
            UNITS        "kbps"
            MAX-ACCESS  accessible-for-notify
            STATUS      current
            DESCRIPTION
                  "The current cell rate provided by this IMA group in the received direction,
                   considering all the receive links in the Active state.
                   Unit: kbps
                  "
            ::= { hwimaTrapsVbOids 2 }
        
        hwImaLinkID OBJECT-TYPE
            SYNTAX Unsigned32
            MAX-ACCESS accessible-for-notify
            STATUS current
            DESCRIPTION
               "Indicate the link ID"
            ::= { hwimaTrapsVbOids 3 }
            
        hwImaGroupState OBJECT-TYPE
            SYNTAX OCTET STRING (SIZE (0..1024))
            MAX-ACCESS accessible-for-notify
            STATUS current
            DESCRIPTION
                    "The type of the IMA group alarm."
            ::= { hwimaTrapsVbOids 4 }
            
        hwImaGroupAlarmState OBJECT-TYPE
            SYNTAX OCTET STRING (SIZE (0..1024))
            MAX-ACCESS accessible-for-notify
            STATUS current
            DESCRIPTION
                    "The state of the IMA group alarm."
            ::= { hwimaTrapsVbOids 5 }
            
        hwimaBandwidthChangeAlarmTrap NOTIFICATION-TYPE
            OBJECTS {
                    hwFrameIndex,
                    hwSlotIndex,
                    imaGroupIndex,
                    hwImaAvailableTxbandwidth,
                    hwImaAvailableRxbandwidth
                    }
            STATUS current
            DESCRIPTION
                   "The bandwidth of the IMA group changes.
                    When the bandwidth of the IMA group changes, the IMA group bandwidth change alarm is reported.
                   "
            ::= { hwimaAlarmTraps 0 1 }
        
        hwimaGroupStatusChangeAlarmTrap NOTIFICATION-TYPE
            OBJECTS {
                    hwFrameIndex,
                    hwSlotIndex,
                    imaGroupIndex,
                    hwImaGroupState,
                    hwImaGroupAlarmState
                    }
            STATUS current
            DESCRIPTION
                   "The status of the IMA group changes.
                    When the status of the IMA group changes, the IMA group status change alarm is reported.
                   "
            ::= { hwimaAlarmTraps 0 2 }
        
        hwimaLinkStatusChangeAlarmTrap NOTIFICATION-TYPE
            OBJECTS {
                    hwFrameIndex,
                    hwSlotIndex,
                    hwImaLinkID,
                    hwImaGroupState,
                    hwImaGroupAlarmState
                    }
            STATUS current
            DESCRIPTION
                   "The status of the IMA link changes.
                    When the status of the IMA link changes, the IMA link status change alarm is reported.
                   "
            ::= { hwimaAlarmTraps 0 3 }
        
        
    END
