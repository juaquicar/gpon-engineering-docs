-- =================================================================
-- Copyright (C) 2014 by HUAWEI TECHNOLOGIES. All rights reserved.
-- Description: The MIB module defines Huawei's IPDSLAM PVCPROTOCAL MIB objects.
-- Reference:  RFC2320 RFC2225
-- Version:    V1.07
-- =================================================================
HUAWEI-IPDSLAM-PVCPROTOCAL-MIB DEFINITIONS ::= BEGIN

IMPORTS
        OBJECT-TYPE, MODULE-IDENTITY, NOTIFICATION-TYPE, IpAddress, Integer32
               FROM SNMPv2-SMI
        MacAddress
               FROM SNMPv2-TC
        hwIpdslamConnectIndex
               FROM HUAWEI-ETHERLIKE-EXT-MIB
        huaweiUtility
               FROM HUAWEI-MIB;      
		 
				
hwDslamPvcProtocol MODULE-IDENTITY
	LAST-UPDATED "201406071137Z"
	ORGANIZATION "Huawei Technologies Co.,Ltd."
	CONTACT-INFO                                       
	             "Huawei Industrial Base               
	              Bantian, Longgang                    
	              Shenzhen 518129                      
	              People's Republic of China           
	              Website: http://www.huawei.com       
	              Email: support@huawei.com            
	             "                                     
	DESCRIPTION 
		     "The MIB module defines Huawei's IPDSLAM PVCPROTOCAL MIB objects."
        
    --  Revision history 
        REVISION     "201406071137Z"
	DESCRIPTION  "V1.07, for the same HUAWEI-MIB defined in the agreement, modify hwIpDslamPvcProtocol to hwDslamPvcProtocol." 
 
        REVISION     "201011090000Z"
	DESCRIPTION  "V1.06, modified the description of Title.	
                 "    
	             
	REVISION     "201008240000Z"
	DESCRIPTION  "V1.05, modified the description of hwIpDslamPvcProtocolTable, hwIpDslamPvcProtocolEntry 
	              and hwIpDslamPvcProtocolType.
	             "
	              
	REVISION     "201003160000Z"
	DESCRIPTION  "V1.04, added the enumerated value that causes the hwIpDslamPvcProtocolSrcMode to be invalid.
	              Modify the description of hwIpDslamPvcProtocolTable.
	             " 
	
	REVISION     "201001090900Z"
	DESCRIPTION  "V1.03, modified the description and fix the compiling error."   

	REVISION     "200802010000Z"
	DESCRIPTION  "V1.02, modified the description of hwIpDslamPvcProtocolEntry."   

	REVISION     "200604270000Z"
	DESCRIPTION  "V1.00, initial version."

        ::= { huaweiUtility 45  }
    
		
		
	  hwIpDslamPvcProtocolTable OBJECT-TYPE
	      SYNTAX      SEQUENCE OF HwIpDslamPvcProtocolEntry
	      MAX-ACCESS  not-accessible
	      STATUS      current
	      DESCRIPTION
	          "
	          Sets and queries the encapsulation mode of a specified PVC.
	          It is created automatically when AtmVcCross is created.The index 
	          of this table is hwIpdslamConnectIndex.
	          "
	      ::= { hwDslamPvcProtocol 1 }

	  hwIpDslamPvcProtocolEntry OBJECT-TYPE
	      SYNTAX      HwIpDslamPvcProtocolEntry
	      MAX-ACCESS  not-accessible
	      STATUS      current
	      DESCRIPTION
	          "
	          Sets and queries the encapsulation mode of a specified PVC.
	          It is created automatically when AtmVcCross is created.The index 
	          of this entry is hwIpdslamConnectIndex.
	          "   
              
	      INDEX { hwIpdslamConnectIndex }
	      ::= { hwIpDslamPvcProtocolTable 1 }

	  HwIpDslamPvcProtocolEntry ::= SEQUENCE {
			      hwIpDslamPvcProtocolType           INTEGER,
			      hwIpDslamPvcProtocolSrcMac         MacAddress,
			      hwIpDslamPvcProtocolDstMac         MacAddress,			      			    
			      hwIpDslamPvcProtocolSrcIP          IpAddress,
			      hwIpDslamPvcProtocolDstIP          IpAddress,
			      hwIpDslamPvcProtocolSrcMode        INTEGER,			      
			      hwIpDslamPvcProtocolPPPoASessionId Integer32,
			      hwIpDslamPvcProtocolActualType     INTEGER
			      			}
	                                      
	hwIpDslamPvcProtocolType OBJECT-TYPE
	      SYNTAX  INTEGER {
	                       auto(1),
	                       llcBridge(2),
	                       llcPPP(3),
	                       llcIP(4),
	                       vcmuxBridge(5),
	                       vcmuxPPP(6),	                      
	                       vcmuxIP(7)
	                      }
	      MAX-ACCESS  read-create
	      STATUS      current
	      DESCRIPTION
	         "
	         Specifies the PVC encapsulation type. The default value is llcBridge. 
	         Options:
	         1. auto(1)        -Indicates that the PVC encapsulation type is auto
	         2. llcBridge(2)   -Indicates that the PVC encapsulation type is llcBridge
	         3. llcPPP(3)      -Indicates that the PVC encapsulation type is llcPPP
	         4. llcIP(4)       -Indicates that the PVC encapsulation type is llcIP
	         5. vcmuxBridge(5) -Indicates that the PVC encapsulation type is vcmuxBridge
	         6. vcmuxPPP(6)    -Indicates that the PVC encapsulation type is vcmuxPPP             
	         7. vcmuxIP(7)     -Indicates that the PVC encapsulation type is vcmuxIP
	         Default: llcBridge(2)
	         "
	      DEFVAL { llcBridge }
	      ::= { hwIpDslamPvcProtocolEntry 1 }
	      
	hwIpDslamPvcProtocolSrcMac OBJECT-TYPE
	      SYNTAX      MacAddress
	      MAX-ACCESS  read-only
	      STATUS      current
	      DESCRIPTION
	         "
	         Indicates SrcMac of the PVC forwarding entry.
	         "
	      ::= { hwIpDslamPvcProtocolEntry 2 }
	      
	hwIpDslamPvcProtocolDstMac OBJECT-TYPE
	      SYNTAX      MacAddress
	      MAX-ACCESS  read-only
	      STATUS      current
	      DESCRIPTION
	         "
	         Indicates DstMac of the PVC forwarding entry.
	         "
	      ::= { hwIpDslamPvcProtocolEntry 3 }      
	      
	      
	      
	hwIpDslamPvcProtocolSrcIP OBJECT-TYPE
	      SYNTAX      IpAddress
	      MAX-ACCESS  read-write
	      STATUS      current
	      DESCRIPTION
	         "
	         It is valid when the encapsulation mode is IPoA. It is used to set and query
	         the IP address of the static IPoA user configured on the RTU, or to query the 
	         IP address of the IPoA user configured on the RTU.
	         "
	      ::= { hwIpDslamPvcProtocolEntry 4 }	
		
	      
	hwIpDslamPvcProtocolDstIP OBJECT-TYPE
	      SYNTAX      IpAddress
	      MAX-ACCESS  read-write
	      STATUS      current
	      DESCRIPTION
	         "
	         It is valid when the encapsulation mode is IPoA or auto. It is used to set and query 
	         the destination gateway IP address of the IPoA user. 
	         In the case of the auto encapsulation mode, the destination IP address must be 
	         specified during configuration if the IPoA default gateway of the system is not configured. 
	         "
	      ::= { hwIpDslamPvcProtocolEntry 5 }
	      
	hwIpDslamPvcProtocolSrcMode OBJECT-TYPE
	      SYNTAX INTEGER
	          {
	          dynamicIP(1),
	          staticIP(2),
	          invalid(255)
	          }
	      MAX-ACCESS  read-only
	      STATUS      current
	      DESCRIPTION
	         "
	         It is valid when the encapsulation mode is IPoA.
	         Options:
	         1. dynamicIP(1) -Indicates that the user corresponding to the PVC is a dynamic user or an auto user
	         2. staticIP(2)  -Indicates that the user corresponding to the PVC is a static user
	         3. invalid(255) -When the encapsulation mode is not IPOA, the source IP mode is invalid
	         "	      
	      ::= { hwIpDslamPvcProtocolEntry 6 }		      
	
	
	hwIpDslamPvcProtocolPPPoASessionId OBJECT-TYPE
	      SYNTAX      Integer32(0..65535)
	      MAX-ACCESS  read-only
	      STATUS      current
	      DESCRIPTION
	         "
	         It is valid when the actual encapsulation mode is PPPoA.
	         It is used to query the session ID of the PPPoA to PPPoE converted user.
	         "    	  
	      ::= { hwIpDslamPvcProtocolEntry 7 }


	hwIpDslamPvcProtocolActualType OBJECT-TYPE
	      SYNTAX  INTEGER {
	                       bridge(1),
	                       llcPPP(2),
	                       llcIP(3),
	                       vcPPP(4),
	                       llcBridge(5),
	                       vcmuxBridge(6),
	                       vcmuxIP(7)
	                      }
	      MAX-ACCESS  read-only
	      STATUS      current
	      DESCRIPTION
	         "
	         Indicates the actual encapsulation type of PVC.
	         Options:
	         1. bridge(1)      -Indicates that the actual encapsulation type of PVC is bridge
	         2. llcPPP(2)      -Indicates that the actual encapsulation type of PVC is llcPPP
	         3. llcIP(3)       -Indicates that the actual encapsulation type of PVC is llcIP
	         4. vcPPP(4)       -Indicates that the actual encapsulation type of PVC is vcPPP
	         5. llcBridge(5)   -Indicates that the actual encapsulation type of PVC is llcBridge
	         6. vcmuxBridge(6) -Indicates that the actual encapsulation type of PVC is vcmuxBridge
	         7. vcmuxIP(7)     -Indicates that the actual encapsulation type of PVC is vcmuxIP
	         "
	      ::= { hwIpDslamPvcProtocolEntry 8 }	      
	      
END
