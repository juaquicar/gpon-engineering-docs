-- ============================================================================
-- Copyright (C) 2014 by  HUAWEI TECHNOLOGIES. All rights reserved.
-- Description: MIB interface of DNS and protocol configuration.
--              After the configuration, the device uses the DNS suffix
--              and the domain name server to provide the domain name
--              service.
-- Reference:
-- Version: V1.07
-- ============================================================================

    HUAWEI-DNS-AN-MIB DEFINITIONS ::= BEGIN

        IMPORTS
            huaweiUtility
                FROM HUAWEI-MIB
            OBJECT-TYPE, IpAddress, Integer32, MODULE-IDENTITY
                FROM SNMPv2-SMI ;

        hwDns MODULE-IDENTITY
            LAST-UPDATED "201406300000Z"
            ORGANIZATION "Huawei Technologies Co.,Ltd."
            CONTACT-INFO                                 
                         "Huawei Industrial Base         
                          Bantian, Longgang              
                          Shenzhen 518129                
                          People's Republic of China     
                          Website: http://www.huawei.com 
                          Email: support@huawei.com      
                         "                               
            DESCRIPTION
                "MIB interface of DNS and protocol configuration.
                 After the configuration, the device uses the DNS suffix
                 and the domain name server to provide the domain name
                 service.
                "

            --  Revision history
            REVISION     "201406300000Z"
            DESCRIPTION  "V1.07, Modify the following not normative nodes to satisfy for the new OMSYS tool.
                          hwDnsConfig"

            REVISION     "201007140000Z"
            DESCRIPTION  "V1.06, updated the description and format."

            REVISION     "201004250000Z"
            DESCRIPTION  "V1.05, updated the description and format."

            REVISION     "201004120000Z"
            DESCRIPTION  "V1.04, updated the description and format."

            REVISION     "201001130000Z"
            DESCRIPTION  "V1.03, modified the description and format."

            REVISION     "200707170000Z"
            DESCRIPTION  "V1.02, added nodes hwDnsResolve and hwDnsDomainTable."

            REVISION     "200601040000Z"
            DESCRIPTION  "V1.01, added leaf hwDnsDomainIndex."

            REVISION     "200405280000Z"
            DESCRIPTION  "V1.00, initial version."

            ::= { huaweiUtility 39 }

        hwDnsConfig OBJECT IDENTIFIER ::= { hwDns 1 }

        --1.dnsServerPrimary
        hwDnsServerPrimary OBJECT-TYPE
            SYNTAX              IpAddress
            MAX-ACCESS          read-write
            STATUS              current
            DESCRIPTION
                "If both the primary and secondary DNS servers are configured,
                 after the set operation is performed to delete the primary DNS server,
                 the secondary DNS server will function as the primary DNS server.
                 Range: 0.0.0.0 and all valid A, B, and C IP addresses
                 Default: 0.0.0.0
                "
            ::= { hwDnsConfig 1 }

        --2.dnsServerSecond
        hwDnsServerSecond OBJECT-TYPE
            SYNTAX              IpAddress
            MAX-ACCESS          read-write
            STATUS              current
            DESCRIPTION
                "If the IP address of the primary DNS server is not configured
                 and the IP address of the secondary DNS server is configured,
                 after the set operation is performed, the DNS server is selected as
                 the primary DNS server.
                 Range: 0.0.0.0 and all valid A, B, and C IP addresses
                 Default: 0.0.0.0
                "
            ::= { hwDnsConfig 2 }

        --3.dnsResolve
        hwDnsResolve OBJECT-TYPE
            SYNTAX INTEGER
            {
                dnsEnable(1),
                dnsDisable(2)
            }
            MAX-ACCESS          read-write
            STATUS              current
            DESCRIPTION
                "Controls whether to enable or disable the DNS dynamic resolution function.
                 Options:
                 1. dnsEnable(1)  -indicates the dynamic domain name resolution function is enabled
                 2. dnsDisable(2) -indicates the dynamic domain name resolution function is disabled
                 Default: dnsDisable(2)
                "
            ::= { hwDnsConfig 3 }

        --4.hwDnsDomainNameTable
        hwDnsDomainNameTable OBJECT-TYPE
            SYNTAX              SEQUENCE OF HwDnsDomainNameEntry
            MAX-ACCESS          not-accessible
            STATUS              current
            DESCRIPTION
                "Configures the DNS suffix. To configure the DNS suffix, the user needs to enter
                 only the host name. Then the device completes the full matching of host name+DNS
                 suffix and sends the result to the configured DNS server to resolve the IP
                 address corresponding to this domain.
                 The index of this table is hwDnsDomainIndex.
                "
            ::= { hwDnsConfig 4 }

        hwDnsDomainNameEntry OBJECT-TYPE
            SYNTAX              HwDnsDomainNameEntry
            MAX-ACCESS          not-accessible
            STATUS              current
            DESCRIPTION
                "Configures the DNS suffix. To configure the DNS suffix, the user needs to enter
                 only the host name. Then the device completes the full matching of host name+DNS
                 suffix and sends the result to the configured DNS server to resolve the IP
                 address corresponding to this domain.
                 The index of this entry is hwDnsDomainIndex.
                "
            INDEX { hwDnsDomainIndex }
            ::= { hwDnsDomainNameTable 1 }

        HwDnsDomainNameEntry ::=
            SEQUENCE
            {
                hwDnsDomainIndex        Integer32,
                hwDnsDomainName         OCTET STRING
            }

        hwDnsDomainIndex OBJECT-TYPE
            SYNTAX              Integer32(1..10)
            MAX-ACCESS          not-accessible
            STATUS              current
            DESCRIPTION
                "Indicates the table index. It is the index of the DNS suffix.
                "
            ::={ hwDnsDomainNameEntry 1 }

        hwDnsDomainName OBJECT-TYPE
            SYNTAX              OCTET STRING
            MAX-ACCESS          read-write
            STATUS              current
            DESCRIPTION
                "Indicates the DNS suffix character string. The default value
                 is null and the character string can contain only letters, numbers,
                 and '-', '.', '_'.
                "
            ::={ hwDnsDomainNameEntry 2 }

    END
