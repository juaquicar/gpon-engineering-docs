-- =================================================================
-- Copyright (C) 2016 by HUAWEI TECHNOLOGIES. All rights reserved                                                   
-- Description:  The MIB is used for defining Huawei's GPON and EPON management TRAP objects for both              
--               profile-mode and distributing-mode.                                                             
-- Reference:                                                                                                 
-- Version: V1.26
-- ================================================================                    


    HUAWEI-XPON-TRAP-MIB DEFINITIONS ::= BEGIN
        IMPORTS
            MODULE-IDENTITY, mib-2, OBJECT-TYPE, Counter32, Counter64,
            Unsigned32, Integer32, zeroDotZero, IpAddress, Gauge32, NOTIFICATION-TYPE
                FROM SNMPv2-SMI
            TruthValue, DateAndTime, RowStatus, MacAddress,TEXTUAL-CONVENTION
                FROM SNMPv2-TC
            ifIndex
                FROM IF-MIB
            MODULE-COMPLIANCE, OBJECT-GROUP
                FROM SNMPv2-CONF
            OwnerString, EntryStatus
                FROM RMON-MIB
            huaweiMgmt, huaweiUtility
                FROM HUAWEI-MIB
            hwFrameIndex, hwSlotIndex,hwPortIndex,hwPortPrimaryStatus, hwPortSecondaryStatus, hwConfigChangeIP
                FROM HUAWEI-DEVICE-MIB
            hwReservedValue
                FROM HUAWEI-LINE-COMMON-MIB
            hwPgGroupId
                FROM HUAWEI-PROTECTION-MIB
            hwEponDeviceAutoFindOntInfoCheckcode,               hwGponDeviceAutoFindOntInfoOntVer, 
            hwEponDeviceAutoFindOntInfoHardwareVersion,         hwGponDeviceAutoFindOntInfoPassword, 
            hwEponDeviceAutoFindOntInfoLoid,                    hwGponDeviceAutoFindOntInfoSn, 
            hwEponDeviceAutoFindOntInfoMacAddress,              hwGponDeviceOntAuthMethod, 
            hwEponDeviceAutoFindOntInfoOntModel,                hwGponDeviceOntCatvPortId, 
            hwEponDeviceAutoFindOntInfoPasswordValue,           hwGponDeviceOntCfgAlarmProfileName, 
            hwEponDeviceAutoFindOntInfoSoftwareVersion,         hwGponDeviceOntCfgSnmpProfileName, 
            hwEponDeviceAutoFindOntInfoVendorId,                hwGponDeviceOntCheckcode, 
            hwEponDeviceAutoFindOntNniType,                     hwGponDeviceOntControlDbaStatus, 
            hwEponDeviceOntAuthMode,                            hwGponDeviceOntControlDiscoveryStatus, 
            hwEponDeviceOntCfgSnmpProfileName,                  hwGponDeviceOntControlLastDownCause, 
            hwEponDeviceOntDespt,                               hwGponDeviceOntControlLastDownTime, 
            hwEponDeviceOntDiscoveryState,                      hwGponDeviceOntControlLastDyingGaspTime,
            hwEponDeviceOntEthernetDuplexMode,                  hwGponDeviceOntControlLastUpTime, 
            hwEponDeviceOntEthernetFlowcontrolSwitch,           hwGponDeviceOntDespt, 
            hwEponDeviceOntEthernetNegotiate,                   hwGponDeviceOntEquipmentId,
            hwEponDeviceOntEthernetPortCfgDownStreamCarTrafficTableId, hwGponDeviceOntEthernetPortId, 
            hwEponDeviceOntEthernetPortCfgUpStreamCarTrafficTableId,   hwGponDeviceOntIndex,
            hwEponDeviceOntEthernetPortId,                      hwGponDeviceOntLineProfName, 
            hwEponDeviceOntEthernetSpeed,                       hwGponDeviceOntLoid, 
            hwEponDeviceOntEthernetVlanDefault,                 hwGponDeviceOntManagementMode, 
            hwEponDeviceOntHardwareVersion,                     hwGponDeviceOntPassword, 
            hwEponDeviceOntIndex,                               hwGponDeviceOntReregisterAuthMode, 
            hwEponDeviceOntLastDownCause,                       hwGponDeviceOntServiceProfName, 
            hwEponDeviceOntLastDownTime,                        hwGponDeviceOntSn, 
            hwEponDeviceOntLastDyingGaspTime,                   hwGponDeviceOntTDMPortId, 
            hwEponDeviceOntLastUpTime,                          hwGponDeviceOntTimeOut, 
            hwEponDeviceOntLineProfName,                        hwXponDeviceObjects,
            hwEponDeviceOntLlidCarTrafficTableId,               hwXponDeviceOltDualparentDesc, 
            hwEponDeviceOntLlidDbaProfileName,                  hwXponDeviceOltDualparentForceSwitch, 
            hwEponDeviceOntLlidIndex,                           hwXponDeviceOltDualparentFreeze, 
            hwEponDeviceOntMacAddress,                          hwXponDeviceOltDualparentJoin, 
            hwEponDeviceOntManagementMode,                      hwXponDeviceOltDualparentWorkState, 
            hwEponDeviceOntObjectCheckcode,                     hwXponDeviceOntIndex,
            hwEponDeviceOntObjectLoid,                          hwXponDeviceOntSnmpProfileInfoNameIndex,
            hwEponDeviceOntPassword,                            hwXponDeviceOntSnmpProfileReadCommunityName,
            hwEponDeviceOntPortId,                              hwXponDeviceOntSnmpProfileSecurityName, 
            hwEponDeviceOntPortType,                            hwXponDeviceOntSnmpProfileTrapHostIP, 
            hwEponDeviceOntServiceProfName,                     hwXponDeviceOntSnmpProfileTrapHostSrcUDPPort,
            hwEponDeviceOntTimeout,                             hwXponDeviceOntSnmpProfileVersion, 
            hwEponOntPortVlanCfgCVlan,                          hwXponDeviceOntSnmpProfileWriteCommunityName,
            hwEponOntPortVlanCfgOntPhyIndex,                    hwXponDeviceDbaProfileBandwithCompensate,
            hwEponOntPortVlanCfgOntPhyType,                     hwXponOntLoadFileType, 
            hwEponOntPortVlanCfgSVlan,                          hwXponOntUniPhyIndex, 
            hwEponOntPortVlanCfgType,                           hwXponOntUniPhyType, 
            hwGponDeviceAutoFindOntInfoCheckcode,               hwGponDeviceAutoFindOntInfoOntEquipmentId,        
            hwGponDeviceAutoFindOntInfoOntVendorId,             hwGponDeviceAutoFindOntInfoOntMainSoftVer,
            hwGponDeviceAutoFindOntInfoLoid,                    hwEponDeviceOntNniType,        
            hwEponDeviceAutoFindOntInfoOntExtendedModel,        hwEponDeviceAutoFindOntInfoOuiVersion,
            hwEponDeviceOntPGMemberRole,                        hwEponDeviceOntSoftwareVersion,
            hwEponDeviceOntSoftwareWorkMode,                    hwEponDeviceOntVendorId,
            hwGponDeviceOntEthernetDuplexMode,                  hwGponDeviceOntEthernetFlowCtrlSwitch,
            hwGponDeviceOntEthernetNegotiate,                   hwXponDeviceDbaProfileAssuredRate,
            hwGponDeviceOntEthernetSpeed,                       hwGponDeviceOntMainSoftVer, 
            hwGponDeviceOntPGMemberRole,                        hwGponDeviceOntSoftwareWorkMode, 
            hwXponDeviceDbaProfileFixedRate,                    hwXponDeviceDbaProfileInfoNameIndex,
            hwXponDeviceDbaProfileMaxRate,                      hwXponDeviceDbaProfileType,            
            hwGponDeviceOntVendorId,                            hwXponDeviceDbaProfileFixDelay,
            hwXponDeviceDbaProfileAdditionalBW,                 hwXponDeviceDbaProfilePriority,
            hwXponDeviceDbaProfileWeight,                       hwGponDeviceAutoFindOntInfoCustomizedInfo,
	        hwGponDeviceOntCustomizedInfo,                      hwEponDeviceAutoFindOntInfoCustomizedInfo,
	        hwEponDeviceOntCustomizedInfo,                      hwGponDeviceAutoFindOntInfoOntNniType,
	        hwGponDeviceOntNniType
                FROM HUAWEI-XPON-MIB
            hwGponDeviceAllocId,                                hwGponDeviceOntProfileGeNum, 
            hwGponDeviceAutoFindOntCheckcode,                   hwGponDeviceOntProfileGemPortMap,
            hwGponDeviceAutoFindOntEquipmentId,                 hwGponDeviceOntProfileGemPortNum,
            hwGponDeviceAutoFindOntLoid,                        hwGponDeviceOntProfileIPSupport, 
            hwGponDeviceAutoFindOntMainSoftVer,                 hwGponDeviceOntProfileMACBridge, 
            hwGponDeviceAutoFindOntPassword,                    hwGponDeviceOntProfileMocaNum, 
            hwGponDeviceAutoFindOntSn,                          hwGponDeviceOntProfileNameIndex, 
            hwGponDeviceAutoFindOntVendorId,                    hwGponDeviceOntProfilePonAniNum, 
            hwGponDeviceAutoFindOntVer,                         hwGponDeviceOntProfilePotsNum, 
            hwGponDeviceObjects,                                hwGponDeviceOntProfileTcont0PQNum,
            hwGponDeviceOntIgmpForwardTranslationVlan,          hwGponDeviceOntProfileTcont1PQNum,
            hwGponDeviceOntMacAddressSwitch,                    hwGponDeviceOntProfileTcont2PQNum,
            hwGponDeviceOntMulticastCtrlMode,                   hwGponDeviceOntProfileTcont3PQNum,
            hwGponDeviceOntObjectAuthMethod,                    hwGponDeviceOntProfileTcont4PQNum,
            hwGponDeviceOntObjectCapabProfileName,              hwGponDeviceOntProfileTcont5PQNum,
            hwGponDeviceOntObjectCheckcode,                     hwGponDeviceOntProfileTcont6PQNum,
            hwGponDeviceOntObjectDbaStatus,                     hwGponDeviceOntProfileTcont7PQNum,
            hwGponDeviceOntObjectDespt,                         hwGponDeviceOntProfileTcontNum,            
            hwGponDeviceOntObjectDiscoveryStatus,               hwGponDeviceOntProfileUniConfig, 
            hwGponDeviceOntObjectEquipmentId,                   hwGponDeviceOntTdmLocalInnerLoopback,
            hwGponDeviceOntObjectIgmpMode,                      hwGponDeviceOntTdmLocalOuterLoopback,
            hwGponDeviceOntObjectIgmpSwitchVlan,                hwGponDeviceOntTdmPortType,
            hwGponDeviceOntObjectIndex,                         hwGponDeviceOntTransparent,
            hwGponDeviceOntObjectLastDownCause,                 hwGponDeviceOntUpIgmpMsgProcMode,
            hwGponDeviceOntObjectLastDownTime,                  hwGponDevicePortidCascade,
            hwGponDeviceOntObjectLastUpTime,                    hwGponDevicePortidDescription,
            hwGponDeviceOntObjectLoid,                          hwGponDevicePortidFlowIndex,
            hwGponDeviceOntObjectMainSoftVer,                   hwGponDevicePortidMapObjectIndex, 
            hwGponDeviceOntObjectManageMode,                    hwGponDevicePortidMapObjectPir, 
            hwGponDeviceOntObjectPGMemberRole,                  hwGponDevicePortidMapObjectPortID, 
            hwGponDeviceOntObjectPassword,                      hwGponDevicePortidMapObjectPortType, 
            hwGponDeviceOntObjectRefAlarmProfileName,           hwGponDevicePortidMapObjectVlanID, 
            hwGponDeviceOntObjectReregisterAuthMode,            hwGponDevicePortidMapTrafficTableId, 
            hwGponDeviceOntObjectRunStatus,                     hwGponDevicePortidMapTransparent, 
            hwGponDeviceOntObjectSn,                            hwGponDevicePortidObjectDnEncrypt,
            hwGponDeviceOntObjectSnmpProfileName,               hwGponDevicePortidObjectIndex,
            hwGponDeviceOntObjectSoftWorkMode,                  hwGponDevicePortidServiceType,
            hwGponDeviceOntObjectTimeOut,                       hwGponDeviceTcontRefIndex,
            hwGponDeviceOntObjectVendorId,                      hwGponOntCatvPortId,
            hwGponDeviceOntPortidTrafficTableId,                hwGponOntPortVlanCfgCPri, 
            hwGponDeviceOntPortidObjectIndex,                   hwGponOntPortVlanCfgCVlan, 
            hwGponDeviceOntPortidObjectOntId,                   hwGponOntPortVlanCfgEtherType,
            hwGponDeviceOntPortidObjectTcontId,                 hwGponOntPortVlanCfgOntPhyIndex, 
            hwGponDeviceOntPortidObjectUpPQIndex,               hwGponOntPortVlanCfgOntPhyType, 
            hwGponDeviceOntProfileCatvAniNum,                   hwGponOntPortVlanCfgSPri, 
            hwGponDeviceOntProfileCatvUniNum,                   hwGponOntPortVlanCfgSVlan, 
            hwGponDeviceOntProfileE1T1Num,                      hwGponOntPortVlanCfgType, 
            hwGponDeviceOntProfileE1T1TYPE,                     hwGponOntTDMPortId,
            hwGponDeviceOntProfileEthNum,                       hwGponOntifEthernetPort,
            hwGponDeviceOntProfileFCType,                       hwOntLoadFileType, 
            hwGponDeviceTcontName,                              hwGponDeviceOntProfileFeNum,
            hwGponOntEthPortDownStreamCarTrafficTableId,        hwGponOntEthPortLoopback,
            hwGponOntPortPriorityPolicy,                        hwGponOntPortQinqMode,
            hwGponOntEthPortUpStreamCarTrafficTableId,          hwGponOntPortId,
            hwGponOntPortType,                                  hwXponDeviceOntSnmpProfileNameIndex,
            hwXponDeviceOntSnmpSecurityName,                    hwXponDeviceOntSnmpTrapHostIP,
            hwXponDeviceOntSnmpReadCommunityName,               hwXponDeviceOntSnmpTrapHostSrcUDPPort,
            hwXponDeviceOntSnmpVersion,                         hwXponDeviceOntSnmpWriteCommunityName,
            hwGponDeviceOntProfileVdslPortNum,                  hwGponDeviceOntPortidObjectDownPQIndex,
            hwGponDeviceOntRingCheckSwitch,                     hwGponDeviceOntRingCheckAutoShutdownSwitch,
            hwGponDeviceOntRingCheckDetectingFrequency,         hwGponDeviceOntRingCheckResumeInterval,
            hwGponDeviceAutoFindOntCustomizedInfo,              hwGponDeviceOntConfigCustomizedInfo,
            hwGponDeviceOntObjectNniType
                FROM HUAWEI-GPON-MIB
            hwXponCommonMIB,                                    hwGponOntPerfHis15MinFecCorrectCodeWords,
            hwGponOntPerfHis15MinFecUncorrectCodeWords,         hwXponDeviceOntControlPrimaryStatus, 
            hwXponDeviceOntControlSecondaryStatus,              hwXponOntIndex,
            hwXponOntInfoSupportXmlVersion,                     hwXponOntIpIndex, 
            hwXponOntPppoeOuterSimuCVlanPri,                    hwXponOntPppoeSimuPortID, 
            hwXponOntPppoeSimuOuterCVlanID,                     hwXponOntTransmittingSerialNo,
            hwGponOntPerfHis15MinFecUncorrectCodeWords,         hwGponOntPerfHis15MinFecUncorrectCodeWords,
            hwXponOntSupportVoipCfgMethod,                      hwGponOntPerfHis15MinFecTotalCodeWords,
            hwXponDeviceOtdrTestResult,                         hwGponDeviceOntVoipFtpCfgResult,
            hwGponDeviceOntVoipCfgFileVersion
                FROM HUAWEI-XPON-COMMON-MIB;

        hwXponCommonTraps MODULE-IDENTITY
            LAST-UPDATED "201603280900Z"
            ORGANIZATION "Huawei Technologies Co.,Ltd."
            CONTACT-INFO                                        
                         "Huawei Industrial Base                
                          Bantian, Longgang                     
                          Shenzhen 518129                       
                          People's Republic of China            
                          Website: http://www.huawei.com        
                          Email: support@huawei.com             
                         "    
            DESCRIPTION  "The MIB is used for defining Huawei's GPON and EPON management TRAP objects for both profile-mode and distributing-mode."

    --  Revision history 
            REVISION     "201603280900Z"   
            DESCRIPTION  "V1.26, changes in this revision: 
                        - Add the trap hwGponDeviceOntNniType into node hwGponConfigChangeProfModeOntTrap. 
                        - Add the trap hwGponDeviceOntObjectNniType into node hwGponDistModeOntInfoTrap. 
                        - Modify nodes name: 
                          hwEponPortOntCfgAndHdwCapUnmatchedAlarmTrap to hwXponPortOntCfgAndHdwCapUnmatchedAlarmTrap,
                          hwEponPortOntCfgAndHdwCapUnmatchedRecoverAlarmTrap to hwXponPortOntCfgAndHdwCapUnmatchedRecoverAlarmTrap.
                        "

            REVISION     "201603080900Z"   
	        DESCRIPTION  "V1.25, changes in this revision:
                          - Add the trap node hwXponPortFaultAlarmTrap, hwXponPortFaultAlarmRecoverTrap 
			    in table hwXponOltAlarmTrapsPrefix. 
                          - Add the trap node hwEponPortHasIllegalOccupiedLLIDOntsAlarmTrap, hwEponPortNotHaveIllegalOccupiedLLIDOntsAlarmTrap 
			    in table hwXponDeviceOltAlarmTraps. 
                         "
            
            REVISION     "201601040900Z"   
            DESCRIPTION  "V1.24, changes in this revision: 
                        - Add the trap hwGponDeviceAutoFindOntInfoOntNniType into node hwGponOntNoAuthOntAutoFindTrap.
                        - Add the trap hwGponDeviceAutoFindOntInfoOntNniType into node hwGponProfOntAutoFindTrap.
			            - Add the trap node hwXponOntDosAttackAlarmTrap,hwXponOntDosAttackAlarmRecoverTrap into table hwXponOntAlarmTrapsPrefix. 
			            - Add the leaf nodes hwXponOntDosAttackProtocolType and hwXponOntDosAttackPeakTrafficValue into table hwXponCommonTrapsVbOids. 	
                         "
    
    	    REVISION     "201511120900Z"   
            DESCRIPTION  "V1.23, changes in this revision: 
                        - Add the trap node
	                        hwGponOltTrafficUpstreamAlarmTrap,
	                        hwGponOltTrafficUpstreamRecoverAlarmTrap,
	                        hwGponOltTrafficUpstreamWarningTrap,
	                        hwGponOltTrafficUpstreamRecoverWarningTrap,
	                        hwGponOltTrafficDownstreamAlarmTrap,
	                        hwGponOltTrafficDownstreamRecoverAlarmTrap,
	                        hwGponOltTrafficDownstreamWarningTrap,
	                        hwGponOltTrafficDownstreamRecoverWarningTrap into table hwXponOltAlarmTrapsPrefix.
	                      - Add the leaf nodes
	                        hwXponOltTrafficAlarmProfileAlarmDetectTimes
	                        hwXponOltTrafficAlarmProfileWarningDetectTimes
	                        hwXponOltTrafficStatisticUpstreamCongestionTimes
	                        hwXponOltTrafficStatisticDownstreamCongestionTimes
	                        into the table hwXponCommonTrapsVbOids.
                         "
	        REVISION     "201507220900Z" 
            DESCRIPTION  "V1.23, changes in this revision:
                          - Add the leaves hwGponOntPowerOverloadAlarmTrap and hwGponOntPowerOverloadRecoverAlarmTrap in table hwXponOntAlarmTrapsPrefix.
                         " 
                             
            REVISION     "201501060900Z"   
            DESCRIPTION  "V1.22, changes in this revision:
                          - Add the node of hwXponOntCannotAutoAddEventTrap in table hwXponDeviceOltAlarmTraps.
                         " 
                         
            REVISION     "201412060900Z"   
            DESCRIPTION  "V1.21, changes in this revision:
                          - Add the trap hwGponDeviceAutoFindOntInfoCustomizedInfo into node hwGponProfOntAutoFindTrap.     
                          - Add the trap hwEponDeviceAutoFindOntInfoCustomizedInfo into node hwEponProfOntAutoFindTrap.   
                          - Add the trap hwGponDeviceAutoFindOntCustomizedInfo into node hwGponDeviceOntAutoFindTrap.     
                          - Add the trap hwGponDeviceOntCustomizedInfo into node hwGponProfOntVersionTrap.
                          - Add the trap hwEponDeviceOntCustomizedInfo into node hwEponProfOntUpVersionTrap.
                          - Add the trap hwGponDeviceOntConfigCustomizedInfo into node hwGponDeviceOntVersionTrap.
                          - Add the trap hwGponDeviceAutoFindOntInfoCustomizedInfo into node hwGponOntNoAuthOntAutoFindTrap.
                          - Add the trap hwEponDeviceAutoFindOntInfoCustomizedInfo into node hwEponOntNoAuthOntAutoFindTrap.
                          - Add the trap hwGponDeviceOntCustomizedInfo  into node hwXponCommonOntFirstOnlineTrap.
                         " 
                         
            REVISION     "201408010900Z"   
            DESCRIPTION  "V1.20, changes in this revision:
                          - Modify the enum values in node hwXponProfOntOpticalMoudleAlarmType.     
                          - Modify the enum values in node hwGponOntOpticalMoudleAlarmType.                                                   
                         "     
                         
            REVISION     "201407100900Z"   
            DESCRIPTION  "V1.19, changes in this revision:
                          - Add a new trap hwEponOntNoAuthOntAutoFindTrap into table hwXponCommonGeneralTrapsPrefix.                                                   
                         "     
            REVISION     "201407030900Z"   
            DESCRIPTION  "V1.18, changes in this revision:
                          - Modify the range of nodes hwXponOltLosAffectOntNum and hwXponOltLosDgiOntNum.                                                    
                         "   

            REVISION     "201406160900Z"           
            DESCRIPTION  "V1.17, changes in this revision:
                         - Fix the errors for OMSYS.
                         "

            REVISION     "201403040900Z"   
            DESCRIPTION  "V1.16, changes in this revision:
                          - Modify the enum values in node hwXponOntPppoeSimuResult.
                          - Add the trap nodes hwXponDeviceDbaProfileFixDelay, hwXponDeviceDbaProfileAdditionalBW,
                            hwXponDeviceDbaProfilePriority, hwXponDeviceDbaProfileWeight into hwXponDBAProfileOperateTrap.
                          - Add the leaf nodes hwXponOltLosAffectOntNum and hwXponOltLosDgiOntNum into the table hwXponCommonTrapsVbOids.
                          - Add the trap nodes hwXponOltLosAffectOntNum and hwXponOltLosDgiOntNum into hwGponOltLOSAlarmTrap.
                          - Add the trap nodes hwXponOltLosAffectOntNum and hwXponOltLosDgiOntNum into hwXponProfOltLOSAlarmTrap.                            
                         "  
                         
            REVISION     "201305200900Z"   
            DESCRIPTION  "V1.15, changes in this revision:
                          - Rename hwGponOntEthPortQinqMode to hwGponOntPortQinqMode.
                          - Rename hwGponOntEthPortPriorityPolicy to hwGponOntPortPriorityPolicy.
                          - Rename hwXponOntPppoeSimuEthPortID to hwXponOntPppoeSimuPortID.
                          - Add the trap nodes hwGponDeviceOntProfileVdslPortNum into hwGponDevProfileCfgTrap.
                          - Add a new trap hwGponOntNoAuthOntAutoFindTrap into table hwXponCommonGeneralTrapsPrefix.
                         "
                         
            REVISION     "201303180900Z"   
            DESCRIPTION  "V1.14, changes in this revision:
                        - Add the leaf nodes hwGponOntPortTDMTxClock into table hwXponCommonTrapsVbOids.                          
                        "
            REVISION     "201210190900Z"   
            DESCRIPTION  "V1.13, changes in this revision:
                        - Add the leaf nodes hwXponOltAdminState, hwXponOltEnergySavingFlag into table hwXponCommonTrapsVbOids.
                        - Add the trap nodes hwXponOltAdminState into hwXponConfigPmConfigTrap.
                        - Add the trap nodes hwXponOltEnergySavingFlag into hwXponPortStateChangeTrap.
                        - Modify nodes name: 
                          hwGponOltMinBandwidth to hwXponOltMinBandwidth, 
                          hwGponOltNearestDistance to hwXponOltNearestDistance, 
                          hwGponOltFarestDistance to hwXponOltFarestDistance, 
                          hwGponOltAutoFindOntFlag to hwXponOltAutoFindOntFlag, 
                          hwGponOltAutoUpdateOntFlag to hwXponOltAutoUpdateOntFlag, 
                          hwGponOltDownFecEnableFlag to hwXponOltDownFecEnableFlag, 
                          hwGponOltChangePasswordIntervalTime to hwXponOltChangePasswordIntervalTime.                            
                        "
            REVISION     "201210190900Z"   
            DESCRIPTION  "V1.12, changes in this revision:
                        - Add the leaf nodes : hwXponOntInitiativeDownAlarmTrap, hwXponOntInitiativeDownAlarmRecoverTrap into table hwXponOntAlarmTraps.
                        - Add the trap node hwEponDeviceAutoFindOntInfoOntExtendedModel into hwXponCommonOntFirstOnlineTrap.
                        - Add the trap node hwEponDeviceAutoFindOntInfoOntExtendedModel into hwEponProfOntUpVersionTrap.
                        - Modify hwEponDeviceAutoFindOntRateType name to hwEponDeviceAutoFindOntNniType.
                        - Add the node of hwEponPortOntCfgAndHdwCapUnmatchedAlarmTrap and hwEponPortOntCfgAndHdwCapUnmatchedRecoverAlarmTrap
                          in table hwXponDeviceOltAlarmTraps.
                        - Add the trap node hwGponDeviceOntVoipCfgFileVersion into hwGponDeviceOntVersionTrap.
                        - Add the trap node hwGponDeviceOntVoipCfgFileVersion into hwGponProfOntVersionTrap.
                        - Add a new trap hwXponOntVoipConfigResultTrap.
                         "
                              
            REVISION     "201206200900Z"   
            DESCRIPTION  "V1.11, changes in this revision:
                        - Modify the enum values in node hwXponModeSwitchResult.
                        - Add leaf hwXponPortOtdrResultTrap in table hwXponCommonGeneralTrapsPrefix.
                         "

            REVISION     "201206140900Z"   
            DESCRIPTION  "V1.10, changes in this revision:
                        - Modify hwXponTrapOperType to hwTrapOperType into hwXponDeviceConfigChangeSnmpProfileTrap.
                        - Modify hwXponTrapOperType to hwTrapOperType into hwXponConfigChangeSnmpProfileTrap.
                         "     
        
            REVISION     "201204200900Z"   
            DESCRIPTION  "V1.09, changes in this revision: 
                        - Modify hwGponDeviceOntPoridTrafficTblId to hwGponDeviceOntPortidTrafficTblId.
                        - Add the trap node hwXponOntSupportVoipCfgMethod into hwGponProfOntVersionTrap.
                        - Add the trap node hwEponDeviceAutoFindOntInfoOntExtendedModel into hwGponProfOntVersionTrap.
                        - Add the trap node hwEponDeviceAutoFindOntInfoOuiVersion into hwGponProfOntVersionTrap.
                        - Add the trap node hwXponOntSupportVoipCfgMethod into hwEponProfOntUpVersionTrap.
                        - Add the trap node hwXponOntSupportVoipCfgMethod into hwGponDeviceOntVersionTrap.
                        - Add the trap node hwXponOntSupportVoipCfgMethod into hwXponCommonOntFirstOnlineTrap.
                         "
                         
            REVISION     "201202200900Z"   
            DESCRIPTION  "V1.08, changes in this revision: 
                        - Modify the definition of node hwGponONTGEMPortCfgChangeTrap.
                         "
                         
            REVISION     "201112120900Z"   
            DESCRIPTION  "V1.07, changes in this revision:
                        - Add the leaf nodes : hwGponOntLoociCountAlarmTrap, hwGponOntLoociCountRecoverAlarmTrap into table hwXponOntAlarmTraps.
                        - Add the leaf nodes hwEponPortStatisticsExceedAlarmThresholdFaultAlarmTrap,
                          hwEponPortStatisticsExceedAlarmThresholdRecoverAlarmTrap, 
                          hwEponPortStatisticsExceedWarningThresholdFaultAlarmTrap, 
                          hwEponPortStatisticsExceedWarningThresholdRecoverAlarmTrap into table hwXponDeviceOltAlarmTraps.
                        - Add the leaf nodes hwEponOntStatisticsExceedAlarmThresholdFaultAlarmTrap,
                          hwEponOntStatisticsExceedAlarmThresholdRecoverAlarmTrap, 
                          hwEponOntStatisticsExceedWarningThresholdFaultAlarmTrap, 
                          hwEponOntStatisticsExceedWarningThresholdRecoverAlarmTrap into table hwXponDeviceOntAlarmTraps. 
                        - Add the leaf nodes hwEponAlarmProfileStatisticsItem,hwEponAlarmProfileThresholdValue,hwEponAlarmProfileCurrentValue
                          into table hwXponDeviceTrapsVbOids.
                        - Modify hwGponOntPerfHis15MinFECCorrectCodeWords to hwGponOntPerfHis15MinFecCorrectCodeWords.
                        - Modify hwGponOntPerfHis15MinFECUncorrectCodeWords to hwGponOntPerfHis15MinFecUncorrectCodeWords.
                        - Modify hwGponOntPerfHis15MinFECTotalCodeWords to hwGponOntPerfHis15MinFecTotalCodeWords.
                         "
            
            REVISION     "201111040900Z"   
            DESCRIPTION  "V1.06, changes in this revision:
                        - Add the leaf nodes hwGponOntDownstreamSDAlarmTrap, hwGponOntDownstreamSDRecoverAlarmTrap, hwGponOntDownstreamSFAlarmTrap, 
                          hwGponOntDownstreamSFRecoverAlarmTrap, hwGponOntTemperatureAlarmTrap, hwGponOntTemperatureRecoverAlarmTrap, 
                          hwGponOntVoltageAlarmTrap, hwGponOntVoltageRecoverAlarmTrap into table hwXponOntAlarmTraps.
                        - Add leaf hwXponTrapParaOltPortState in hwXponCommonTrapsVbOids for trap hwXponPortStateChangeTrap"

            REVISION     "201110140900Z"   
            DESCRIPTION  "V1.05, changes in this revision:
                        - Add one new trap hwGponTypeBDParentRogueOntStatusChangeTrap.
                        - Modify hwEponProfBoardChipFaultAlarmTrap and hwEponProfBoardChipFaultRecoverAlarmTrap names to hwXponBoardChipFaultAlarmTrap and hwXponBoardChipFaultRecoverAlarmTrap.
                        - Modify hwEponDeviceInnerFaultID name to hwXponDeviceOltChipsetId in hwXponDeviceTrapsVbOids.
                        - Add leaf hwXponDeviceOltPortList in hwXponCommonTrapsVbOids for trap hwXponBoardChipFaultAlarmTrap and hwXponBoardChipFaultRecoverAlarmTrap."

            REVISION     "201109070900Z"   
            DESCRIPTION  "V1.04, changes in this revision:
                        - Modify the spelling mistake of word porfile."
                        
            REVISION     "201108300900Z"   
            DESCRIPTION  "V1.03, changes in this revision:
                        - Modify the trap node name from hwGponOntRangingFailureAlarmTrap to hwGponPortRangingFailureAlarmTrap for port ranging failure alarm. 
                        - Modify the trap node name from hwGponOntRangingFailureRecoverAlarmTrap to hwGponPortRangingFailureRecoverAlarmTrap for restore alarm of port ranging failure."

            REVISION     "201108120900Z"   
            DESCRIPTION  "V1.03, changes in this revision:
                        - Add the trap node hwPSGponOnuMemberStateInconsistentAlarmTrap,hwPSGponOnuMemberStateInconsistentRecoverAlarmTrap in hwXponOntAlarmTrapsPrefix."

            REVISION     "201108100900Z"   
            DESCRIPTION "V1.03, changes in this revision:
                        - Add the trap node hwXponProtectionGroupAPSProtocolFaultAlarmTrap into table hwXponOntAlarmTrapsPrefix.
                        - Add the trap node hwXponProtectionGroupAPSProtocolRecoveryAlarmTrap into table hwXponOntAlarmTrapsPrefix.
                        - Add leaf hwXponOntFirstOnline in hwXponCommonTrapsVbOids for trap hwGponDeviceOntVersionTrap, hwGponProfOntVersionTrap and hwEponProfOntUpVersionTrap.     
                        - Add the trap node hwXponOntFirstOnline into hwGponDeviceOntVersionTrap.
                        - Add the trap node hwXponOntFirstOnline into hwGponProfOntVersionTrap.
                        - Add the trap node hwXponOntFirstOnline into hwEponProfOntUpVersionTrap.
                        - Add leaf hwXponCommonOntFirstOnlineTrap in table hwXponCommonGeneralTrapsPrefix.
                        "
            REVISION     "201107200900Z"   
            DESCRIPTION  "V1.02, changes in this revision:
                        - Add the leaf nodes hwXponOntRegisterSn, hwFrameIndexOfNewConnectedOnt, hwSlotIndexOfNewConnectedOnt, hwPortIndexOfNewConnectedOnt in hwXponCommonTrapsVbOids for standard traps.
                        - Add the trap node hwGponOntRangingFailureAlarmTrap for ONT ranging failure alarm. 
                        - Add the trap node hwGponOntRangingFailureRecoverAlarmTrap for restore alarm of ONT ranging failure.
                        - Add the trap node hwXponOntRegisterInvalidAlarmTrap for the authorization information of ONT is invalid.
                        - Modify the name of trap node from hwXponProfLocalOpticalModuleExceedAlramThresAlarmTrap to hwXponProfLocalOpticalModuleExceedAlarmThresAlarmTrap.
                        - Delete the trap node hwGponOntMISAlarmTrap and hwGponOntMISRecoverAlarmTrap from table hwGponOntAlarmTraps.
                        - Delete the trap node hwGponProfOntMISAlarmTrap and hwGponProfOntMISRecoverAlarmTrap from table hwXponDeviceOntAlarmTraps.
                        - Delete the trap node hwGponOntProtectionSwitchFailAlarmTrap from table hwGponOntAlarmTraps.
                        - Delete the trap node hwGponProfOntProtectionSwitchFailAlarmTrap from table hwXponDeviceOntAlarmTraps.
                        - Add the trap node hwXponOntLoadResult into hwXponUpLoadReportTrap.
                        - Modify the definition and description of node hwXponOntLoadResult.
                        - Add leaf hwGponOntDfiAlarmTrap and hwGponOntDfiRecoverAlarmTrap in table hwXponOntAlarmTrapsPrefix.                       
                        - Add leaf hwGponOntDowiCountAlarmTrap,hwGponOntDowiCountRecoverAlarmTrap,hwGponOntRdiiAlarmTrap,
                          hwGponOntRdiiRecoverAlarmTrap in table hwXponOntAlarmTraps.
                        - Add leaf hwXponAlarmUpperCountThreshold,hwXponAlarmLowerCountThreshold,hwXponAlarmCurrentCountValue
                          in table hwXponCommonTrapsVbOids.
                        - Add the node of hwXponNumerousOntsPowerOffRestoreAlarmTrap for restore alarm of distric power-off."
                         
            REVISION     "201106230900Z"
            DESCRIPTION  "V1.01, Move TRAP objects from HUAWEI-XPON-COMMON-MIB.mib, HUAWEI-XPON-MIB.mib and HUAWEI-GPON-MIB.mib 
                         to HUAWEI-XPON-TRAP-MIB.mib."

            REVISION     "201105180900Z"
            DESCRIPTION  "V1.00, Initial version."
            ::= { hwXponCommonMIB 3 }

     -- XPON Trap
        hwXponDeviceTrapsVbOids           OBJECT IDENTIFIER ::= { hwXponDeviceObjects 11 }
        hwXponDeviceTraps                 OBJECT IDENTIFIER ::= { hwXponDeviceObjects 12 }

        hwXponDeviceAlarmTraps            OBJECT IDENTIFIER ::= { hwXponDeviceTraps 2 }
        hwXponDeviceOltAlarmTraps         OBJECT IDENTIFIER ::= { hwXponDeviceAlarmTraps 1 }
        hwXponDeviceOltAlarmTrapsPrefix   OBJECT IDENTIFIER ::= { hwXponDeviceOltAlarmTraps 0 }
        hwXponDeviceOntAlarmTraps         OBJECT IDENTIFIER ::= { hwXponDeviceAlarmTraps 2 }
        hwXponDeviceOntAlarmTrapsPrefix   OBJECT IDENTIFIER ::= { hwXponDeviceOntAlarmTraps 0 }
        hwXponDeviceCommonTraps           OBJECT IDENTIFIER ::= { hwXponDeviceTraps 3 }
        hwXponDeviceCommonTrapsPrefix     OBJECT IDENTIFIER ::= { hwXponDeviceCommonTraps 0 }

     -- GPON Trap
        hwGponTrapsVbOids                 OBJECT IDENTIFIER ::= { hwGponDeviceObjects 30 }
        hwGponTraps                       OBJECT IDENTIFIER ::= { hwGponDeviceObjects 31 }

        hwGponCommonTraps                 OBJECT IDENTIFIER ::= { hwGponTraps 1 }
        hwGponCommonTrapsPrefix           OBJECT IDENTIFIER ::= { hwGponCommonTraps 0 }
        hwGponAlarmTraps                  OBJECT IDENTIFIER ::= { hwGponTraps 2 }
        hwGponOltAlarmTraps               OBJECT IDENTIFIER ::= { hwGponAlarmTraps 1 }
        hwGponOltAlarmTrapsPrefix         OBJECT IDENTIFIER ::= { hwGponOltAlarmTraps 0 }
        hwGponOntAlarmTraps               OBJECT IDENTIFIER ::= { hwGponAlarmTraps 2 }
        hwGponOntAlarmTrapsPrefix         OBJECT IDENTIFIER ::= { hwGponOntAlarmTraps 0 }

     -- XPON-COMMON Trap
        hwXponCommonTrapsVbOids           OBJECT IDENTIFIER ::= { hwXponCommonMIB 2 }

        hwXponCommonGeneralTraps          OBJECT IDENTIFIER ::= { hwXponCommonTraps 1 }
        
        hwXponCommonGeneralTrapsPrefix    OBJECT IDENTIFIER ::= { hwXponCommonGeneralTraps 0 }
        hwXponAlarmTraps                  OBJECT IDENTIFIER ::= { hwXponCommonTraps 2 }
        hwXponOntAlarmTraps               OBJECT IDENTIFIER ::= { hwXponAlarmTraps 1 }
        hwXponOntAlarmTrapsPrefix         OBJECT IDENTIFIER ::= { hwXponOntAlarmTraps 0 }
        hwXponOltAlarmTraps               OBJECT IDENTIFIER ::= { hwXponAlarmTraps 2 }
        hwXponOltAlarmTrapsPrefix         OBJECT IDENTIFIER ::= { hwXponOltAlarmTraps 0 }


-- XPON TRAP

        hwGponProfOntTDMPortAlarmType OBJECT-TYPE
            SYNTAX OCTET STRING (SIZE (1..50))
            MAX-ACCESS accessible-for-notify
            STATUS current
            DESCRIPTION
                "This object indicates the alarm type.
                 Options:
                 1. Transmit failure (TF),
                 2. Loss of frame (LOF),
                 3. Out of frame (OOF),
                 4. Remote alarm indication (RAI),
                 5. 2.048 Mbit/s alarm indication signal (AIS).
                "
            ::= { hwXponDeviceTrapsVbOids 1 }

        hwXponOntMask OBJECT-TYPE
            SYNTAX OCTET STRING (SIZE (1..16))
            MAX-ACCESS accessible-for-notify
            STATUS current
            DESCRIPTION
                "This object indicates the ONT MASK."
            ::= { hwXponDeviceTrapsVbOids 2 }

        hwGponProfOltDualparentWorkState OBJECT-TYPE
            SYNTAX INTEGER{
                active(1),
                standby(2),
                fault(3),
                detect(4)
            }
            MAX-ACCESS accessible-for-notify
            STATUS current
            DESCRIPTION
                "This object indicates the work status.
                 Options:
                 1. active(1)      - The work status is active
                 2. standby(2)     - The work status is standby
                 3. fault(3)       - The work status is fault
                 4. detect(4)      - The work status is detective
                "
            ::= { hwXponDeviceTrapsVbOids 3 }

        hwXponProfOntOpticalMoudleAlarmType OBJECT-TYPE
            SYNTAX INTEGER {
                rxPower(1),
                txPower(2),
                voltage(3),
                temperature(4),
                biasCurrent(5),
                txPower10g(6),
                biasCurrent10g(7),
	        catvRxPower(8)
            }
            MAX-ACCESS accessible-for-notify
            STATUS current
            DESCRIPTION
                "This object indicates the alarm type,
                 Options:
                 1. rxPower(1)               - The alarm type is rxPower
                 2. txPower(2)               - The alarm type is txPower
                 3. voltage(3)               - The alarm type is voltage
                 4. temperature(4)           - The alarm type is temperature
                 5. biasCurrent(5)           - The alarm type is bias current
                 6. txPower10g(6)   	     - The alarm type is 10G txPower
                 7. biasCurrent10g(7)        - The alarm type is 10G bias current
	         8. catvRxPower(8)           - The alarm type is catv rxPower
                "
            ::= { hwXponDeviceTrapsVbOids 4 }

        hwXponProfOntOpticalMoudleAlarmUpperValue OBJECT-TYPE
            SYNTAX OCTET STRING (SIZE (1..20))
            MAX-ACCESS accessible-for-notify
            STATUS current
            DESCRIPTION
                "This object indicates the upper threshold(Value:-1024.00~1024.00)."
            ::= { hwXponDeviceTrapsVbOids 5 }

        hwXponProfOntOpticalMoudleAlarmLowerValue OBJECT-TYPE
            SYNTAX OCTET STRING (SIZE (1..20))
            MAX-ACCESS accessible-for-notify
            STATUS current
            DESCRIPTION
                "This object indicates the lower threshold(Value:-1024.00~1024.00)."
            ::= { hwXponDeviceTrapsVbOids 6 }

        hwXponProfOntOpticalMoudleAlarmCurrentValue OBJECT-TYPE
            SYNTAX OCTET STRING (SIZE (1..20))
            MAX-ACCESS accessible-for-notify
            STATUS current
            DESCRIPTION
                "This object indicates the current value(Value:-1024.00~1024.00)."
            ::= { hwXponDeviceTrapsVbOids 7 }

        hwGponProfOntDualUpstreamSupport OBJECT-TYPE
            SYNTAX   INTEGER{
                support(1),
                notsupport(2),
                unknown(255)
            }
            MAX-ACCESS   accessible-for-notify
            STATUS       current
            DESCRIPTION 
                "This object indicates whether the ONT supports type C protection.
                 Options:
                 1. support(1)      - Support the ONT supports type C protection
                 2. notsupport(2)   - Do not support the ONT supports type C protection
                 3. unknown(255)    - Indicates that the query fails or no information is detected
                "
            ::= { hwXponDeviceTrapsVbOids 8 }

        hwXponDeviceOltChipsetId  OBJECT-TYPE
            SYNTAX Integer32 (0..255)
            MAX-ACCESS accessible-for-notify
            STATUS current
            DESCRIPTION
                "This object indicates only the MAC chipset ID on the board."
            ::= { hwXponDeviceTrapsVbOids 250 }

        hwEponDeviceAutoFindOntInfoLoidValue  OBJECT-TYPE
            SYNTAX OCTET STRING (SIZE (0..24))
            MAX-ACCESS accessible-for-notify
            STATUS current
            DESCRIPTION
                "This object indicates the logic ONT ID."
            ::= { hwXponDeviceTrapsVbOids 251 }

        hwEponDeviceAutoFindOntInfoCheckcodeValue  OBJECT-TYPE
            SYNTAX OCTET STRING (SIZE (0..12))
            MAX-ACCESS accessible-for-notify
            STATUS current
            DESCRIPTION
                "This object indicates the check code."
            ::= { hwXponDeviceTrapsVbOids 252 }

        hwEponDeviceOntVoltageState OBJECT-TYPE
            SYNTAX   INTEGER {
                higher(0),
                lower(1),
                unknown(-1)
            }
            MAX-ACCESS accessible-for-notify
            STATUS current
            DESCRIPTION
                "This object indicates the voltage state.
                 Options:
                 1. higher(0)   - Indicates that the voltage state is higher
                 2. lower(1)    - Indicates that the voltage state is lower
                 3. unknown(-1) - Indicates that the voltage state is unknown
                "
            ::= { hwXponDeviceTrapsVbOids 253 }

        hwEponDeviceOntTypeDSupport OBJECT-TYPE
            SYNTAX   INTEGER{
                support(1),
                notsupport(2),
                unknown(255)
            }
            MAX-ACCESS   accessible-for-notify
            STATUS       current
            DESCRIPTION
                "This object indicates whether the ONT supports type D protection.
                 Options:
                 1. support(1)      - Support the ONT supports type D protection
                 2. notsupport(2)   - Do not support the ONT supports type D protection
                 3. unknown(255)    - Indicates that the query fails or no information is detected
                "
            ::= { hwXponDeviceTrapsVbOids 254 }

        hwEponDeviceAutoFindOntInfoTdmNumber OBJECT-TYPE
            SYNTAX   Integer32
            MAX-ACCESS   accessible-for-notify
            STATUS       current
            DESCRIPTION
                "This object indicates the auto find ont info TDM number."
            ::= { hwXponDeviceTrapsVbOids 255 }

        hwEponDeviceAutoFindOntInfoPotsNumber OBJECT-TYPE
            SYNTAX   Integer32
            MAX-ACCESS   accessible-for-notify
            STATUS       current
            DESCRIPTION
                "This object indicates the uto find ont info pots number."
            ::= { hwXponDeviceTrapsVbOids 256 }

        hwEponDeviceAutoFindOntInfoFeNumber OBJECT-TYPE
            SYNTAX   Integer32
            MAX-ACCESS   accessible-for-notify
            STATUS       current
            DESCRIPTION
                "This object indicates the auto find ont info FE number."
            ::= { hwXponDeviceTrapsVbOids 257 }

        hwEponDeviceAutoFindOntInfoGeNumber OBJECT-TYPE
            SYNTAX   Integer32
            MAX-ACCESS   accessible-for-notify
            STATUS       current
            DESCRIPTION
                "This object indicates the auto find ont info GE number."
            ::= { hwXponDeviceTrapsVbOids 258 }

        hwEponDeviceOntEquipmentId OBJECT-TYPE
            SYNTAX   OCTET STRING (SIZE(1..20))
            MAX-ACCESS   accessible-for-notify
            STATUS       current
            DESCRIPTION
                "This object indicates the auto find ont info GE number."
            ::= { hwXponDeviceTrapsVbOids 259 }

        hwXponTrapOperType OBJECT-TYPE
            SYNTAX   INTEGER {
                add(1),
                modify(2),
                delete(3)
            }
            MAX-ACCESS   accessible-for-notify
            STATUS       current
            DESCRIPTION
                "This object indicates the operation type.
                 Options:
                 1. add(1)     - Add
                 2. modify(2)  - Modify
                 3. delete(3)  - Delete
                "
            ::= { hwXponDeviceTrapsVbOids 502 }

        hwXponDeviceOntPortRunStatus OBJECT-TYPE
            SYNTAX   Integer32
            MAX-ACCESS   accessible-for-notify
            STATUS       current
            DESCRIPTION
                "This object indicates the ONT port run status.
                 The value 1 means that the ONT port is up,
                 the value 2 means that the ONT port is down.
               "
            ::= { hwXponDeviceTrapsVbOids 503 }

        hwXponOntLoadResult OBJECT-TYPE
            SYNTAX   INTEGER {
                success(0),
                fail(1),
                load20Percent(2),
                resultfiletoobig(3),
                filecheckerror(4),
                packetfileerror(5),
                ontreplaytimeout(6)
            }
            MAX-ACCESS   accessible-for-notify
            STATUS       current
            DESCRIPTION
                "This object indicates the load result.
                 Options:
                 1. success(0)            - Indicates that the load result is success
                 2. fail(1)               - Indicates that the load result is fail
                 3. load20Percent(2)      - Indicates that the load result is loaded 20 percent
                 4. resultfiletoobig(3)   - Indicates that the result file is too big
                 5. filecheckerror(4)     - Indicates that it is fail to check the file
                 6. packetfileerror(5)    - Indicates that it is fail to check the packet
                 7. ontreplaytimeout(6)   - Indicates that the reply of the ont is time out
                "
            ::= { hwXponDeviceTrapsVbOids 504 }

        hwXponOntLoadCrcSupport OBJECT-TYPE
            SYNTAX   INTEGER {
                noSupport(0),
                support(1),
                unconcern(255)
            }
            MAX-ACCESS   accessible-for-notify
            STATUS       current
            DESCRIPTION
                "This object indicates whether the ONT load supports the CRC.
                 Options:
                 1. noSupport(0)    - Do not support the ONT load supports the CRC
                 2. support(1)      - Support the ONT load supports the CRC
                 3. unconcern(255)  - Indicates that the query fails or no information is detected
                "
            ::= { hwXponDeviceTrapsVbOids 505 }

        hwXponOntLoadCrcValue OBJECT-TYPE
            SYNTAX   Integer32
            MAX-ACCESS   accessible-for-notify
            STATUS       current
            DESCRIPTION
                "This object indicates the CRC value of the loaded ONT configuration file.
                 The value (-1) indicates that the ont does not support CRC or value is invalid."
            ::= { hwXponDeviceTrapsVbOids 506 }

        hwXponDeviceOntCRCSupport OBJECT-TYPE
            SYNTAX   INTEGER {
                noSupport(0),
                support(1)
            }
            MAX-ACCESS   accessible-for-notify
            STATUS       current
            DESCRIPTION
                "This object indicates whether the ONT supports the CRC.
                 Options:
                 1. noSupport(0) - If the value of this object is 0, it indicates that the CRC function is not supported
                 2. support(1)   - If the value of this object is 1, it indicates that the CRC function is supported
                "
            ::= { hwXponDeviceTrapsVbOids 507 }

        hwXponDeviceOntCRCCode OBJECT-TYPE
            SYNTAX   Integer32
            MAX-ACCESS   accessible-for-notify
            STATUS       current
            DESCRIPTION
                "This object indicates the code of ONT CRC, it is valid only the ont support CRC check.
                 Otherwise, the value always equals 0.
                "
            ::= { hwXponDeviceTrapsVbOids 508 }

        hwXponOntLoadOperType OBJECT-TYPE
            SYNTAX   Integer32
            MAX-ACCESS   accessible-for-notify
            STATUS       current
            DESCRIPTION
                "This object indicates the operations type of the ONT load.
                 The value 1 indicates loading the configuration or application file,
                 the value 2 indicates the checked result of the configuration file.
                "
            ::= { hwXponDeviceTrapsVbOids 509 }

        hwXponDeviceOntRunStatus OBJECT-TYPE
            SYNTAX  INTEGER {
                up(1),
                down(2)
            }
            MAX-ACCESS   accessible-for-notify
            STATUS       current
            DESCRIPTION
                "This object indicates the running status of ONT load.
                 Options:
                 1. up(1)     - Indicates that the running status of ONT load is up
                 2. down(2)   - Indicates that the running status of ONT load is down
                "
            ::= { hwXponDeviceTrapsVbOids 510 }

        hwEponRogueOntDetectOperStatus OBJECT-TYPE
            SYNTAX   INTEGER {
                start(1),
                over(2)
            }
            MAX-ACCESS   accessible-for-notify
            STATUS       current
            DESCRIPTION
                "This object indicates the operation status of the EPON rogue ONT detection.
                 Options:
                 1. start(1)   - Start the EPON rogue ONT detection
                 2. over(2)    - Stop the EPON rogue ONT detection
                "
            ::= { hwXponDeviceTrapsVbOids 511 }

        hwEponDeviceOntPortManageStatus OBJECT-TYPE
            SYNTAX   INTEGER {
                unlock(1),
                lock(2)
            }
            MAX-ACCESS   accessible-for-notify
            STATUS       current
            DESCRIPTION
                "This object indicates the running status of the EPON ONT port.
                 Options:
                 1. unlock(1)   - Unlock the EPON ONT port
                 2. lock(2)     - Lock the EPON ONT port
                "
            ::= { hwXponDeviceTrapsVbOids 512 }

        hwXponDeviceAccessType OBJECT-TYPE
            SYNTAX   INTEGER {
                gpon(1),
                epon(2)
            }
            MAX-ACCESS   accessible-for-notify
            STATUS       current
            DESCRIPTION
                "This object indicates the XPON profile type.
                 Options:
                 1. gpon(1)   - GPON
                 2. epon(2)   - EPON
                "
            ::= { hwXponDeviceTrapsVbOids 513 }

        hwXponDeviceServiceProfileName OBJECT-TYPE
            SYNTAX OCTET STRING (SIZE (0..33))
            MAX-ACCESS   accessible-for-notify
            STATUS       current
            DESCRIPTION
                "This object indicates the service profile name."
            ::= { hwXponDeviceTrapsVbOids 514 }

        hwXponDeviceLineProfileName OBJECT-TYPE
            SYNTAX OCTET STRING (SIZE (0..33))
            MAX-ACCESS   accessible-for-notify
            STATUS       current
            DESCRIPTION
                "This object indicates the line profile name."
            ::= { hwXponDeviceTrapsVbOids 515 }

        hwEponDeviceAlarmProfileName OBJECT-TYPE
            SYNTAX OCTET STRING (SIZE (0..33))
            MAX-ACCESS   accessible-for-notify
            STATUS       current
            DESCRIPTION
                "This object indicates the alarm profile name."
            ::= { hwXponDeviceTrapsVbOids 516 }

        hwEponDeviceOntDbaStatus OBJECT-TYPE
            SYNTAX   INTEGER {
                dbaGpon(1),
                dbaEthernet(2),
                invalid(-1)
            }
            MAX-ACCESS   accessible-for-notify
            STATUS       current
            DESCRIPTION
                "This object indicates the status of Ont's DBA.
                 Options:
                 1. dbaGpon(1)      - Indicates that the status of Ont's DBA is GPON DBA
                 2. dbaEthernet(2)  - Indicates that the status of Ont's DBA is ETH DBA
                 3. invalid(-1)     - Indicates that the query fails or no information is detected
                "
            ::= { hwXponDeviceTrapsVbOids 517 }

        hwGponDeviceProfOntIsOntUpfromReset OBJECT-TYPE
            SYNTAX   INTEGER {
                yes(1),
                no(2)
            }
            MAX-ACCESS   accessible-for-notify
            STATUS       current
            DESCRIPTION
                "This object indicates whether the GPON ONT is online after reset.
                 Options:
                 1. yes(1)    - The ONT is reseted.
                 2. no(2)     - The ONT is not reseted.
                "
            ::= { hwXponDeviceTrapsVbOids 518 }

        hwEponDeviceOntIsOntUpfromReset OBJECT-TYPE
            SYNTAX   INTEGER {
                yes(1),
                no(2)
            }
            MAX-ACCESS   accessible-for-notify
            STATUS       current
            DESCRIPTION
                "This object indicates whether the EPON ONT is online after reset.
                 Options:
                 1. yes(1)    - The ONT is reseted.
                 2. no(2)     - The ONT is not reseted.
                "
            ::= { hwXponDeviceTrapsVbOids 519 }

        hwXponProfOntPortLearnedHGVlan OBJECT-TYPE
            SYNTAX Integer32 (-1 | 1..4094)
            MAX-ACCESS   accessible-for-notify
            STATUS       current
            DESCRIPTION
                "This object indicates the VLAN learned on the ONT port."
            ::= { hwXponDeviceTrapsVbOids 520 }

        hwXponProfOntPortLearnedHGMacAddr OBJECT-TYPE
            SYNTAX OCTET STRING (SIZE (0..6))
            MAX-ACCESS   accessible-for-notify
            STATUS       current
            DESCRIPTION
                "This object indicates the MAC address learned on the ONT port."
            ::= { hwXponDeviceTrapsVbOids 521 }
            
        hwEponAlarmProfileStatisticsItem OBJECT-TYPE
            SYNTAX OCTET STRING (SIZE (1..30))
            MAX-ACCESS accessible-for-notify
            STATUS current
            DESCRIPTION
                "This object indicates the Epon alarm profile statistics item."
            ::= { hwXponDeviceTrapsVbOids 522 }
              
        hwEponAlarmProfileThresholdValue OBJECT-TYPE
            SYNTAX OCTET STRING (SIZE (1..11))
            MAX-ACCESS accessible-for-notify
            STATUS current
            DESCRIPTION
                "This object indicates the Epon alarm profile threshold value(Value:0~4294967294)."
            ::= { hwXponDeviceTrapsVbOids 523 }

        hwEponAlarmProfileCurrentValue OBJECT-TYPE
            SYNTAX OCTET STRING (SIZE (1..21))
            MAX-ACCESS accessible-for-notify
            STATUS current
            DESCRIPTION
                "This object indicates the current value(Value:0~18446744073709551614)."
            ::= { hwXponDeviceTrapsVbOids 524 }

     -- Alarm trap

     -- GPON BOARD AND PORT ALARM
        hwGponProfOltLOSAlarmTrap NOTIFICATION-TYPE
            OBJECTS {
                hwFrameIndex,
                hwSlotIndex,
                hwPortIndex
            }
            STATUS current
            DESCRIPTION
                "The hwGponProfOltLOSAlarmTrap is sent
                 when the feed fiber is broken or OLT can not receive any expected optical signals(LOS).
                "
            ::= { hwXponDeviceOltAlarmTraps 0 1 }

        hwGponProfOltLOSRecoverAlarmTrap NOTIFICATION-TYPE
            OBJECTS {
                hwFrameIndex,
                hwSlotIndex,
                hwPortIndex
            }
            STATUS current
            DESCRIPTION
                "The hwGponProfOltLOSRecoverAlarmTrap is sent
                 when the OLT can receive expected optical signals from ONTs(LOS recovers).
                "
            ::= { hwXponDeviceOltAlarmTraps 0 2 }

        hwGponProfOltTFAlarmTrap NOTIFICATION-TYPE
            OBJECTS {
                hwFrameIndex,
                hwSlotIndex,
                hwPortIndex
            }
            STATUS current
            DESCRIPTION
                "The hwGponProfOltTFAlarmTrap is sent when the transmit failure (TF) occurs
                 at the GPON port for the hardware of the optical transceiver is faulty.
                "
            ::= { hwXponDeviceOltAlarmTraps 0 3 }

        hwGponProfOltTFRecoverAlarmTrap NOTIFICATION-TYPE
            OBJECTS {
                hwFrameIndex,
                hwSlotIndex,
                hwPortIndex
            }
            STATUS current
            DESCRIPTION
                "The hwGponProfOltTFRecoverAlarmTrap is sent
                 when the transmit failure (TF) at the GPON port recovers.
                "
            ::= { hwXponDeviceOltAlarmTraps 0 4 }

        hwGponProfOltOpticalTransceiverAbsentAlarmTrap NOTIFICATION-TYPE
            OBJECTS {
                hwFrameIndex,
                hwSlotIndex,
                hwPortIndex
            }
            STATUS current
            DESCRIPTION
                "The hwGponProfOltOpticalTransceiverAbsentAlarmTrap is sent
                 when the optical transceiver of the PON port is absent.
                "
            ::= { hwXponDeviceOltAlarmTraps 0 5 }

        hwGponProfOltOpticalTransceiverNormalAlarmTrap NOTIFICATION-TYPE
            OBJECTS {
                hwFrameIndex,
                hwSlotIndex,
                hwPortIndex
            }
            STATUS current
            DESCRIPTION
                "The hwGponProfOltOpticalTransceiverNormalAlarmTrap is sent
                 when the optical transceiver of the PON port recovers to the normal state.
                "
            ::= { hwXponDeviceOltAlarmTraps 0 6 }

        hwXponProfPortHasRogueOntsAlarmTrap NOTIFICATION-TYPE
            OBJECTS {
                hwFrameIndex,
                hwSlotIndex,
                hwPortIndex
            }
            STATUS current
            DESCRIPTION
                "The hwXponProfPortHasRogueOntsAlarmTrap is sent
                 when there are illegal incursionary rogue ONTs under the port.
                "
            ::= { hwXponDeviceOltAlarmTraps 0 7 }

        hwXponProfPortNotHaveRogueOntsAlarmTrap NOTIFICATION-TYPE
            OBJECTS {
                hwFrameIndex,
                hwSlotIndex,
                hwPortIndex
            }
            STATUS current
            DESCRIPTION
                "The hwXponProfPortNotHaveRogueOntsAlarmTrap is sent
                 when the illegal incursionary rogue ONTs under the port have been cleared.
                "
            ::= { hwXponDeviceOltAlarmTraps 0 8 }

        hwGponProfPortStatusChangesInTypeBDualAlarmTrap NOTIFICATION-TYPE
            OBJECTS {
                hwFrameIndex,
                hwSlotIndex,
                hwPortIndex
            }
            STATUS current
            DESCRIPTION
                "The hwGponProfPortStatusChangesInTypeBDualAlarmTrap is sent
                 when the working status of the GPON port in a TYPE-B dual parenting protect group changes frequently.
                "
            ::= { hwXponDeviceOltAlarmTraps 0 9 }

        hwGponProfPortStatusChangesInTypeBDualRecoverAlarmTrap NOTIFICATION-TYPE
            OBJECTS {
                hwFrameIndex,
                hwSlotIndex,
                hwPortIndex
            }
            STATUS current
            DESCRIPTION
                "The hwGponProfPortStatusChangesInTypeBDualRecoverAlarmTrap is sent
                 when the port recovers from the fault that its TYPE-B dual parenting protect status changes frequently.
                "
            ::= { hwXponDeviceOltAlarmTraps 0 10 }

        hwXponProfOltOpticalTransceiverAbsentAlarmTrap NOTIFICATION-TYPE
            OBJECTS {
                hwFrameIndex,
                hwSlotIndex,
                hwPortIndex
            }
            STATUS current
            DESCRIPTION
                "The hwXponProfOltOpticalTransceiverAbsentAlarmTrap is sent
                 when the optical transceiver of the PON port is absent.
                "
            ::= { hwXponDeviceOltAlarmTraps 0 11 }

        hwXponProfOltOpticalTransceiverNormalAlarmTrap NOTIFICATION-TYPE
            OBJECTS {
                hwFrameIndex,
                hwSlotIndex,
                hwPortIndex
            }
            STATUS current
            DESCRIPTION
                "The hwXponProfOltOpticalTransceiverNormalAlarmTrap is sent
                 when the optical transceiver of the PON port recovers to the normal state.
                "
            ::= { hwXponDeviceOltAlarmTraps 0 12 }

     -- EPON board alarm trap
        hwEponProfOltLOSAlarmTrap NOTIFICATION-TYPE
            OBJECTS {
                hwFrameIndex,
                hwSlotIndex,
                hwPortIndex
            }
            STATUS current
            DESCRIPTION
                "The hwEponProfOltLOSAlarmTrap is sent
                 when the feed fiber is broken or OLT can not receive any expected optical signals(LOS).
                "
            ::= { hwXponDeviceOltAlarmTraps 0 101 }

        hwEponProfOltLOSRecoverAlarmTrap NOTIFICATION-TYPE
            OBJECTS {
                hwFrameIndex,
                hwSlotIndex,
                hwPortIndex
            }
            STATUS current
            DESCRIPTION
                "The hwEponProfOltLOSRecoverAlarmTrap is sent
                 when the OLT canreceive expected optical signals from ONTs(LOS recovers).
                "
            ::= { hwXponDeviceOltAlarmTraps 0 102 }

        hwEponProfTooManyOntsRegisterAlarmTrap NOTIFICATION-TYPE
            OBJECTS {
                hwFrameIndex,
                hwSlotIndex,
                hwPortIndex
            }
            STATUS current
            DESCRIPTION
                "The hwEponProfTooManyOntsRegisterAlarmTrap is sent
                 when the too many ONTs register with the EPON port.
                "
            ::= { hwXponDeviceOltAlarmTraps 0 103 }

        hwXponBoardChipFaultAlarmTrap NOTIFICATION-TYPE
            OBJECTS {
                hwFrameIndex,
                hwSlotIndex,
                hwXponDeviceOltChipsetId,
                hwXponDeviceOltPortList
            }
            STATUS current
            DESCRIPTION
                "The hwXponBoardChipFaultAlarmTrap is sent
                 when the XPON board chip is faulty.
                "
            ::= { hwXponDeviceOltAlarmTraps 0 104 }

        hwXponBoardChipFaultRecoverAlarmTrap NOTIFICATION-TYPE
            OBJECTS {
                hwFrameIndex,
                hwSlotIndex,
                hwXponDeviceOltChipsetId,
                hwXponDeviceOltPortList
            }
            STATUS current
            DESCRIPTION
                "The hwXponBoardChipFaultRecoverAlarmTrap is sent
                 when the XPON board chip recovers from the fault.
                "
            ::= { hwXponDeviceOltAlarmTraps 0 105 }

        hwEponOpticalTransceiverStateFaultAlarmTrap NOTIFICATION-TYPE
            OBJECTS {
                hwFrameIndex,
                hwSlotIndex,
                hwPortIndex
            }
            STATUS current
            DESCRIPTION
                "The hwEponOpticalTransceiverStateFaultAlarmTrap is sent
                 when the optical transceiver of the port is faulty.
                 All ONTs under the port get offline.
                "
            ::= { hwXponDeviceOltAlarmTraps 0 106 }

        hwEponOpticalTransceiverStateRestoreAlarmTrap NOTIFICATION-TYPE
            OBJECTS {
                hwFrameIndex,
                hwSlotIndex,
                hwPortIndex
            }
            STATUS current
            DESCRIPTION
                "The hwEponOpticalTransceiverStateRestoreAlarmTrap is sent
                 when the optical transceiver state of the port recovers.
                "
            ::= { hwXponDeviceOltAlarmTraps 0 107 }

        hwXponProfOltLOSAlarmTrap NOTIFICATION-TYPE
            OBJECTS {
                     hwFrameIndex,
                     hwSlotIndex,
                     hwPortIndex,
                     hwXponOltLosAffectOntNum,
                     hwXponOltLosDgiOntNum
                    }
            STATUS current
            DESCRIPTION
                "The hwXponProfOltLOSAlarmTrap is sent
                 when the feed fiber is broken or OLT can not receive any expected optical signals(LOS).
                "
            ::= { hwXponDeviceOltAlarmTraps 0 108 }

        hwXponProfOltLOSRecoverAlarmTrap NOTIFICATION-TYPE
            OBJECTS {
                     hwFrameIndex,
                     hwSlotIndex,
                     hwPortIndex
                    }
            STATUS current
            DESCRIPTION
                "The hwXponProfOltLOSRecoverAlarmTrap is sent
                 when OLT can receive expected optical signals from ONTs(LOS recovers).
                "
            ::= { hwXponDeviceOltAlarmTraps 0 109 }

        hwXponTypeBUpstreamSDFaultAlarmTrap NOTIFICATION-TYPE
            OBJECTS {
                     hwFrameIndex,
                     hwSlotIndex,
                     hwPortIndex,
                     hwPgGroupId
                    }
            STATUS current
            DESCRIPTION
                   "The hwXponTypeBUpstreamSDFaultAlarmTrap trap is sent
                    when the feed fiber is broken or pon port in TYPEB protect group can not receive any expected optical signals."
            ::= { hwXponDeviceOltAlarmTraps 0 110 }

        hwXponTypeBUpstreamSDRestoreAlarmTrap NOTIFICATION-TYPE
            OBJECTS {
                     hwFrameIndex,
                     hwSlotIndex,
                     hwPortIndex,
                     hwPgGroupId
                    }
            STATUS current
            DESCRIPTION
                   "The hwXponTypeBUpstreamSDRestoreAlarmTrap trap is sent
                    when pon port in TYPEB protect group can receive expected optical signals from ONTs."
            ::= { hwXponDeviceOltAlarmTraps 0 111 }
            
        hwEponPortStatisticsExceedAlarmThresholdFaultAlarmTrap NOTIFICATION-TYPE
            OBJECTS {
                hwFrameIndex,
                hwSlotIndex,
                hwPortIndex,
                hwEponAlarmProfileStatisticsItem,
                hwEponAlarmProfileThresholdValue,
                hwEponAlarmProfileCurrentValue
            }
            STATUS current
            DESCRIPTION
                "The hwEponPortStatisticsExceedAlarmThresholdFaultAlarmTrap is sent
                 when the performance statistics value of the EPON port exceeds the alarm threshold in the alarm profile bound to the port.
                "
            ::= { hwXponDeviceOltAlarmTraps 0 112 }
            
        hwEponPortStatisticsExceedAlarmThresholdRecoverAlarmTrap NOTIFICATION-TYPE
            OBJECTS {
                hwFrameIndex,
                hwSlotIndex,
                hwPortIndex,
                hwEponAlarmProfileStatisticsItem,
                hwEponAlarmProfileThresholdValue,
                hwEponAlarmProfileCurrentValue
            }
            STATUS current
            DESCRIPTION
                "The hwEponPortStatisticsExceedAlarmThresholdRecoverAlarmTrap is sent
                 when the performance statistics value of the EPON port is within the alarm threshold range in the alarm profile bound to the port.
                 "
            ::= { hwXponDeviceOltAlarmTraps 0 113 }
        
        hwEponPortStatisticsExceedWarningThresholdFaultAlarmTrap NOTIFICATION-TYPE
            OBJECTS {
                hwFrameIndex,
                hwSlotIndex,
                hwPortIndex,
                hwEponAlarmProfileStatisticsItem,
                hwEponAlarmProfileThresholdValue,
                hwEponAlarmProfileCurrentValue
            }
            STATUS current
            DESCRIPTION
                "The hwEponPortStatisticsExceedWarningThresholdFaultAlarmTrap is sent
                 when the performance statistics value of the EPON port exceeds the warning threshold in the alarm profile bound to the port.
                "
            ::= { hwXponDeviceOltAlarmTraps 0 114 }
            
        hwEponPortStatisticsExceedWarningThresholdRecoverAlarmTrap NOTIFICATION-TYPE
            OBJECTS {
                hwFrameIndex,
                hwSlotIndex,
                hwPortIndex,
                hwEponAlarmProfileStatisticsItem,
                hwEponAlarmProfileThresholdValue,
                hwEponAlarmProfileCurrentValue
            }
            STATUS current
            DESCRIPTION
                "The hwEponPortStatisticsExceedWarningThresholdRecoverAlarmTrap is sent
                 when the performance statistics value of the EPON port is within the warning threshold range in the alarm profile bound to the port.
                "
            ::= { hwXponDeviceOltAlarmTraps 0 115 }

        hwXponPortOntCfgAndHdwCapUnmatchedAlarmTrap NOTIFICATION-TYPE
            OBJECTS {
                hwFrameIndex,
                hwSlotIndex,
                hwPortIndex
            }
            STATUS current
            DESCRIPTION
                "The hwEponPortOntCfgAndHdwCapUnmatchedAlarmTrap is sent
                 when this port has an ONT with the NNI type of 10G/10G, but the OLT optical module of this port does not support this ONT.
                "
            ::= { hwXponDeviceOltAlarmTraps 0 116 }
            
        hwXponPortOntCfgAndHdwCapUnmatchedRecoverAlarmTrap NOTIFICATION-TYPE
            OBJECTS {
                hwFrameIndex,
                hwSlotIndex,
                hwPortIndex
            }
            STATUS current
            DESCRIPTION
                "The hwEponPortOntCfgAndHdwCapUnmatchedRecoverAlarmTrap is sent
                 when the OLT optical module of this port supports all ONT NNI types configured on the port.
                "
            ::= { hwXponDeviceOltAlarmTraps 0 117 } 
             
        hwXponOntCannotAutoAddEventTrap NOTIFICATION-TYPE
            STATUS current
            DESCRIPTION
                "The hwXponOntCannotAutoAddEventTrap is sent
                 when the number of ONTs has reached the maximum of the system and a new automaticaly-added ONT is being connected.
                "
            ::= { hwXponDeviceOltAlarmTraps 0 118 }  
            
        hwEponPortHasIllegalOccupiedLLIDOntsAlarmTrap NOTIFICATION-TYPE
            OBJECTS {
                hwFrameIndex,
                hwSlotIndex,
                hwPortIndex
            }
            STATUS current
            DESCRIPTION
                "The hwEponPortHasIllegalOccupiedLLIDOntsAlarmTrap is sent
                 when there are illegal occupied LLID ONUs under the EPON port.
                "
            ::= { hwXponDeviceOltAlarmTraps 0 119 }
            
        hwEponPortNotHaveIllegalOccupiedLLIDOntsAlarmTrap NOTIFICATION-TYPE
            OBJECTS {
                hwFrameIndex,
                hwSlotIndex,
                hwPortIndex
            }
            STATUS current
            DESCRIPTION
                "The hwEponPortNotHaveIllegalOccupiedLLIDOntsAlarmTrap is sent
                 when there are no longer illegal occupied LLID ONUs under the EPON port.
                "
            ::= { hwXponDeviceOltAlarmTraps 0 120 }  
            
     -- ONT AND ONT PORT ALARM
        hwGponProfReceiveOntKeyTransmitFailAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfReceiveOntKeyTransmitFailAlarmTrap is sent
                 when failed to receive the key transmit from the ONT(LOKi).
                "
            ::= { hwXponDeviceOntAlarmTraps 0 1 }

        hwGponProfOntDiscoveryAlarmTrap NOTIFICATION-TYPE
            OBJECTS {
                hwFrameIndex,
                hwSlotIndex,
                hwPortIndex,
                hwGponDeviceAutoFindOntInfoSn,
                hwGponDeviceAutoFindOntInfoPassword,
                hwGponDeviceAutoFindOntInfoLoid,
                hwGponDeviceAutoFindOntInfoCheckcode
            }
            STATUS current
            DESCRIPTION
                "The hwGponProfOntDiscoveryAlarmTrap is sent when the GPON ONT is discovered by the OLT."
            ::= { hwXponDeviceOntAlarmTraps 0 2 }

        hwGponProfDiscoveredOntDeletedAlarmTrap NOTIFICATION-TYPE
            OBJECTS {
                hwFrameIndex,
                hwSlotIndex,
                hwPortIndex,
                hwGponDeviceAutoFindOntInfoSn,
                hwGponDeviceAutoFindOntInfoPassword,
                hwGponDeviceAutoFindOntInfoLoid,
                hwGponDeviceAutoFindOntInfoCheckcode
            }
            STATUS current
            DESCRIPTION
                "The hwGponProfDiscoveredOntDeletedAlarmTrap is sent when the discovered GPON ONT is deleted."
            ::= { hwXponDeviceOntAlarmTraps 0 3 }

        hwGponProfOntLCDGAlarmTrap NOTIFICATION-TYPE
            OBJECTS {
                hwFrameIndex,
                hwSlotIndex,
                hwPortIndex,
                hwGponDeviceOntIndex
            }
            STATUS current
            DESCRIPTION
                "The hwGponProfOntLCDGAlarmTrap is sent when the loss of GEM channel delineation (LCDGi) occurs."
            ::= { hwXponDeviceOntAlarmTraps 0 4 }

        hwGponProfOntLCDGRecoverAlarmTrap NOTIFICATION-TYPE
            OBJECTS {
                hwFrameIndex,
                hwSlotIndex,
                hwPortIndex,
                hwGponDeviceOntIndex
            }
            STATUS current
            DESCRIPTION
                "The hwGponProfOntLCDGRecoverAlarmTrap is sent
                 when the loss of GEM channel delineation (LCDGi) recovers.
                "
            ::= { hwXponDeviceOntAlarmTraps 0 5 }

        hwGponProfOntSDAlarmTrap NOTIFICATION-TYPE
            OBJECTS {
                hwFrameIndex,
                hwSlotIndex,
                hwPortIndex,
                hwGponDeviceOntIndex
            }
            STATUS current
            DESCRIPTION
                "The hwGponProfOntSDAlarmTrap is sent when the signal degrade of ONTi (SDi) occurs."
            ::= { hwXponDeviceOntAlarmTraps 0 6 }

        hwGponProfOntSDRecoverAlarmTrap NOTIFICATION-TYPE
            OBJECTS {
                hwFrameIndex,
                hwSlotIndex,
                hwPortIndex,
                hwGponDeviceOntIndex
            }
            STATUS current
            DESCRIPTION
                "The hwGponProfOntSDRecoverAlarmTrap is sent when the signal degrade of ONTi (SDi) recovers."
            ::= { hwXponDeviceOntAlarmTraps 0 7 }

        hwGponProfOntSFAlarmTrap NOTIFICATION-TYPE
            OBJECTS {
                hwFrameIndex,
                hwSlotIndex,
                hwPortIndex,
                hwGponDeviceOntIndex
            }
            STATUS current
            DESCRIPTION
                "The hwGponProfOntSFAlarmTrap is sent when the signal fail of ONTi (SFi) occurs."
            ::= { hwXponDeviceOntAlarmTraps 0 8 }

        hwGponProfOntSFRecoverAlarmTrap NOTIFICATION-TYPE
            OBJECTS {
                hwFrameIndex,
                hwSlotIndex,
                hwPortIndex,
                hwGponDeviceOntIndex
            }
            STATUS current
            DESCRIPTION
                "The hwGponProfOntSFRecoverAlarmTrap is sent when the signal fail of ONTi (SFi) recovers."
            ::= { hwXponDeviceOntAlarmTraps 0 9 }

        hwGponProfOntLOFAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntLOFAlarmTrap is sent when the loss of frame of ONTi (LOFi) occurs."
            ::= { hwXponDeviceOntAlarmTraps 0 10 }

        hwGponProfOntLOFRecoverAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntLOFRecoverAlarmTrap is sent when the loss of frame of ONTi (LOFi) recovers."
            ::= { hwXponDeviceOntAlarmTraps 0 11 }

        hwGponProfOntLOSAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntLOSAlarmTrap is sent
                 when the distribute fiber is broken or OLT can not receive expected optical signals from ONT(LOSi).
                "
            ::= { hwXponDeviceOntAlarmTraps 0 12 }

        hwGponProfOntLOSRecoverAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntLOSRecoverAlarmTrap is sent
                 when the OLT can receive expected optical signals from ONT(LOSi) recovers.
                "
            ::= { hwXponDeviceOntAlarmTraps 0 13 }

        hwGponProfOntSUFAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntSUFAlarmTrap is sent
                 when the ranging of ONTi failure (SUFi) occurs.
                "
            ::= { hwXponDeviceOntAlarmTraps 0 14 }

        hwGponProfOntSUFRecoverAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntSUFRecoverAlarmTrap is sent
                 when the ranging of ONTi failure (SUFi) recovers.
                "
            ::= { hwXponDeviceOntAlarmTraps 0 15 }

        hwGponProfOntLOAAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntLOAAlarmTrap is sent
                 when the loss of acknowledgement PLOAM message with ONTi (LOAi) occurs.
                "
            ::= { hwXponDeviceOntAlarmTraps 0 16 }

        hwGponProfOntLOARecoverAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntLOARecoverAlarmTrap is sent
                 when the loss of acknowledgement PLOAM message with ONTi (LOAi) recovers."
            ::= { hwXponDeviceOntAlarmTraps 0 17 }

        hwGponProfOntDGAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntDGAlarmTrap is sent
                 when the dying-gasp of ONTi (DGi) is generated.
                "
            ::= { hwXponDeviceOntAlarmTraps 0 18 }

        hwGponProfOntDGRecoverAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntDGRecoverAlarmTrap is sent
                 when the dying-gasp of ONTi (DGi) recovers.
                "
            ::= { hwXponDeviceOntAlarmTraps 0 19 }

        hwGponProfOntLOAMAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntLOAMAlarmTrap is sent
                 when the loss of PLOAM of ONTi (LOAMi) occurs.
                "
            ::= { hwXponDeviceOntAlarmTraps 0 20 }

        hwGponProfOntLOAMRecoverAlarmTrap NOTIFICATION-TYPE
            OBJECTS {
                hwFrameIndex,
                hwSlotIndex,
                hwPortIndex,
                hwGponDeviceOntIndex,
                hwGponDeviceOntEquipmentId
            }
            STATUS current
            DESCRIPTION
                "The hwGponProfOntLOAMRecoverAlarmTrap is sent
                 when the loss of PLOAM of ONTi (LOAMi) recovers.
                "
            ::= { hwXponDeviceOntAlarmTraps 0 21 }

        hwGponProfOntPEEAlarmTrap NOTIFICATION-TYPE
            OBJECTS {
                hwFrameIndex,
                hwSlotIndex,
                hwPortIndex,
                hwGponDeviceOntIndex
            }
            STATUS current
            DESCRIPTION
                "The hwGponProfOntPEEAlarmTrap is sent
                 when the physical equipment error of ONTi (PEEi) occurs.
                "
            ::= { hwXponDeviceOntAlarmTraps 0 24 }

        hwGponProfOntPEERecoverAlarmTrap NOTIFICATION-TYPE
            OBJECTS {
                hwFrameIndex,
                hwSlotIndex,
                hwPortIndex,
                hwGponDeviceOntIndex
            }
            STATUS current
            DESCRIPTION
                "The hwGponProfOntPEERecoverAlarmTrap is sent
                 when the physical equipment error of ONTi (PEEi) recovers.
                "
            ::= { hwXponDeviceOntAlarmTraps 0 25 }

        hwGponProfOntConfigRecoveryFailAlarmTrap NOTIFICATION-TYPE
            OBJECTS {
                hwFrameIndex,
                hwSlotIndex,
                hwPortIndex,
                hwGponDeviceOntIndex
            }
            STATUS current
            DESCRIPTION
                "The hwGponProfOntConfigRecoveryFailAlarmTrap is sent
                 when the GPON ONT configuration recovery fails.
                "
            ::= { hwXponDeviceOntAlarmTraps 0 26 }

        hwGponProfOntConfigRecoverySuccAlarmTrap NOTIFICATION-TYPE
            OBJECTS {
                hwFrameIndex,
                hwSlotIndex,
                hwPortIndex,
                hwGponDeviceOntIndex
            }
            STATUS current
            DESCRIPTION
                "The hwGponProfOntConfigRecoverySuccAlarmTrap is sent
                 when the GPON ONT configuration recovery is successful.
                "
            ::= { hwXponDeviceOntAlarmTraps 0 27 }

        hwGponProfOntAuthInfoConflictAlarmTrap NOTIFICATION-TYPE
            OBJECTS {
                hwFrameIndex,
                hwSlotIndex,
                hwPortIndex,
                hwGponDeviceOntIndex
            }
            STATUS current
            DESCRIPTION
                "The hwGponProfOntAuthInfoConflictAlarmTrap is sent
                 when the authentication information of the ONT is invalid.
                "
            ::= { hwXponDeviceOntAlarmTraps 0 29 }

        hwGponProfOntResetByWatchdogAlarmTrap NOTIFICATION-TYPE
            OBJECTS {
                hwFrameIndex,
                hwSlotIndex,
                hwPortIndex,
                hwGponDeviceOntIndex
            }
            STATUS current
            DESCRIPTION
                "The hwGponProfOntResetByWatchdogAlarmTrap is sent
                 when the ONT is reset by watchdog and gets online again.
                "
            ::= { hwXponDeviceOntAlarmTraps 0 30 }

        hwGponProfOntSoftwareUpgradeSuccAlarmTrap NOTIFICATION-TYPE
            OBJECTS {
                hwFrameIndex,
                hwSlotIndex,
                hwPortIndex,
                hwGponDeviceOntIndex
            }
            STATUS current
            DESCRIPTION
                "This trap is sent when the GPON ONT software upgrade is successful."
            ::= { hwXponDeviceOntAlarmTraps 0 31 }

        hwGponProfOntSoftwareUpgradeFailAlarmTrap NOTIFICATION-TYPE
            OBJECTS {
                hwFrameIndex,
                hwSlotIndex,
                hwPortIndex,
                hwGponDeviceOntIndex
            }
            STATUS current
            DESCRIPTION
                "This trap is sent when the GPON ONT software upgrade fails."
            ::= { hwXponDeviceOntAlarmTraps 0 32 }

        hwXponProfOntHardwareFaultyAlarmTrap NOTIFICATION-TYPE
            OBJECTS {
                hwFrameIndex,
                hwSlotIndex,
                hwPortIndex,
                hwXponDeviceOntIndex
            }
            STATUS current
            DESCRIPTION
                "This trap is sent when the hardware of the ONT is faulty."
            ::= { hwXponDeviceOntAlarmTraps 0 33 }

        hwXponProfOntHardwareFaultRecoverAlarmTrap NOTIFICATION-TYPE
            OBJECTS {
                hwFrameIndex,
                hwSlotIndex,
                hwPortIndex,
                hwXponDeviceOntIndex
            }
            STATUS current
            DESCRIPTION
                "This trap is sent when the ONT recovers from the fault of hardware."
            ::= { hwXponDeviceOntAlarmTraps 0 34 }

        hwGponProfOntSwitchToStandbybatteryAlarmTrap NOTIFICATION-TYPE
            OBJECTS {
                hwFrameIndex,
                hwSlotIndex,
                hwPortIndex,
                hwGponDeviceOntIndex
            }
            STATUS current
            DESCRIPTION
                "This trap is sent when the ONT switches to the standby battery."
            ::= { hwXponDeviceOntAlarmTraps 0 35 }

        hwGponProfOntExternalPowerSupplyRecoverAlarmTrap NOTIFICATION-TYPE
            OBJECTS {
                hwFrameIndex,
                hwSlotIndex,
                hwPortIndex,
                hwGponDeviceOntIndex
            }
            STATUS current
            DESCRIPTION
                "This trap is sent when the external power supply of the ONT recovers."
            ::= { hwXponDeviceOntAlarmTraps 0 36 }

        hwXponProfOntStandbyBatteryLostAlarmTrap NOTIFICATION-TYPE
            OBJECTS {
                hwFrameIndex,
                hwSlotIndex,
                hwPortIndex,
                hwXponDeviceOntIndex
            }
            STATUS current
            DESCRIPTION
                "This trap is sent when the standby battery of the ONT is lost."
            ::= { hwXponDeviceOntAlarmTraps 0 37 }

        hwXponProfOntLossOfStandbyBatteryRecoverAlarmTrap NOTIFICATION-TYPE
            OBJECTS {
                hwFrameIndex,
                hwSlotIndex,
                hwPortIndex,
                hwXponDeviceOntIndex
            }
            STATUS current
            DESCRIPTION
                "This trap is sent when the ONT recovers from the loss of standby battery."
            ::= { hwXponDeviceOntAlarmTraps 0 38 }

        hwXponProfOntStandbyBatteryCannotChargedAlarmTrap NOTIFICATION-TYPE
            OBJECTS {
            hwFrameIndex,
            hwSlotIndex,
            hwPortIndex,
            hwXponDeviceOntIndex
            }
            STATUS current
            DESCRIPTION
                "This trap is sent when the standby battery of the ONT cannot be charged."
            ::= { hwXponDeviceOntAlarmTraps 0 39 }

        hwXponProfOntStandbyBatteryRecoverAlarmTrap NOTIFICATION-TYPE
            OBJECTS {
            hwFrameIndex,
            hwSlotIndex,
            hwPortIndex,
            hwXponDeviceOntIndex
            }
            STATUS current
            DESCRIPTION
                "This trap is sent when the standby battery of the ONT recovers."
            ::= { hwXponDeviceOntAlarmTraps 0 40 }

        hwXponProfOntVoltageOfStandbyBatteryTooLowAlarmTrap NOTIFICATION-TYPE
            OBJECTS {
                hwFrameIndex,
                hwSlotIndex,
                hwPortIndex,
                hwXponDeviceOntIndex
            }
            STATUS current
            DESCRIPTION
                "This trap is sent when the voltage of the standby battery of the ONT is too low."
            ::= { hwXponDeviceOntAlarmTraps 0 41 }

        hwXponProfOntVoltageOfStandbyBatteryRecoverAlarmTrap NOTIFICATION-TYPE
            OBJECTS {
                hwFrameIndex,
                hwSlotIndex,
                hwPortIndex,
                hwXponDeviceOntIndex
            }
            STATUS current
            DESCRIPTION
                "This trap is sent when the voltage of the standby battery of the ONT recovers."
            ::= { hwXponDeviceOntAlarmTraps 0 42 }

        hwGponProfOntShellOpenedAlarmTrap NOTIFICATION-TYPE
            OBJECTS {
                hwFrameIndex,
                hwSlotIndex,
                hwPortIndex,
                hwGponDeviceOntIndex
            }
            STATUS current
            DESCRIPTION
                "This trap is sent when the shell of the ONT is opened."
            ::= { hwXponDeviceOntAlarmTraps 0 43 }

        hwGponProfOntShellClosedAlarmTrap NOTIFICATION-TYPE
            OBJECTS {
                hwFrameIndex,
                hwSlotIndex,
                hwPortIndex,
                hwGponDeviceOntIndex
            }
            STATUS current
            DESCRIPTION
                "This trap is sent when the shell of the ONT is closed."
            ::= { hwXponDeviceOntAlarmTraps 0 44 }

        hwXponNumerousOntsPowerOffAlarmTrap NOTIFICATION-TYPE
            OBJECTS {
                hwFrameIndex,
                hwSlotIndex,
                hwPortIndex,
                hwXponOntMask
            }
            STATUS current
            DESCRIPTION
                "This trap is sent when the numerous ONTs are powered off in one district."
            ::= { hwXponDeviceOntAlarmTraps 0 45 }

        hwXponProfOntIsRogueOntAlarmTrap NOTIFICATION-TYPE
            OBJECTS {
                hwFrameIndex,
                hwSlotIndex,
                hwPortIndex,
                hwXponDeviceOntIndex
            }
            STATUS current
            DESCRIPTION
                "This trap is sent when the ONT is rogue ONT."
            ::= { hwXponDeviceOntAlarmTraps 0 46 }

        hwXponProfRogueOntDisapearAlarmTrap NOTIFICATION-TYPE
            OBJECTS {
                hwFrameIndex,
                hwSlotIndex,
                hwPortIndex,
                hwXponDeviceOntIndex
            }
            STATUS current
            DESCRIPTION
                "This trap is sent when the rogue ONT disappears."
            ::= { hwXponDeviceOntAlarmTraps 0 47 }

        hwXponProfLocalOpticalModuleExceedAlarmThresAlarmTrap NOTIFICATION-TYPE
            OBJECTS {
                hwFrameIndex,
                hwSlotIndex,
                hwPortIndex,
                hwXponDeviceOntIndex,
                hwXponProfOntOpticalMoudleAlarmType,
                hwXponProfOntOpticalMoudleAlarmUpperValue,
                hwXponProfOntOpticalMoudleAlarmLowerValue,
                hwXponProfOntOpticalMoudleAlarmCurrentValue
            }
            STATUS current
            DESCRIPTION
                "This trap is sent when the local optical transceiver parameters exceed alarm threshold."
            ::= { hwXponDeviceOntAlarmTraps 0 48 }

        hwXponProfLocalOpticalModuleRecoverAlarmThresAlarmTrap NOTIFICATION-TYPE
            OBJECTS {
                hwFrameIndex,
                hwSlotIndex,
                hwPortIndex,
                hwXponDeviceOntIndex,
                hwXponProfOntOpticalMoudleAlarmType,
                hwXponProfOntOpticalMoudleAlarmUpperValue,
                hwXponProfOntOpticalMoudleAlarmLowerValue,
                hwXponProfOntOpticalMoudleAlarmCurrentValue
            }
            STATUS current
            DESCRIPTION
                "This trap is sent when the local optical transceiver parameters exceed alarm threshold recover."
            ::= { hwXponDeviceOntAlarmTraps 0 49 }

        hwXponProfRemoteOpticalModuleExceedAlarmThresAlarmTrap NOTIFICATION-TYPE
            OBJECTS {
                hwFrameIndex,
                hwSlotIndex,
                hwPortIndex,
                hwXponDeviceOntIndex,
                hwXponProfOntOpticalMoudleAlarmType,
                hwXponProfOntOpticalMoudleAlarmUpperValue,
                hwXponProfOntOpticalMoudleAlarmLowerValue,
                hwXponProfOntOpticalMoudleAlarmCurrentValue
            }
            STATUS current
            DESCRIPTION
                "This trap is sent when the remote optical transceiver parameters exceed alarm threshold."
            ::= { hwXponDeviceOntAlarmTraps 0 50 }

        hwXponProfRemoteOpticalModuleRecoverAlarmThresAlarmTrap NOTIFICATION-TYPE
            OBJECTS {
                hwFrameIndex,
                hwSlotIndex,
                hwPortIndex,
                hwXponDeviceOntIndex,
                hwXponProfOntOpticalMoudleAlarmType,
                hwXponProfOntOpticalMoudleAlarmUpperValue,
                hwXponProfOntOpticalMoudleAlarmLowerValue,
                hwXponProfOntOpticalMoudleAlarmCurrentValue
            }
            STATUS current
            DESCRIPTION
                "This trap is sent when the remote optical transceiver parameters exceed alarm threshold recover."
            ::= { hwXponDeviceOntAlarmTraps 0 51 }

        hwXponProfLocalOpticalModuleExceedWarnThresAlarmTrap NOTIFICATION-TYPE
            OBJECTS {
                hwFrameIndex,
                hwSlotIndex,
                hwPortIndex,
                hwXponDeviceOntIndex,
                hwXponProfOntOpticalMoudleAlarmType,
                hwXponProfOntOpticalMoudleAlarmUpperValue,
                hwXponProfOntOpticalMoudleAlarmLowerValue,
                hwXponProfOntOpticalMoudleAlarmCurrentValue
            }
            STATUS current
            DESCRIPTION
                "This trap is sent when the local optical transceiver parameters exceed warning threshold."
            ::= { hwXponDeviceOntAlarmTraps 0 52 }

        hwXponProfLocalOpticalModuleRecoverWarnThresAlarmTrap NOTIFICATION-TYPE
            OBJECTS {
                hwFrameIndex,
                hwSlotIndex,
                hwPortIndex,
                hwXponDeviceOntIndex,
                hwXponProfOntOpticalMoudleAlarmType,
                hwXponProfOntOpticalMoudleAlarmUpperValue,
                hwXponProfOntOpticalMoudleAlarmLowerValue,
                hwXponProfOntOpticalMoudleAlarmCurrentValue
            }
            STATUS current
            DESCRIPTION
                "This trap is sent when the local optical transceiver parameters exceed warning threshold recover."
            ::= { hwXponDeviceOntAlarmTraps 0 53 }

        hwXponProfRemoteOpticalModuleExceedWarnThresAlarmTrap NOTIFICATION-TYPE
            OBJECTS {
                hwFrameIndex,
                hwSlotIndex,
                hwPortIndex,
                hwXponDeviceOntIndex,
                hwXponProfOntOpticalMoudleAlarmType,
                hwXponProfOntOpticalMoudleAlarmUpperValue,
                hwXponProfOntOpticalMoudleAlarmLowerValue,
                hwXponProfOntOpticalMoudleAlarmCurrentValue
            }
            STATUS current
            DESCRIPTION
                "This trap is sent when the remote optical transceiver parameters exceed warning threshold."
            ::= { hwXponDeviceOntAlarmTraps 0 54 }

        hwXponProfRemoteOpticalModuleRecoverWarnThresAlarmTrap NOTIFICATION-TYPE
            OBJECTS {
                hwFrameIndex,
                hwSlotIndex,
                hwPortIndex,
                hwXponDeviceOntIndex,
                hwXponProfOntOpticalMoudleAlarmType,
                hwXponProfOntOpticalMoudleAlarmUpperValue,
                hwXponProfOntOpticalMoudleAlarmLowerValue,
                hwXponProfOntOpticalMoudleAlarmCurrentValue
            }
            STATUS current
            DESCRIPTION
                "This trap is sent when the remote optical transceiver parameters exceed warning threshold recover."
            ::= { hwXponDeviceOntAlarmTraps 0 55 }

        hwGponProfWorkingStateChangedInTypeBDualAlarmTrap NOTIFICATION-TYPE
            OBJECTS {
                hwFrameIndex,
                hwSlotIndex,
                hwPortIndex,
                hwGponProfOltDualparentWorkState
            }
            STATUS current
            DESCRIPTION
                "This trap is sent when the Working status of the port in a TYPE-B dual parenting protect group has changed."
            ::= { hwXponDeviceOntAlarmTraps 0 56 }

        hwGponProfOntE1T1PortStatusAbnormalAlarmTrap NOTIFICATION-TYPE
            OBJECTS {
                hwFrameIndex,
                hwSlotIndex,
                hwPortIndex,
                hwGponDeviceOntIndex,
                hwGponDeviceOntTDMPortId,
                hwGponProfOntTDMPortAlarmType
            }
            STATUS current
            DESCRIPTION
                "This trap is sent when the status of ONT's E1/T1 port is abnormal."
            ::= { hwXponDeviceOntAlarmTraps 0 81 }

        hwGponProfOntE1T1PortStatusRecoverAlarmTrap NOTIFICATION-TYPE
            OBJECTS {
                hwFrameIndex,
                hwSlotIndex,
                hwPortIndex,
                hwGponDeviceOntIndex,
                hwGponDeviceOntTDMPortId,
                hwGponProfOntTDMPortAlarmType
            }
            STATUS current
            DESCRIPTION
                "This trap is sent when the status of ONT's E1/T1 port recovers."
            ::= { hwXponDeviceOntAlarmTraps 0 82 }

        hwGponProfEthernetPortLossOfSignelOccurAlarmTrap NOTIFICATION-TYPE
            OBJECTS {
                hwFrameIndex,
                hwSlotIndex,
                hwPortIndex,
                hwGponDeviceOntIndex,
                hwGponDeviceOntEthernetPortId
            }
            STATUS current
            DESCRIPTION
                "This trap is sent when the loss of signals occurs on the ethernet port of the ONT."
            ::= { hwXponDeviceOntAlarmTraps 0 83 }

        hwGponProfEthernetPortLossRecoverAlarmTrap NOTIFICATION-TYPE
            OBJECTS {
                hwFrameIndex,
                hwSlotIndex,
                hwPortIndex,
                hwGponDeviceOntIndex,
                hwGponDeviceOntEthernetPortId
            }
            STATUS current
            DESCRIPTION
                "This trap is sent when the ethernet port of the ONT recovers from the loss of signals."
            ::= { hwXponDeviceOntAlarmTraps 0 84 }

        hwGponProfVideoUNINoSignalAlarmTrap NOTIFICATION-TYPE
            OBJECTS {
                hwFrameIndex,
                hwSlotIndex,
                hwPortIndex,
                hwGponDeviceOntIndex,
                hwGponDeviceOntCatvPortId
            }
            STATUS current
            DESCRIPTION
                "This trap is sent when no signal is received in the video UNI of the ONT."
            ::= { hwXponDeviceOntAlarmTraps 0 85 }

        hwGponProfVideoUNISignalRecoverAlarmTrap NOTIFICATION-TYPE
            OBJECTS {
                hwFrameIndex,
                hwSlotIndex,
                hwPortIndex,
                hwGponDeviceOntIndex,
                hwGponDeviceOntCatvPortId
            }
            STATUS current
            DESCRIPTION
                "This trap is sent when the video UNI of the ONT recovers from the loss of signals."
            ::= { hwXponDeviceOntAlarmTraps 0 86 }

        hwGponProfE1T1PortLOSOccurAlarmTrap NOTIFICATION-TYPE
            OBJECTS {
                hwFrameIndex,
                hwSlotIndex,
                hwPortIndex,
                hwGponDeviceOntIndex,
                hwGponDeviceOntTDMPortId
            }
            STATUS current
            DESCRIPTION
                "This trap is sent when the E1/T1 port loss of signal (LOS) occurs at the ONT."
            ::= { hwXponDeviceOntAlarmTraps 0 87 }

        hwGponProfE1T1PortRecoverFromLOSAlarmTrap NOTIFICATION-TYPE
            OBJECTS {
                hwFrameIndex,
                hwSlotIndex,
                hwPortIndex,
                hwGponDeviceOntIndex,
                hwGponDeviceOntTDMPortId
            }
            STATUS current
            DESCRIPTION
                "This trap is sent when the E1/T1 port of the ONT recovers from loss of signal (LOS)."
            ::= { hwXponDeviceOntAlarmTraps 0 88 }

     -- ONT AND ONT PORT ALARM
        hwEponProfOntAuthInfoInvalidAlarmTrap NOTIFICATION-TYPE
            OBJECTS {
                hwFrameIndex,
                hwSlotIndex,
                hwPortIndex,
                hwEponDeviceOntIndex
            }
            STATUS current
            DESCRIPTION
                "This trap is sent when the authorization information of ONT is invalid."
            ::= { hwXponDeviceOntAlarmTraps 0 251 }

        hwEponProfOntDiscoveredAlarmTrap NOTIFICATION-TYPE
            OBJECTS {
                hwFrameIndex,
                hwSlotIndex,
                hwPortIndex,
                hwEponDeviceAutoFindOntInfoMacAddress,
                hwEponDeviceAutoFindOntInfoPasswordValue,
                hwEponDeviceAutoFindOntInfoLoid,
                hwEponDeviceAutoFindOntInfoCheckcode
            }
            STATUS current
            DESCRIPTION
                "This trap is sent when the EPON ONT is discovered by the OLT."
            ::= { hwXponDeviceOntAlarmTraps 0 252 }

        hwEponProfOntDiscoveredDeletedAlarmTrap NOTIFICATION-TYPE
            OBJECTS {
                hwFrameIndex,
                hwSlotIndex,
                hwPortIndex,
                hwEponDeviceAutoFindOntInfoMacAddress,
                hwEponDeviceAutoFindOntInfoPasswordValue,
                hwEponDeviceAutoFindOntInfoLoid,
                hwEponDeviceAutoFindOntInfoCheckcode
            }
            STATUS current
            DESCRIPTION
                "This trap is sent when the discovered EPON ONT is deleted."
            ::= { hwXponDeviceOntAlarmTraps 0 253 }

        hwEponProfOntConfigRecoveryFailAlarmTrap NOTIFICATION-TYPE
            OBJECTS {
                hwFrameIndex,
                hwSlotIndex,
                hwPortIndex,
                hwEponDeviceOntIndex
            }
            STATUS current
            DESCRIPTION
                "This trap is sent when the EPON ONT configuration recovery fails."
            ::= { hwXponDeviceOntAlarmTraps 0 254 }

        hwEponProfOntConfigRecoverySuccAlarmTrap NOTIFICATION-TYPE
            OBJECTS {
                hwFrameIndex,
                hwSlotIndex,
                hwPortIndex,
                hwEponDeviceOntIndex
            }
            STATUS current
            DESCRIPTION
                "This trap is sent when the EPON ONT configuration recovery is successful."
            ::= { hwXponDeviceOntAlarmTraps 0 255 }

        hwEponProfOntOpticalPathQualityPoorAlarmTrap NOTIFICATION-TYPE
            OBJECTS {
                hwFrameIndex,
                hwSlotIndex,
                hwPortIndex,
                hwEponDeviceOntIndex
            }
            STATUS current
            DESCRIPTION
                "This trap is sent when the quality of the ONT optical path is poor."
            ::= { hwXponDeviceOntAlarmTraps 0 256 }

        hwEponProfOntOpticalPathQualityRecoverAlarmTrap NOTIFICATION-TYPE
            OBJECTS {
                hwFrameIndex,
                hwSlotIndex,
                hwPortIndex,
                hwEponDeviceOntIndex
            }
            STATUS current
            DESCRIPTION
                "This trap is sent when the quality of the ONT optical path Recovers."
            ::= { hwXponDeviceOntAlarmTraps 0 257 }

        hwEponProfOntLOSAlarmTrap NOTIFICATION-TYPE
            OBJECTS {
                hwFrameIndex,
                hwSlotIndex,
                hwPortIndex,
                hwEponDeviceOntIndex,
                hwEponDeviceOntHardwareVersion
            }
            STATUS current
            DESCRIPTION
                "This trap is sent when the distribute fiber is broken or OLT can not receive expected
                 optical signals from ONT(LOSi).
                "
            ::= { hwXponDeviceOntAlarmTraps 0 258 }

        hwEponProfOntLOSRecoverAlarmTrap NOTIFICATION-TYPE
            OBJECTS {
                hwFrameIndex,
                hwSlotIndex,
                hwPortIndex,
                hwEponDeviceOntIndex,
                hwEponDeviceOntHardwareVersion
            }
            STATUS current
            DESCRIPTION
                "This trap is sent when the OLT can receive expected optical signals from ONT(LOSi recovers)."
            ::= { hwXponDeviceOntAlarmTraps 0 259 }

        hwEponProfOntKeyExchangeFailAlarmTrap NOTIFICATION-TYPE
            OBJECTS {
                hwFrameIndex,
                hwSlotIndex,
                hwPortIndex,
                hwEponDeviceOntIndex
            }
            STATUS current
            DESCRIPTION
                "This trap is sent when the key exchange fails."
            ::= { hwXponDeviceOntAlarmTraps 0 260 }

        hwEponProfOntSoftwareUpgradeSuccAlarmTrap NOTIFICATION-TYPE
            OBJECTS {
                hwFrameIndex,
                hwSlotIndex,
                hwPortIndex,
                hwEponDeviceOntIndex
            }
            STATUS current
            DESCRIPTION
                "This trap is sent when the EPON ONT software upgrade is successful."
            ::= { hwXponDeviceOntAlarmTraps 0 261 }

        hwEponProfOntSoftwareUpgradeFailAlarmTrap NOTIFICATION-TYPE
            OBJECTS {
                hwFrameIndex,
                hwSlotIndex,
                hwPortIndex,
                hwEponDeviceOntIndex
            }
            STATUS current
            DESCRIPTION
                "This trap is sent when the EPON ONT software upgrade fails."
            ::= { hwXponDeviceOntAlarmTraps 0 262 }

        hwEponProfOntDGAlarmTrap NOTIFICATION-TYPE
            OBJECTS {
                hwFrameIndex,
                hwSlotIndex,
                hwPortIndex,
                hwEponDeviceOntIndex,
                hwEponDeviceOntHardwareVersion
            }
            STATUS current
            DESCRIPTION
                "This trap is sent when the dying-gasp of ONTi (DGi) occurs."
            ::= { hwXponDeviceOntAlarmTraps 0 263 }

        hwEponProfOntDGRecoverAlarmTrap NOTIFICATION-TYPE
            OBJECTS {
                hwFrameIndex,
                hwSlotIndex,
                hwPortIndex,
                hwEponDeviceOntIndex,
                hwEponDeviceOntHardwareVersion
            }
            STATUS current
            DESCRIPTION
                "This trap is sent when the dying-gasp of ONTi (DGi) recovers."
            ::= { hwXponDeviceOntAlarmTraps 0 264 }

        hwEponProfOntVoltageOfExternalPowerAbnormalAlarmTrap NOTIFICATION-TYPE
            OBJECTS {
                hwFrameIndex,
                hwSlotIndex,
                hwPortIndex,
                hwEponDeviceOntIndex,
                hwEponDeviceOntVoltageState
            }
            STATUS current
            DESCRIPTION
                "This trap is sent when the voltage of ONT's external power is abnormal."
            ::= { hwXponDeviceOntAlarmTraps 0 265 }

        hwEponProfOntVoltageOfExternalPowerRecoverAlarmTrap NOTIFICATION-TYPE
            OBJECTS {
                hwFrameIndex,
                hwSlotIndex,
                hwPortIndex,
                hwEponDeviceOntIndex,
                hwEponDeviceOntVoltageState
            }
            STATUS current
            DESCRIPTION
                "This trap is sent when the voltage of the external power of the ONT recovers."
            ::= { hwXponDeviceOntAlarmTraps 0 266 }

        hwEponProfOntEtherPortBlockModeAlarmTrap NOTIFICATION-TYPE
            OBJECTS {
                hwFrameIndex,
                hwSlotIndex,
                hwPortIndex,
                hwEponDeviceOntIndex,
                hwEponDeviceOntEthernetPortId
            }
            STATUS current
            DESCRIPTION
                "This trap is sent when the ONT ethernet port enters block mode."
            ::= { hwXponDeviceOntAlarmTraps 0 267 }


        hwEponProfOntEtherPortForwardingModeAlarmTrap NOTIFICATION-TYPE
            OBJECTS {
                hwFrameIndex,
                hwSlotIndex,
                hwPortIndex,
                hwEponDeviceOntIndex,
                hwEponDeviceOntEthernetPortId
            }
            STATUS current
            DESCRIPTION
                "This trap is sent when the ONT ethernet port enters forwarding mode."
            ::= { hwXponDeviceOntAlarmTraps 0 268 }
            
        hwEponOntStatisticsExceedAlarmThresholdFaultAlarmTrap NOTIFICATION-TYPE
            OBJECTS {
                hwFrameIndex,
                hwSlotIndex,
                hwPortIndex,
                hwEponDeviceOntIndex,
                hwEponAlarmProfileStatisticsItem,
                hwEponAlarmProfileThresholdValue,
                hwEponAlarmProfileCurrentValue
            }
            STATUS current
            DESCRIPTION
                "The hwEponOntStatisticsExceedAlarmThresholdFaultAlarmTrap is sent
                 when the performance statistics value of the ONT exceeds the alarm threshold in the alarm profile bound to the port.
                "
            ::= { hwXponDeviceOntAlarmTraps 0 269 }
            
        hwEponOntStatisticsExceedAlarmThresholdRecoverAlarmTrap NOTIFICATION-TYPE
            OBJECTS {
                hwFrameIndex,
                hwSlotIndex,
                hwPortIndex,
                hwEponDeviceOntIndex,
                hwEponAlarmProfileStatisticsItem,
                hwEponAlarmProfileThresholdValue,
                hwEponAlarmProfileCurrentValue
            }
            STATUS current
            DESCRIPTION
                "The hwEponOntStatisticsExceedAlarmThresholdRecoverAlarmTrap is sent
                 when the performance statistics value of the ONT is within the alarm threshold range in the alarm profile bound to the port.
                "
            ::= { hwXponDeviceOntAlarmTraps 0 270 }
        
        hwEponOntStatisticsExceedWarningThresholdFaultAlarmTrap NOTIFICATION-TYPE
            OBJECTS {
                hwFrameIndex,
                hwSlotIndex,
                hwPortIndex,
                hwEponDeviceOntIndex,
                hwEponAlarmProfileStatisticsItem,
                hwEponAlarmProfileThresholdValue,
                hwEponAlarmProfileCurrentValue
            }
            STATUS current
            DESCRIPTION
                "The hwEponOntStatisticsExceedWarningThresholdFaultAlarmTrap is sent
                 when the performance statistics value of the ONT exceeds the warning threshold in the alarm profile bound to the port.
                "
            ::= { hwXponDeviceOntAlarmTraps 0 271 }
            
        hwEponOntStatisticsExceedWarningThresholdRecoverAlarmTrap NOTIFICATION-TYPE
            OBJECTS {
                hwFrameIndex,
                hwSlotIndex,
                hwPortIndex,
                hwEponDeviceOntIndex,
                hwEponAlarmProfileStatisticsItem,
                hwEponAlarmProfileThresholdValue,
                hwEponAlarmProfileCurrentValue
            }
            STATUS current
            DESCRIPTION
                "The hwEponOntStatisticsExceedWarningThresholdRecoverAlarmTrap is sent
                 when the performance statistics value of the ONT is within the warning threshold range in the alarm profile bound to the port.
                "
            ::= { hwXponDeviceOntAlarmTraps 0 272 }
            
        hwGponProfTypeBDParentRogueOntDetectTrap NOTIFICATION-TYPE
            OBJECTS {
                hwReservedValue,
                ifIndex
            }
            STATUS current
            DESCRIPTION
                "This trap is sent when the member port of the type B dual-homing
                 protection group completes the rogue ONT detection.
                "
            ::= { hwXponDeviceCommonTraps 0 1 }

        hwGponProfOntAutoFindTrap NOTIFICATION-TYPE
            OBJECTS {
                hwReservedValue,
                hwXponTrapOperType,
                hwFrameIndex,
                hwSlotIndex,
                hwPortIndex,
                hwGponDeviceAutoFindOntInfoSn,
                hwGponDeviceAutoFindOntInfoPassword,
                hwGponDeviceAutoFindOntInfoOntVendorId,
                hwGponDeviceAutoFindOntInfoOntVer,
                hwGponDeviceAutoFindOntInfoOntMainSoftVer,
                hwGponDeviceAutoFindOntInfoOntEquipmentId,
                hwGponDeviceAutoFindOntInfoLoid,
                hwGponDeviceAutoFindOntInfoCheckcode,
                hwGponDeviceAutoFindOntInfoCustomizedInfo,
                hwGponDeviceAutoFindOntInfoOntNniType
            }
            STATUS current
            DESCRIPTION
                "This trap is sent when the ONT reports the ONT type and version information
                 during the ONT automatic discovery.
                "
            ::= { hwXponDeviceCommonTraps 0 2 }

        hwGponProfOntVersionTrap NOTIFICATION-TYPE
            OBJECTS {
                hwReservedValue,
                hwXponTrapOperType,
                ifIndex,
                hwGponDeviceOntIndex,
                hwXponDeviceOntCRCSupport,
                hwXponDeviceOntCRCCode,
                hwGponDeviceOntVendorId,
                hwGponDeviceOntEquipmentId,
                hwGponDeviceOntMainSoftVer,
                hwGponProfOntDualUpstreamSupport,
                hwGponDeviceOntPGMemberRole,
                hwGponDeviceOntSoftwareWorkMode,
                hwGponDeviceProfOntIsOntUpfromReset,
                hwXponOntInfoSupportXmlVersion,
                hwXponOntFirstOnline,
                hwXponOntSupportVoipCfgMethod,
                hwGponDeviceOntVoipCfgFileVersion,
                hwGponDeviceOntCustomizedInfo
            }
            STATUS current
            DESCRIPTION
                "This trap is sent when the GPON terminal goes online."
            ::= { hwXponDeviceCommonTraps 0 3 }

        hwGponProfOntDiscoveryStateTrap NOTIFICATION-TYPE
            OBJECTS {
                hwConfigChangeIP,
                hwXponTrapOperType,
                ifIndex,
                hwGponDeviceOntIndex,
                hwGponDeviceOntControlDiscoveryStatus
            }
            STATUS current
            DESCRIPTION
                "This trap is sent when the discovery status of the ONT changes."
            ::= { hwXponDeviceCommonTraps 0 4 }

        hwEponProfOntAutoFindTrap NOTIFICATION-TYPE
            OBJECTS {
                hwReservedValue,
                hwXponTrapOperType,
                hwFrameIndex,
                hwSlotIndex,
                hwPortIndex,
                hwEponDeviceAutoFindOntInfoMacAddress,
                hwEponDeviceAutoFindOntInfoPasswordValue,
                hwEponDeviceAutoFindOntInfoVendorId,
                hwEponDeviceAutoFindOntInfoOntModel,
                hwEponDeviceAutoFindOntInfoSoftwareVersion,
                hwEponDeviceAutoFindOntInfoGeNumber,
                hwEponDeviceAutoFindOntInfoFeNumber,
                hwEponDeviceAutoFindOntInfoPotsNumber,
                hwEponDeviceAutoFindOntInfoTdmNumber,
                hwEponDeviceAutoFindOntInfoHardwareVersion,
                hwEponDeviceAutoFindOntInfoLoid,
                hwEponDeviceAutoFindOntInfoCheckcode,
                hwEponDeviceAutoFindOntNniType,
                hwEponDeviceAutoFindOntInfoOntExtendedModel,
                hwEponDeviceAutoFindOntInfoOuiVersion,
                hwEponDeviceAutoFindOntInfoCustomizedInfo
            }
            STATUS current
            DESCRIPTION
                "This trap is sent when the ONT type and capability in the ONT automatic discovery."
            ::= { hwXponDeviceCommonTraps 0 50 }

        hwXponProfOntPortStatusTrap NOTIFICATION-TYPE
            OBJECTS {
                hwReservedValue,
                hwXponTrapOperType,
                ifIndex,
                hwXponDeviceOntIndex,
                hwXponOntUniPhyType,
                hwXponOntUniPhyIndex,
                hwXponDeviceOntPortRunStatus
            }
            STATUS current
            DESCRIPTION
                "This trap is sent when the status of the ONT port changes."
            ::= { hwXponDeviceCommonTraps 0 51 }
            
        hwEponProfOntUpVersionTrap NOTIFICATION-TYPE
            OBJECTS {
                hwReservedValue,
                hwXponTrapOperType,
                ifIndex,
                hwEponDeviceOntIndex,
                hwXponDeviceOntCRCSupport,
                hwXponDeviceOntCRCCode,
                hwEponDeviceOntVendorId,
                hwEponDeviceOntEquipmentId,
                hwEponDeviceOntSoftwareVersion,
                hwEponDeviceOntTypeDSupport,
                hwEponDeviceOntPGMemberRole,
                hwEponDeviceOntSoftwareWorkMode,
                hwEponDeviceOntIsOntUpfromReset,
                hwXponOntInfoSupportXmlVersion,
                hwXponOntFirstOnline,
                hwXponOntSupportVoipCfgMethod,
                hwEponDeviceAutoFindOntInfoOntExtendedModel,
                hwEponDeviceOntCustomizedInfo
            }
            STATUS current
            DESCRIPTION
                "This trap is sent when the EPON terminal goes online."
            ::= { hwXponDeviceCommonTraps 0 52 }            
            
        hwXponProfOntRunStateChangeTrap NOTIFICATION-TYPE
            OBJECTS {
                hwReservedValue,
                hwXponTrapOperType,
                ifIndex,
                hwXponDeviceOntIndex,
                hwXponDeviceOntRunStatus
            }
            STATUS current
            DESCRIPTION
                "This trap is sent when the ONT running state changed."
            ::= { hwXponDeviceCommonTraps 0 100 }

        hwXponProfOntLoadTrap NOTIFICATION-TYPE
            OBJECTS {
                hwReservedValue,
                hwXponOntLoadOperType,
                ifIndex,
                hwXponDeviceOntIndex,
                hwXponOntLoadFileType,
                hwXponOntLoadResult,
                hwXponOntLoadCrcSupport,
                hwXponOntLoadCrcValue
            }
            STATUS current
            DESCRIPTION
                "This trap is sent when the XPON ont load."
            ::= { hwXponDeviceCommonTraps 0 101 }

        hwXponUpLoadReportTrap NOTIFICATION-TYPE
            OBJECTS {
                hwReservedValue,
                hwXponOntLoadOperType,
                ifIndex,
                hwXponDeviceOntIndex,
                hwXponOntLoadCrcValue,
                hwXponOntLoadResult
            }
            STATUS current
            DESCRIPTION
                "This trap is sent when the ont file need transfer."
            ::= { hwXponDeviceCommonTraps 0 102 }

        hwEponProfTypeBDParentRogueOntDetectTrap NOTIFICATION-TYPE
            OBJECTS {
                hwReservedValue,
                ifIndex,
                hwEponRogueOntDetectOperStatus
            }
            STATUS current
            DESCRIPTION
                "This trap is sent when the member port of the type B dual-homing
                 protection group completes the rogue ONT detection.
                "
            ::= { hwXponDeviceCommonTraps 0 103 }

        hwEponConfigChangeOntDiscTrap NOTIFICATION-TYPE
            OBJECTS {
                hwConfigChangeIP,
                hwXponTrapOperType,
                ifIndex,
                hwEponDeviceOntIndex,
                hwEponDeviceOntDiscoveryState
            }
            STATUS current
            DESCRIPTION
                "This trap is sent when the discovery status of the ONT changes."
            ::= { hwXponDeviceCommonTraps 0 104 }

        hwEponConfigChangeOntPortAttrTrap NOTIFICATION-TYPE
            OBJECTS {
                hwConfigChangeIP,
                hwXponTrapOperType,
                ifIndex,
                hwEponDeviceOntIndex,
                hwEponDeviceOntPortType,
                hwEponDeviceOntPortId,
                hwEponDeviceOntPortManageStatus,
                hwEponDeviceOntEthernetNegotiate,
                hwEponDeviceOntEthernetDuplexMode,
                hwEponDeviceOntEthernetSpeed,
                hwEponDeviceOntEthernetFlowcontrolSwitch,
                hwEponDeviceOntEthernetPortCfgUpStreamCarTrafficTableId,
                hwEponDeviceOntEthernetPortCfgDownStreamCarTrafficTableId
            }
            STATUS current
            DESCRIPTION
                "This trap is sent when the attribute configuration of the EPON ONT port changes."
            ::= { hwXponDeviceCommonTraps 0 105 }

        hwXponConfigChangeSrvProfileTrap NOTIFICATION-TYPE
            OBJECTS {
                hwConfigChangeIP,
                hwXponTrapOperType,
                hwXponDeviceAccessType,
                hwXponDeviceServiceProfileName
            }
            STATUS current
            DESCRIPTION
                "This trap is sent when the configuration of the service profile changes."
            ::= { hwXponDeviceCommonTraps 0 106 }

        hwXponConfigChangeLineProfileTrap NOTIFICATION-TYPE
            OBJECTS {
                hwConfigChangeIP,
                hwXponTrapOperType,
                hwXponDeviceAccessType,
                hwXponDeviceLineProfileName
            }
            STATUS current
            DESCRIPTION
                "This trap is sent when the configuration of the line profile changes."
            ::= { hwXponDeviceCommonTraps 0 107 }

        hwEponConfigChangeProfModeOntTrap NOTIFICATION-TYPE
            OBJECTS {
                hwConfigChangeIP,
                hwXponTrapOperType,
                ifIndex,
                hwEponDeviceOntIndex,
                hwEponDeviceOntAuthMode,
                hwEponDeviceOntMacAddress,
                hwEponDeviceOntPassword,
                hwEponDeviceAlarmProfileName,
                hwEponDeviceOntDespt,
                hwEponDeviceOntDbaStatus,
                hwEponDeviceOntTimeout,
                hwEponDeviceOntManagementMode,
                hwEponDeviceOntLineProfName,
                hwEponDeviceOntServiceProfName,
                hwEponDeviceOntCfgSnmpProfileName,
                hwEponDeviceOntLastDownTime,
                hwEponDeviceOntLastUpTime,
                hwEponDeviceOntLastDownCause,
                hwEponDeviceOntLastDyingGaspTime,
                hwEponDeviceOntObjectLoid,
                hwEponDeviceOntObjectCheckcode,
                hwEponDeviceOntNniType
            }
            STATUS current
            DESCRIPTION
                "This trap is sent when the configuration of the EPON ONT changes."
            ::= { hwXponDeviceCommonTraps 0 108 }

        hwGponConfigChangeProfModeOntTrap NOTIFICATION-TYPE
            OBJECTS {
                hwConfigChangeIP,
                hwXponTrapOperType,
                ifIndex,
                hwGponDeviceOntIndex,
                hwGponDeviceOntAuthMethod,
                hwGponDeviceOntSn,
                hwGponDeviceOntPassword,
                hwGponDeviceOntCfgAlarmProfileName,
                hwGponDeviceOntDespt,
                hwGponDeviceOntControlDbaStatus,
                hwGponDeviceOntTimeOut,
                hwGponDeviceOntManagementMode,
                hwGponDeviceOntLineProfName,
                hwGponDeviceOntServiceProfName,
                hwGponDeviceOntCfgSnmpProfileName,
                hwGponDeviceOntControlLastDownTime,
                hwGponDeviceOntControlLastUpTime,
                hwGponDeviceOntControlLastDownCause,
                hwGponDeviceOntControlLastDyingGaspTime,
                hwGponDeviceOntLoid,
                hwGponDeviceOntCheckcode,
                hwGponDeviceOntReregisterAuthMode,
                hwGponDeviceOntNniType
            }
            STATUS current
            DESCRIPTION
                "This trap is sent when the configuration of the GPON ONT in the profile mode changes."
            ::= { hwXponDeviceCommonTraps 0 109 }

        hwEponConfigOltTypeBDparenttTrap NOTIFICATION-TYPE
            OBJECTS {
                hwConfigChangeIP,
                ifIndex,
                hwXponDeviceOltDualparentJoin,
                hwXponDeviceOltDualparentFreeze,
                hwXponDeviceOltDualparentForceSwitch,
                hwXponDeviceOltDualparentWorkState,
                hwXponDeviceOltDualparentDesc
            }
            STATUS current
            DESCRIPTION
                "This trap is sent when the configuration of the EPON type B dual-homing protection group changes."
            ::= { hwXponDeviceCommonTraps 0 110 }

        hwEponConfigOntPortNativeVlanTrap NOTIFICATION-TYPE
            OBJECTS {
                hwConfigChangeIP,
                hwXponTrapOperType,
                ifIndex,
                hwEponDeviceOntIndex,
                hwEponDeviceOntPortType,
                hwEponDeviceOntPortId,
                hwEponDeviceOntEthernetVlanDefault
            }
            STATUS current
            DESCRIPTION
                "This trap is sent when the native VLAN configuration of the EPON ONT port changes."
            ::= { hwXponDeviceCommonTraps 0 111 }

        hwXponDeviceConfigChangeSnmpProfileTrap NOTIFICATION-TYPE
            OBJECTS {
                hwConfigChangeIP,
                hwXponTrapOperType,
                hwXponDeviceOntSnmpProfileInfoNameIndex,
                hwXponDeviceOntSnmpProfileVersion,
                hwXponDeviceOntSnmpProfileTrapHostIP,
                hwXponDeviceOntSnmpProfileTrapHostSrcUDPPort,
                hwXponDeviceOntSnmpProfileReadCommunityName,
                hwXponDeviceOntSnmpProfileWriteCommunityName,
                hwXponDeviceOntSnmpProfileSecurityName
            }
            STATUS current
            DESCRIPTION
                   "This trap is sent when the configuration of the SNMP profile is changed."
            ::= { hwXponDeviceCommonTraps 0 112 }

        hwEponConfigOntLlidDbaCarTrap NOTIFICATION-TYPE
            OBJECTS {
                hwConfigChangeIP,
                ifIndex,
                hwEponDeviceOntIndex,
                hwEponDeviceOntLlidIndex,
                hwEponDeviceOntLlidDbaProfileName,
                hwEponDeviceOntLlidCarTrafficTableId
            }
            STATUS current
            DESCRIPTION
                "This trap is sent when the EPON ONT LLID dba profile and car profile config changes."
            ::= { hwXponDeviceCommonTraps 0 113 }

        hwEponConfigOntPortVlanTrap NOTIFICATION-TYPE
            OBJECTS {
                hwConfigChangeIP,
                hwXponTrapOperType,
                ifIndex,
                hwEponDeviceOntIndex,
                hwEponOntPortVlanCfgOntPhyType,
                hwEponOntPortVlanCfgOntPhyIndex,
                hwEponOntPortVlanCfgCVlan,
                hwEponOntPortVlanCfgSVlan,
                hwEponOntPortVlanCfgType
            }
            STATUS current
            DESCRIPTION
                "This trap is sent when the EPON ONT port vlan config changes."
            ::= { hwXponDeviceCommonTraps 0 114 }

        hwXponProfOntPortLearnedHGInfoTrap NOTIFICATION-TYPE
           OBJECTS {
                ifIndex,
                hwXponDeviceOntIndex,
                hwXponOntUniPhyType,
                hwXponOntUniPhyIndex,
                hwXponProfOntPortLearnedHGVlan,
                hwXponProfOntPortLearnedHGMacAddr
            }
            STATUS current
            DESCRIPTION
                "This trap is sent when the VLAN and MAC address of the home
                 gateway are learned on the ONT port.
                "
            ::= { hwXponDeviceCommonTraps 0 115 }


     -- GPON Trap
        hwGponOntTDMPortAlarmType OBJECT-TYPE
            SYNTAX OCTET STRING (SIZE (0..50))
            MAX-ACCESS accessible-for-notify
            STATUS current
            DESCRIPTION
                "Alarm type. The values are as follows:
                 Transmit failure (TF),
                 Loss of frame (LOF),
                 Out of frame (OOF),
                 Remote alarm indication (RAI),
                 2.048 Mbit/s alarm indication signal (AIS).
                "
            ::= { hwGponTrapsVbOids 1 }

        hwGponOntMask OBJECT-TYPE
            SYNTAX OCTET STRING (SIZE (1..16))
            MAX-ACCESS accessible-for-notify
            STATUS current
            DESCRIPTION
                "ONT MASK."
            ::= { hwGponTrapsVbOids 2 }

        hwGponOntOpticalMoudleAlarmType OBJECT-TYPE
            SYNTAX INTEGER {
                rxPower(1),
                txPower(2),
                voltage(3),
                temperature(4),
                biasCurrent(5),
                catvRxPower(8)
            }
            MAX-ACCESS accessible-for-notify
            STATUS current
            DESCRIPTION
                "Alarm type.
                 Options:
                 1. rxPower(1)     - Alarm type is rxPower
                 2. txPower(2)     - Alarm type is txPower
                 3. voltage(3)     - Alarm type is voltage
                 4. temperature(4) - Alarm type is temperature
                 5. biasCurrent(5) - Alarm type is biasCurrent
                 6. catvRxPower(8) - Alarm type is catv rxPower
                "
            ::= { hwGponTrapsVbOids 3 }

        hwGponOntOpticalMoudleAlarmUpperValue OBJECT-TYPE
            SYNTAX OCTET STRING (SIZE (1..20))
            MAX-ACCESS accessible-for-notify
            STATUS current
            DESCRIPTION
                "Upper threshold(Value:-1024.00~1024.00)."
            ::= { hwGponTrapsVbOids 4 }

        hwGponOntOpticalMoudleAlarmLowerValue OBJECT-TYPE
            SYNTAX OCTET STRING (SIZE (1..20))
            MAX-ACCESS accessible-for-notify
            STATUS current
            DESCRIPTION
                "Lower threshold(Value:-1024.00~1024.00)."
            ::= { hwGponTrapsVbOids 5 }

        hwGponOntOpticalMoudleAlarmCurrentValue OBJECT-TYPE
            SYNTAX OCTET STRING (SIZE (1..20))
            MAX-ACCESS accessible-for-notify
            STATUS current
            DESCRIPTION
                "Current value(Value:-1024.00~1024.00)."
            ::= { hwGponTrapsVbOids 6 }

        hwGponTrapSerialNo OBJECT-TYPE
            SYNTAX Integer32
            MAX-ACCESS accessible-for-notify
            STATUS current
            DESCRIPTION
                "Serial number."
            ::= { hwGponTrapsVbOids 7 }

        hwGponTrapOperType OBJECT-TYPE
            SYNTAX INTEGER {
                add(1),
                modify(2),
                delete(3)
            }
            MAX-ACCESS accessible-for-notify
            STATUS current
            DESCRIPTION
                "Operation type.
                 Options:
                 1. add(1)    - Operation type is adding
                 2. modify(2) - Operation type is modifing
                 3. delete(3) - Operation type is deleting
                "
            ::= { hwGponTrapsVbOids 8 }

        hwGponOntLoadOperType OBJECT-TYPE
            SYNTAX INTEGER {
                loadProgress(1),
                configureApply(2)
                }
            MAX-ACCESS accessible-for-notify
            STATUS current
            DESCRIPTION
                "ONT load operation type.
                 Options:
                 1. loadProgress(1)   - ONT load operation type is loading Progress
                 2. configureApply(2) - ONT load operation type is configuring Apply
                "
            ::= { hwGponTrapsVbOids 9 }

        hwGponOntLoadResult OBJECT-TYPE
            SYNTAX INTEGER {
                 success(0),
                 fail(1),
                 load20Percent(2)
            }
            MAX-ACCESS accessible-for-notify
            STATUS current
            DESCRIPTION
                "ONT load result.
                 Options:
                 1. success(0)       - ONT load result is success
                 2. fail(1)          - ONT load result is fail
                 3. load20Percent(2) - ONT load result is loading 20 Percent
                "
            ::= { hwGponTrapsVbOids 10 }

        hwGponOntLoadCrcSupport OBJECT-TYPE
            SYNTAX INTEGER {
                noSupport(0),
                support(1),
                unconcern(255)
            }
            MAX-ACCESS accessible-for-notify
            STATUS current
            DESCRIPTION
                "Support state of ONT load CRC.
                 Options:
                 1. noSupport(0)   - Doesn't support state of ONT load CRC
                 2. support(1)     - Support state of ONT load CRC
                 3. unconcern(255) - Unconcern state of ONT load CRC
                "
            ::= { hwGponTrapsVbOids 11 }

        hwGponOntLoadCrcValue OBJECT-TYPE
            SYNTAX Integer32
            MAX-ACCESS accessible-for-notify
            STATUS current
            DESCRIPTION
                "ONT load CRC value."
            ::= { hwGponTrapsVbOids 12 }

        hwGponDeviceOntObjectCRCSupport OBJECT-TYPE
            SYNTAX INTEGER {
                noSupport(0),
                support(1)
            }
            MAX-ACCESS accessible-for-notify
            STATUS current
            DESCRIPTION
                "Support state of ONT CRC.
                 Options:
                 1. noSupport(0) - Doesn't support state of ONT CRC
                 2. support(1)   - Support state of ONT CRC
                "
            ::= { hwGponTrapsVbOids 13 }

        hwGponDeviceOntObjectCRCCode  OBJECT-TYPE
            SYNTAX Integer32
            MAX-ACCESS accessible-for-notify
            STATUS current
            DESCRIPTION
                "ONT CRC vlue.
                 The value (0) indicates that the query fails or ONT does not support it.
                "
            ::= { hwGponTrapsVbOids 14 }

        hwGponDeviceOntDualUpstreamSupport  OBJECT-TYPE
            SYNTAX INTEGER {
                support(1),
                notsupport(2),
                unknown(255)
            }
            MAX-ACCESS accessible-for-notify
            STATUS current
            DESCRIPTION
                "Indicate if ont support typeC.
                 Options:
                 1. support(1)    - Support typeC
                 2. notsupport(2) - Doesn't support typeC
                 3. unknown(255)  - Doesn't known if ont support typeC
                "
            ::= { hwGponTrapsVbOids 15 }

        hwGponDeviceOntIsOntUpfromReset  OBJECT-TYPE
            SYNTAX INTEGER {
                yes(1),
                no(2)
            }
            MAX-ACCESS accessible-for-notify
            STATUS current
            DESCRIPTION
                "This object indicates whether the GPON ONT is online after reset.
                 Options:
                 1. yes(1)    - The ONT is reseted.
                 2. no(2)     - The ONT is not reseted.
                "
            ::= { hwGponTrapsVbOids 16 }

     -- GPON BOARD AND PORT ALARM
        hwGponOltLOSAlarmTrap NOTIFICATION-TYPE
            OBJECTS {
                hwFrameIndex,
                hwSlotIndex,
                hwPortIndex,
                hwXponOltLosAffectOntNum,
                hwXponOltLosDgiOntNum
            }
            STATUS current
            DESCRIPTION
                "The LOS alarm trap of OLT.
                 The notification indicates alarm when the feed fiber is broken or OLT can not receive
                 any expected optical signals.
                "
            ::= { hwGponOltAlarmTraps 0 1 }

        hwGponOltLOSRecoverAlarmTrap NOTIFICATION-TYPE
            OBJECTS {
                hwFrameIndex,
                hwSlotIndex,
                hwPortIndex
            }
            STATUS current
            DESCRIPTION
                "This trap is sent when the OLT can receive expected optical signals from ONTs(LOS recovers)."
            ::= { hwGponOltAlarmTraps 0 2 }

        hwGponOltTFlarmTrap NOTIFICATION-TYPE
            OBJECTS {
                hwFrameIndex,
                hwSlotIndex,
                hwPortIndex
            }
            STATUS current
            DESCRIPTION
                "This trap is sent when the transmit failure (TF) occurs at the GPON port
                 for the hardware of the optical transceiver is faulty.
                "
            ::= { hwGponOltAlarmTraps 0 3 }

        hwGponOltTFRecoverAlarmTrap NOTIFICATION-TYPE
            OBJECTS {
                hwFrameIndex,
                hwSlotIndex,
                hwPortIndex
            }
            STATUS current
            DESCRIPTION
                "This trap is sent when the transmit failure (TF) occurs at the GPON port recovers."
            ::= { hwGponOltAlarmTraps 0 4 }

        hwGponOltOpticalTransceiverAbsentAlarmTrap NOTIFICATION-TYPE
            OBJECTS {
                hwFrameIndex,
                hwSlotIndex,
                hwPortIndex
            }
            STATUS current
            DESCRIPTION
                "This trap is sent when the optical transceiver of the PON port is absent."
            ::= { hwGponOltAlarmTraps 0 5 }

        hwGponOltOpticalTransceiverNormalAlarmTrap NOTIFICATION-TYPE
            OBJECTS {
                hwFrameIndex,
                hwSlotIndex,
                hwPortIndex
            }
            STATUS current
            DESCRIPTION
                "This trap is sent when the optical transceiver of the PON port recovers to the normal state."
            ::= { hwGponOltAlarmTraps 0 6 }

        hwGponPortHasRogueOntsAlarmTrap NOTIFICATION-TYPE
            OBJECTS {
                hwFrameIndex,
                hwSlotIndex,
                hwPortIndex
            }
            STATUS current
            DESCRIPTION
                "This trap is sent when there are illegal incursionary rogue ONTs under the port."
            ::= { hwGponOltAlarmTraps 0 7 }

        hwGponPortNotHaveRogueOntsAlarmTrap NOTIFICATION-TYPE
            OBJECTS {
                hwFrameIndex,
                hwSlotIndex,
                hwPortIndex
            }
            STATUS current
            DESCRIPTION
                "This trap is sent when the illegal incursionary rogue ONTs under the port have been cleared."
            ::= { hwGponOltAlarmTraps 0 8 }

        hwGponPortStatusChangesInTypeBDualAlarmTrap NOTIFICATION-TYPE
            OBJECTS {
                hwFrameIndex,
                hwSlotIndex,
                hwPortIndex
            }
            STATUS current
            DESCRIPTION
                "This trap is sent when the working status of the GPON port
                 in a TYPE-B dual parenting protect group changes frequently.
                "
            ::= { hwGponOltAlarmTraps 0 9 }

        hwGponPortStatusChangesInTypeBDualRecoverAlarmTrap NOTIFICATION-TYPE
            OBJECTS {
                hwFrameIndex,
                hwSlotIndex,
                hwPortIndex
            }
            STATUS current
            DESCRIPTION
                "This trap is sent when the port recovers from the fault
                 that its TYPE-B dual parenting protect status changes frequently.
                "
            ::= { hwGponOltAlarmTraps 0 10 }

     -- ONT AND ONT PORT ALARM
        hwGponReceiveOntKeyTransmitFailAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when failed to receive the key transmit from the ONT(LOKi)."
            ::= { hwGponOntAlarmTraps 0 1 }

        hwGponOntDiscoveryAlarmTrap NOTIFICATION-TYPE
            OBJECTS {
                hwFrameIndex,
                hwSlotIndex,
                hwPortIndex,
                hwGponDeviceAutoFindOntSn,
                hwGponDeviceAutoFindOntPassword,
                hwGponDeviceAutoFindOntLoid,
                hwGponDeviceAutoFindOntCheckcode
            }
            STATUS current
            DESCRIPTION
                "This trap is sent when the GPON ONT is discovered by the OLT."
            ::= { hwGponOntAlarmTraps 0 2 }

        hwGponDiscoveredOntDeletedAlarmTrap NOTIFICATION-TYPE
            OBJECTS {
                hwFrameIndex,
                hwSlotIndex,
                hwPortIndex,
                hwGponDeviceAutoFindOntSn,
                hwGponDeviceAutoFindOntPassword,
                hwGponDeviceAutoFindOntLoid,
                hwGponDeviceAutoFindOntCheckcode
            }
            STATUS current
            DESCRIPTION
                "This trap is sent when the discovered GPON ONT is deleted."
            ::= { hwGponOntAlarmTraps 0 3 }

        hwGponOntLCDGAlarmTrap NOTIFICATION-TYPE
            OBJECTS {
                hwFrameIndex,
                hwSlotIndex,
                hwPortIndex,
                hwGponDeviceOntObjectIndex
            }
            STATUS current
            DESCRIPTION
                "This trap is sent when the loss of GEM channel delineation (LCDGi) occurs."
            ::= { hwGponOntAlarmTraps 0 4 }

        hwGponOntLCDGRecoverAlarmTrap NOTIFICATION-TYPE
            OBJECTS {
                hwFrameIndex,
                hwSlotIndex,
                hwPortIndex,
                hwGponDeviceOntObjectIndex
            }
            STATUS current
            DESCRIPTION
                "This trap is sent when the loss of GEM channel delineation (LCDGi) recovers."
            ::= { hwGponOntAlarmTraps 0 5 }

        hwGponOntSDAlarmTrap NOTIFICATION-TYPE
            OBJECTS {
                hwFrameIndex,
                hwSlotIndex,
                hwPortIndex,
                hwGponDeviceOntObjectIndex
            }
            STATUS current
            DESCRIPTION
                "This trap is sent when the signal degrade of ONTi (SDi) occurs."
            ::= { hwGponOntAlarmTraps 0 6 }

        hwGponOntSDRecoverAlarmTrap NOTIFICATION-TYPE
            OBJECTS {
                hwFrameIndex,
                hwSlotIndex,
                hwPortIndex,
                hwGponDeviceOntObjectIndex
            }
            STATUS current
            DESCRIPTION
                "This trap is sent when the signal degrade of ONTi (SDi) recovers."
            ::= { hwGponOntAlarmTraps 0 7 }

        hwGponOntSFAlarmTrap NOTIFICATION-TYPE
            OBJECTS {
                hwFrameIndex,
                hwSlotIndex,
                hwPortIndex,
                hwGponDeviceOntObjectIndex
            }
            STATUS current
            DESCRIPTION
                "This trap is sent when the signal fail of ONTi (SFi) occurs."
            ::= { hwGponOntAlarmTraps 0 8 }

        hwGponOntSFRecoverAlarmTrap NOTIFICATION-TYPE
            OBJECTS {
                hwFrameIndex,
                hwSlotIndex,
                hwPortIndex,
                hwGponDeviceOntObjectIndex
            }
            STATUS current
            DESCRIPTION
                "This trap is sent when the signal fail of ONTi (SFi) recovers."
            ::= { hwGponOntAlarmTraps 0 9 }

        hwGponOntLOFAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the loss of frame of ONTi (LOFi) occurs."
            ::= { hwGponOntAlarmTraps 0 10 }

        hwGponOntLOFRecoverAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the loss of frame of ONTi (LOFi) recovers."
            ::= { hwGponOntAlarmTraps 0 11 }

        hwGponOntLOSAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the distribute fiber is broken or OLT can not
                 receive expected optical signals from ONT(LOSi).
                "
            ::= { hwGponOntAlarmTraps 0 12 }

        hwGponOntLOSRecoverAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the OLT can receive expected optical signals from ONT(LOSi recovers)."
            ::= { hwGponOntAlarmTraps 0 13 }

        hwGponOntSUFAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the ranging of ONTi failure (SUFi) occurs."
            ::= { hwGponOntAlarmTraps 0 14 }

        hwGponOntSUFRecoverAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the ranging of ONTi failure (SUFi) recovers."
            ::= { hwGponOntAlarmTraps 0 15 }

        hwGponOntLOAAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the loss of acknowledgement PLOAM message with ONTi (LOAi) occurs."
            ::= { hwGponOntAlarmTraps 0 16 }

        hwGponOntLOARecoverAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the loss of acknowledgement PLOAM message with ONTi (LOAi) recovers."
            ::= { hwGponOntAlarmTraps 0 17 }

        hwGponOntDGAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the dying-gasp of ONTi (DGi) is generated."
            ::= { hwGponOntAlarmTraps 0 18 }

        hwGponOntDGRecoverAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the dying-gasp of ONTi (DGi) recovers."
            ::= { hwGponOntAlarmTraps 0 19 }

        hwGponOntLOAMAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the loss of PLOAM of ONTi (LOAMi) occurs."
            ::= { hwGponOntAlarmTraps 0 20 }

        hwGponOntLOAMRecoverAlarmTrap NOTIFICATION-TYPE
            OBJECTS {
                hwFrameIndex,
                hwSlotIndex,
                hwPortIndex,
                hwGponDeviceOntObjectIndex,
                hwGponDeviceOntObjectEquipmentId
            }
            STATUS current
            DESCRIPTION
                "This trap is sent when the loss of PLOAM of ONTi (LOAMi) recovers."
            ::= { hwGponOntAlarmTraps 0 21 }

        hwGponOntPEEAlarmTrap NOTIFICATION-TYPE
            OBJECTS {
                hwFrameIndex,
                hwSlotIndex,
                hwPortIndex,
                hwGponDeviceOntObjectIndex
            }
            STATUS current
            DESCRIPTION
                "This trap is sent when the physical equipment error of ONTi (PEEi) occurs."
            ::= { hwGponOntAlarmTraps 0 24 }

        hwGponOntPEERecoverAlarmTrap NOTIFICATION-TYPE
            OBJECTS {
                hwFrameIndex,
                hwSlotIndex,
                hwPortIndex,
                hwGponDeviceOntObjectIndex
            }
            STATUS current
            DESCRIPTION
                "This trap is sent when the physical equipment error of ONTi (PEEi) recovers."
            ::= { hwGponOntAlarmTraps 0 25 }

        hwGponOntConfigRecoveryFailAlarmTrap NOTIFICATION-TYPE
            OBJECTS {
                hwFrameIndex,
                hwSlotIndex,
                hwPortIndex,
                hwGponDeviceOntObjectIndex
            }
            STATUS current
            DESCRIPTION
                "This trap is sent when the GPON ONT configuration recovery fails."
            ::= { hwGponOntAlarmTraps 0 26 }

        hwGponOntConfigRecoverySuccAlarmTrap NOTIFICATION-TYPE
            OBJECTS {
                hwFrameIndex,
                hwSlotIndex,
                hwPortIndex,
                hwGponDeviceOntObjectIndex
            }
            STATUS current
            DESCRIPTION
                "This trap is sent when the GPON ONT configuration recovery is successful."
            ::= { hwGponOntAlarmTraps 0 27 }

        hwGponOntAuthInfoConflictAlarmTrap NOTIFICATION-TYPE
            OBJECTS {
                hwFrameIndex,
                hwSlotIndex,
                hwPortIndex,
                hwGponDeviceOntObjectIndex
            }
            STATUS current
            DESCRIPTION
                "This trap is sent when the authentication information of the ONT is invalid."
            ::= { hwGponOntAlarmTraps 0 29 }

        hwGponOntResetByWatchdogAlarmTrap NOTIFICATION-TYPE
            OBJECTS {
                hwFrameIndex,
                hwSlotIndex,
                hwPortIndex,
                hwGponDeviceOntObjectIndex
            }
            STATUS current
            DESCRIPTION
                "This trap is sent when the ONT is reset by watchdog and gets online again."
            ::= { hwGponOntAlarmTraps 0 30 }

        hwGponOntSoftwareUpgradeSuccAlarmTrap NOTIFICATION-TYPE
            OBJECTS {
                hwFrameIndex,
                hwSlotIndex,
                hwPortIndex,
                hwGponDeviceOntObjectIndex
            }
            STATUS current
            DESCRIPTION
                "This trap is sent when the GPON ONT software upgrade is successful."
            ::= { hwGponOntAlarmTraps 0 31 }

        hwGponOntSoftwareUpgradeFailAlarmTrap NOTIFICATION-TYPE
            OBJECTS {
                hwFrameIndex,
                hwSlotIndex,
                hwPortIndex,
                hwGponDeviceOntObjectIndex
            }
        STATUS current
            DESCRIPTION
                "This trap is sent when the GPON ONT software upgrade fails."
            ::= { hwGponOntAlarmTraps 0 32 }

        hwGponOntHardwareFaultyAlarmTrap NOTIFICATION-TYPE
            OBJECTS {
                hwFrameIndex,
                hwSlotIndex,
                hwPortIndex,
                hwGponDeviceOntObjectIndex
            }
            STATUS current
            DESCRIPTION
                "This trap is sent when the hardware of the ONT is faulty."
            ::= { hwGponOntAlarmTraps 0 33 }

        hwGponOntHardwareFaultRecoverAlarmTrap NOTIFICATION-TYPE
            OBJECTS {
                hwFrameIndex,
                hwSlotIndex,
                hwPortIndex,
                hwGponDeviceOntObjectIndex
            }
            STATUS current
            DESCRIPTION
                "This trap is sent when the ONT recovers from the fault of hardware."
            ::= { hwGponOntAlarmTraps 0 34 }

        hwGponOntSwitchToStandbybatteryAlarmTrap NOTIFICATION-TYPE
            OBJECTS {
                hwFrameIndex,
                hwSlotIndex,
                hwPortIndex,
                hwGponDeviceOntObjectIndex
            }
            STATUS current
            DESCRIPTION
                "This trap is sent when the ONT switches to the standby battery."
            ::= { hwGponOntAlarmTraps 0 35 }

        hwGponOntExternalPowerSupplyRecoverAlarmTrap NOTIFICATION-TYPE
            OBJECTS {
                hwFrameIndex,
                hwSlotIndex,
                hwPortIndex,
                hwGponDeviceOntObjectIndex
            }
            STATUS current
            DESCRIPTION
                "This trap is sent when the external power supply of the ONT recovers."
            ::= { hwGponOntAlarmTraps 0 36 }

        hwGponOntStandbyBatteryLostAlarmTrap NOTIFICATION-TYPE
            OBJECTS {
                hwFrameIndex,
                hwSlotIndex,
                hwPortIndex,
                hwGponDeviceOntObjectIndex
            }
            STATUS current
            DESCRIPTION
                "This trap is sent when the standby battery of the ONT is lost."
            ::= { hwGponOntAlarmTraps 0 37 }

        hwGponOntLossOfStandbyBatteryRecoverAlarmTrap NOTIFICATION-TYPE
            OBJECTS {
                hwFrameIndex,
                hwSlotIndex,
                hwPortIndex,
                hwGponDeviceOntObjectIndex
            }
        STATUS current
            DESCRIPTION
                "This trap is sent when the ONT recovers from the loss of standby battery."
            ::= { hwGponOntAlarmTraps 0 38 }

        hwGponOntStandbyBatteryCannotChargedAlarmTrap NOTIFICATION-TYPE
            OBJECTS {
                hwFrameIndex,
                hwSlotIndex,
                hwPortIndex,
                hwGponDeviceOntObjectIndex
            }
        STATUS current
            DESCRIPTION
                "This trap is sent when the standby battery of the ONT cannot be charged."
            ::= { hwGponOntAlarmTraps 0 39 }

        hwGponOntStandbyBatteryRecoverAlarmTrap NOTIFICATION-TYPE
            OBJECTS {
                hwFrameIndex,
                hwSlotIndex,
                hwPortIndex,
                hwGponDeviceOntObjectIndex
            }
            STATUS current
            DESCRIPTION
                "This trap is sent when the standby battery of the ONT recovers."
            ::= { hwGponOntAlarmTraps 0 40 }

        hwGponOntVoltageOfStandbyBatteryTooLowAlarmTrap NOTIFICATION-TYPE
            OBJECTS {
                hwFrameIndex,
                hwSlotIndex,
                hwPortIndex,
                hwGponDeviceOntObjectIndex
            }
            STATUS current
            DESCRIPTION
                "This trap is sent when the voltage of the standby battery of the ONT is too low."
            ::= { hwGponOntAlarmTraps 0 41 }

        hwGponOntVoltageOfStandbyBatteryRecoverAlarmTrap NOTIFICATION-TYPE
            OBJECTS {
                hwFrameIndex,
                hwSlotIndex,
                hwPortIndex,
                hwGponDeviceOntObjectIndex
            }
            STATUS current
            DESCRIPTION
                "This trap is sent when the voltage of the standby battery of the ONT recovers."
            ::= { hwGponOntAlarmTraps 0 42 }

        hwGponOntShellOpenedAlarmTrap NOTIFICATION-TYPE
            OBJECTS {
                hwFrameIndex,
                hwSlotIndex,
                hwPortIndex,
                hwGponDeviceOntObjectIndex
            }
            STATUS current
            DESCRIPTION
                "This trap is sent when the shell of the ONT is opened."
            ::= { hwGponOntAlarmTraps 0 43 }

        hwGponOntShellClosedAlarmTrap NOTIFICATION-TYPE
            OBJECTS {
                hwFrameIndex,
                hwSlotIndex,
                hwPortIndex,
                hwGponDeviceOntObjectIndex
            }
            STATUS current
            DESCRIPTION
                "This trap is sent when the shell of the ONT is closed."
            ::= { hwGponOntAlarmTraps 0 44 }

        hwGponNumerousOntsPowerOffAlarmTrap NOTIFICATION-TYPE
            OBJECTS {
                hwFrameIndex,
                hwSlotIndex,
                hwPortIndex,
                hwGponOntMask
            }
            STATUS current
            DESCRIPTION
                "This trap is sent when the numerous ONTs are powered off in one district."
            ::= { hwGponOntAlarmTraps 0 45 }

        hwGponOntIsRogueOntAlarmTrap NOTIFICATION-TYPE
            OBJECTS {
                hwFrameIndex,
                hwSlotIndex,
                hwPortIndex,
                hwGponDeviceOntObjectIndex
            }
            STATUS current
            DESCRIPTION
                "This trap is sent when the ONT is rogue ONT."
            ::= { hwGponOntAlarmTraps 0 46 }

        hwGponRogueOntDisapearAlarmTrap NOTIFICATION-TYPE
            OBJECTS {
                hwFrameIndex,
                hwSlotIndex,
                hwPortIndex,
                hwGponDeviceOntObjectIndex
            }
            STATUS current
            DESCRIPTION
                "This trap is sent when the rogue ONT disappeared."
            ::= { hwGponOntAlarmTraps 0 47 }

        hwGponLocalOpticalModuleExceedAlarmThresAlarmTrap NOTIFICATION-TYPE
            OBJECTS {
                hwFrameIndex,
                hwSlotIndex,
                hwPortIndex,
                hwGponDeviceOntObjectIndex,
                hwGponOntOpticalMoudleAlarmType,
                hwGponOntOpticalMoudleAlarmUpperValue,
                hwGponOntOpticalMoudleAlarmLowerValue,
                hwGponOntOpticalMoudleAlarmCurrentValue
            }
            STATUS current
            DESCRIPTION
                "This trap is sent when the local optical transceiver parameters exceed alarm threshold."
            ::= { hwGponOntAlarmTraps 0 48 }

        hwGponLocalOpticalModuleRecoverAlarmThresAlarmTrap NOTIFICATION-TYPE
            OBJECTS {
                hwFrameIndex,
                hwSlotIndex,
                hwPortIndex,
                hwGponDeviceOntObjectIndex,
                hwGponOntOpticalMoudleAlarmType,
                hwGponOntOpticalMoudleAlarmUpperValue,
                hwGponOntOpticalMoudleAlarmLowerValue,
                hwGponOntOpticalMoudleAlarmCurrentValue
            }
            STATUS current
            DESCRIPTION
                "This trap is sent when the local optical transceiver parameters exceed alarm threshold recover."
            ::= { hwGponOntAlarmTraps 0 49 }

        hwGponRemoteOpticalModuleExceedAlarmThresAlarmTrap NOTIFICATION-TYPE
            OBJECTS {
                hwFrameIndex,
                hwSlotIndex,
                hwPortIndex,
                hwGponDeviceOntObjectIndex,
                hwGponOntOpticalMoudleAlarmType,
                hwGponOntOpticalMoudleAlarmUpperValue,
                hwGponOntOpticalMoudleAlarmLowerValue,
                hwGponOntOpticalMoudleAlarmCurrentValue
            }
            STATUS current
            DESCRIPTION
                "This trap is sent when the remote optical transceiver parameters exceed alarm threshold."
            ::= { hwGponOntAlarmTraps 0 50 }

        hwGponRemoteOpticalModuleRecoverAlarmThresAlarmTrap NOTIFICATION-TYPE
            OBJECTS {
                hwFrameIndex,
                hwSlotIndex,
                hwPortIndex,
                hwGponDeviceOntObjectIndex,
                hwGponOntOpticalMoudleAlarmType,
                hwGponOntOpticalMoudleAlarmUpperValue,
                hwGponOntOpticalMoudleAlarmLowerValue,
                hwGponOntOpticalMoudleAlarmCurrentValue
            }
            STATUS current
            DESCRIPTION
                "This trap is sent when the remote optical transceiver parameters exceed alarm threshold recover."
            ::= { hwGponOntAlarmTraps 0 51 }

        hwGponLocalOpticalModuleExceedWarnThresAlarmTrap NOTIFICATION-TYPE
            OBJECTS {
                hwFrameIndex,
                hwSlotIndex,
                hwPortIndex,
                hwGponDeviceOntObjectIndex,
                hwGponOntOpticalMoudleAlarmType,
                hwGponOntOpticalMoudleAlarmUpperValue,
                hwGponOntOpticalMoudleAlarmLowerValue,
                hwGponOntOpticalMoudleAlarmCurrentValue
            }
            STATUS current
            DESCRIPTION
                "This trap is sent when the local optical transceiver parameters exceed warning threshold."
            ::= { hwGponOntAlarmTraps 0 52 }

        hwGponLocalOpticalModuleRecoverWarnThresAlarmTrap NOTIFICATION-TYPE
            OBJECTS {
                hwFrameIndex,
                hwSlotIndex,
                hwPortIndex,
                hwGponDeviceOntObjectIndex,
                hwGponOntOpticalMoudleAlarmType,
                hwGponOntOpticalMoudleAlarmUpperValue,
                hwGponOntOpticalMoudleAlarmLowerValue,
                hwGponOntOpticalMoudleAlarmCurrentValue
            }
            STATUS current
            DESCRIPTION
                "This trap is sent when the local optical transceiver parameters exceed warning threshold recover."
            ::= { hwGponOntAlarmTraps 0 53 }

        hwGponRemoteOpticalModuleExceedWarnThresAlarmTrap NOTIFICATION-TYPE
            OBJECTS {
                hwFrameIndex,
                hwSlotIndex,
                hwPortIndex,
                hwGponDeviceOntObjectIndex,
                hwGponOntOpticalMoudleAlarmType,
                hwGponOntOpticalMoudleAlarmUpperValue,
                hwGponOntOpticalMoudleAlarmLowerValue,
                hwGponOntOpticalMoudleAlarmCurrentValue
            }
            STATUS current
            DESCRIPTION
                "This trap is sent when the remote optical transceiver parameters exceed warning threshold."
            ::= { hwGponOntAlarmTraps 0 54 }

        hwGponRemoteOpticalModuleRecoverWarnThresAlarmTrap NOTIFICATION-TYPE
            OBJECTS {
                hwFrameIndex,
                hwSlotIndex,
                hwPortIndex,
                hwGponDeviceOntObjectIndex,
                hwGponOntOpticalMoudleAlarmType,
                hwGponOntOpticalMoudleAlarmUpperValue,
                hwGponOntOpticalMoudleAlarmLowerValue,
                hwGponOntOpticalMoudleAlarmCurrentValue
            }
            STATUS current
            DESCRIPTION
                "This trap is sent when the remote optical transceiver parameters exceed warning threshold recover."
            ::= { hwGponOntAlarmTraps 0 55 }

        hwGponOntE1T1PortStatusAbnormalAlarmTrap NOTIFICATION-TYPE
            OBJECTS {
                hwFrameIndex,
                hwSlotIndex,
                hwPortIndex,
                hwGponDeviceOntObjectIndex,
                hwGponOntTDMPortId,
                hwGponOntTDMPortAlarmType
            }
            STATUS current
            DESCRIPTION
                "This trap is sent when the status of ONT's E1/T1 port is abnormal."
            ::= { hwGponOntAlarmTraps 0 81 }

        hwGponOntE1T1PortStatusRecoverAlarmTrap NOTIFICATION-TYPE
            OBJECTS {
                hwFrameIndex,
                hwSlotIndex,
                hwPortIndex,
                hwGponDeviceOntObjectIndex,
                hwGponOntTDMPortId,
                hwGponOntTDMPortAlarmType
            }
            STATUS current
            DESCRIPTION
                "This trap is sent when the status of ONT's E1/T1 port recovers."
            ::= { hwGponOntAlarmTraps 0 82 }

        hwGponEthernetPortLossOfSignelOccurAlarmTrap NOTIFICATION-TYPE
            OBJECTS {
                hwFrameIndex,
                hwSlotIndex,
                hwPortIndex,
                hwGponDeviceOntObjectIndex,
                hwGponOntifEthernetPort
            }
            STATUS current
            DESCRIPTION
                "This trap is sent when the loss of signals occurs on the ethernet port of the ONT."
            ::= { hwGponOntAlarmTraps 0 83 }

        hwGponEthernetPortSignalRecoverAlarmTrap NOTIFICATION-TYPE
            OBJECTS {
                hwFrameIndex,
                hwSlotIndex,
                hwPortIndex,
                hwGponDeviceOntObjectIndex,
                hwGponOntifEthernetPort
            }
            STATUS current
            DESCRIPTION
                "This trap is sent when the ethernet port of the ONT recovers from the loss of signals."
            ::= { hwGponOntAlarmTraps 0 84 }

        hwGponVideoUNINoSignalAlarmTrap NOTIFICATION-TYPE
            OBJECTS {
                hwFrameIndex,
                hwSlotIndex,
                hwPortIndex,
                hwGponDeviceOntObjectIndex,
                hwGponOntCatvPortId
            }
            STATUS current
            DESCRIPTION
                "This trap is sent when no signal is received in the video UNI of the ONT."
            ::= { hwGponOntAlarmTraps 0 85 }

        hwGponVideoUNISignalRecoverAlarmTrap NOTIFICATION-TYPE
            OBJECTS {
                hwFrameIndex,
                hwSlotIndex,
                hwPortIndex,
                hwGponDeviceOntObjectIndex,
                hwGponOntCatvPortId
            }
            STATUS current
            DESCRIPTION
                "This trap is sent when the video UNI of the ONT recovers from the loss of signals."
            ::= { hwGponOntAlarmTraps 0 86 }

        hwGponE1T1PortLOSOccurAlarmTrap NOTIFICATION-TYPE
            OBJECTS {
                hwFrameIndex,
                hwSlotIndex,
                hwPortIndex,
                hwGponDeviceOntObjectIndex,
                hwGponOntTDMPortId
            }
            STATUS current
            DESCRIPTION
                "This trap is sent when the E1/T1 port loss of signal (LOS) occurs at the ONT."
            ::= { hwGponOntAlarmTraps 0 87 }

        hwGponE1T1PortSignalRecoverAlarmTrap NOTIFICATION-TYPE
            OBJECTS {
                hwFrameIndex,
                hwSlotIndex,
                hwPortIndex,
                hwGponDeviceOntObjectIndex,
                hwGponOntTDMPortId
            }
            STATUS current
            DESCRIPTION
                "This trap is sent when the E1/T1 port of the ONT recovers from loss of signal (LOS)."
            ::= { hwGponOntAlarmTraps 0 88 }
         
        hwGponDeviceOntRunStateChangeTrap NOTIFICATION-TYPE
            OBJECTS {
                hwReservedValue,
                hwGponTrapOperType,
                ifIndex,
                hwGponDeviceOntObjectIndex,
                hwGponDeviceOntObjectRunStatus
            }
            STATUS current
            DESCRIPTION
                "This trap is sent when the run state of the GPON ONT changes."
            ::= { hwGponCommonTraps 0 1 }

        hwGponDeviceOntAutoFindTrap NOTIFICATION-TYPE
            OBJECTS {
                hwReservedValue,
                hwGponTrapOperType,
                hwFrameIndex,
                hwSlotIndex,
                hwPortIndex,
                hwGponDeviceAutoFindOntSn,
                hwGponDeviceAutoFindOntPassword,
                hwGponDeviceAutoFindOntVendorId,
                hwGponDeviceAutoFindOntVer,
                hwGponDeviceAutoFindOntMainSoftVer,
                hwGponDeviceAutoFindOntEquipmentId,
                hwGponDeviceAutoFindOntLoid,
                hwGponDeviceAutoFindOntCheckcode,
                hwGponDeviceAutoFindOntCustomizedInfo
            }
            STATUS current
            DESCRIPTION
                "This trap is sent when the Gpon ont is auto found."
            ::= { hwGponCommonTraps 0 2 }

        hwGponDeviceOntVersionTrap NOTIFICATION-TYPE
            OBJECTS {
                hwReservedValue,
                hwGponTrapOperType,
                ifIndex,
                hwGponDeviceOntObjectIndex,
                hwGponDeviceOntObjectCRCSupport,
                hwGponDeviceOntObjectCRCCode,
                hwGponDeviceOntObjectVendorId,
                hwGponDeviceOntObjectEquipmentId,
                hwGponDeviceOntObjectMainSoftVer,
                hwGponDeviceOntDualUpstreamSupport,
                hwGponDeviceOntObjectPGMemberRole,
                hwGponDeviceOntObjectSoftWorkMode,
                hwGponDeviceOntIsOntUpfromReset,
                hwXponOntInfoSupportXmlVersion,
                hwXponOntFirstOnline,
                hwXponOntSupportVoipCfgMethod,
                hwGponDeviceOntVoipCfgFileVersion,
                hwGponDeviceOntConfigCustomizedInfo
            }
            STATUS current
            DESCRIPTION
                "This trap is sent when the Gpon ONT is online."
            ::= { hwGponCommonTraps 0 3 }
            
        hwGponDeviceOntLoadTrap NOTIFICATION-TYPE
            OBJECTS {
                hwReservedValue,
                hwGponOntLoadOperType,
                ifIndex,
                hwGponDeviceOntObjectIndex,
                hwOntLoadFileType,
                hwGponOntLoadResult,
                hwGponOntLoadCrcSupport,
                hwGponOntLoadCrcValue
            }
            STATUS current
            DESCRIPTION
                "This trap is sent when the Gpon ONT is loaded."
            ::= { hwGponCommonTraps 0 4 }

        hwGponDeviceOntDiscoveryStateTrap NOTIFICATION-TYPE
            OBJECTS {
                hwConfigChangeIP,
                hwGponTrapOperType,
                ifIndex,
                hwGponDeviceOntObjectIndex,
                hwGponDeviceOntObjectDiscoveryStatus
            }
            STATUS current
            DESCRIPTION
                "This trap is sent when the discovery state of the Gpon ONT is changed."
            ::= { hwGponCommonTraps 0 5 }

        hwGponGEMMappingCfgChangeTrap NOTIFICATION-TYPE
            OBJECTS {
                hwConfigChangeIP,
                hwGponTrapOperType,
                ifIndex,
                hwGponDevicePortidMapObjectIndex,
                hwGponDevicePortidFlowIndex,
                hwGponDevicePortidMapObjectVlanID,
                hwGponDevicePortidMapObjectPir,
                hwGponDevicePortidMapObjectPortType,
                hwGponDevicePortidMapObjectPortID,
                hwGponDevicePortidMapTrafficTableId,
                hwGponDevicePortidMapTransparent
            }
            STATUS current
            DESCRIPTION
                "This trap is sent when the gem port mapping configuration changes."
            ::= { hwGponCommonTraps 0 6 }

        hwGponONTGEMPortCfgChangeTrap NOTIFICATION-TYPE
            OBJECTS {
                hwConfigChangeIP,
                hwGponTrapOperType,
                ifIndex,
                hwGponDeviceOntPortidObjectIndex,
                hwGponDeviceOntPortidObjectOntId,
                hwGponDeviceOntPortidObjectTcontId,
                hwGponDeviceOntPortidObjectUpPQIndex,
                hwGponDeviceOntPortidTrafficTableId,
                hwGponDeviceOntPortidObjectDownPQIndex
            }
            STATUS current
            DESCRIPTION
                "This trap is sent when the gem port configuration changes."
            ::= { hwGponCommonTraps 0 7 }

        hwGponOntPortVlanCfgTrap NOTIFICATION-TYPE
            OBJECTS {
                hwConfigChangeIP,
                hwGponTrapOperType,
                ifIndex,
                hwGponDeviceOntObjectIndex,
                hwGponOntPortVlanCfgOntPhyType,
                hwGponOntPortVlanCfgOntPhyIndex,
                hwGponOntPortVlanCfgCVlan,
                hwGponOntPortVlanCfgSVlan,
                hwGponOntPortVlanCfgSPri,
                hwGponOntPortVlanCfgCPri,
                hwGponOntPortVlanCfgType,
                hwGponOntPortVlanCfgEtherType
            }
            STATUS current
            DESCRIPTION
                "This trap is sent when the port vlan configuration of the Gpon ONT changes."
            ::= { hwGponCommonTraps 0 8 }

        hwGponDevProfileCfgTrap NOTIFICATION-TYPE
            OBJECTS {
                hwConfigChangeIP,
                hwGponTrapOperType,
                hwGponDeviceOntProfileNameIndex,
                hwGponDeviceOntProfilePonAniNum,
                hwGponDeviceOntProfileUniConfig,
                hwGponDeviceOntProfileMACBridge,
                hwGponDeviceOntProfilePotsNum,
                hwGponDeviceOntProfileIPSupport,
                hwGponDeviceOntProfileFeNum,
                hwGponDeviceOntProfileGeNum,
                hwGponDeviceOntTdmPortType,
                hwGponDeviceOntProfileE1T1TYPE,
                hwGponDeviceOntProfileE1T1Num,
                hwGponDeviceOntProfileMocaNum,
                hwGponDeviceOntProfileCatvAniNum,
                hwGponDeviceOntProfileCatvUniNum,
                hwGponDeviceOntProfileGemPortNum,
                hwGponDeviceOntProfileGemPortMap,
                hwGponDeviceOntProfileTcontNum,
                hwGponDeviceOntProfileFCType,
                hwGponDeviceOntProfileTcont0PQNum,
                hwGponDeviceOntProfileTcont1PQNum,
                hwGponDeviceOntProfileTcont2PQNum,
                hwGponDeviceOntProfileTcont3PQNum,
                hwGponDeviceOntProfileTcont4PQNum,
                hwGponDeviceOntProfileTcont5PQNum,
                hwGponDeviceOntProfileTcont6PQNum,
                hwGponDeviceOntProfileTcont7PQNum,
                hwGponDeviceOntProfileEthNum,
                hwGponDeviceOntProfileVdslPortNum
            }
            STATUS current
            DESCRIPTION
                "This trap is sent when the device profile configuration of the GPON changes."
            ::= { hwGponCommonTraps 0 9 }

        hwGponGEMPortCfgChangeTrap NOTIFICATION-TYPE
            OBJECTS {
                hwConfigChangeIP,
                hwGponTrapOperType,
                ifIndex,
                hwGponDevicePortidObjectIndex,
                hwGponDevicePortidServiceType,
                hwGponDevicePortidObjectDnEncrypt,
                hwGponDevicePortidCascade,
                hwGponDevicePortidDescription
            }
            STATUS current
            DESCRIPTION
                "This trap is sent when the Gpon GEM port configuration changes."
            ::= { hwGponCommonTraps 0 10 }

        hwGponTcontProfileOperateTrap NOTIFICATION-TYPE
            OBJECTS {
                hwConfigChangeIP,
                hwGponTrapOperType,
                ifIndex,
                hwGponDeviceOntObjectIndex,
                hwGponDeviceTcontRefIndex,
                hwGponDeviceTcontName,
                hwGponDeviceAllocId
            }
            STATUS current
            DESCRIPTION
                "This trap is sent when the Gpon Tcont profile changes."
            ::= { hwGponCommonTraps 0 11 }

        hwGponDistModeOntInfoTrap NOTIFICATION-TYPE
            OBJECTS {
                hwConfigChangeIP,
                hwGponTrapOperType,
                ifIndex,
                hwGponDeviceOntObjectIndex,
                hwGponDeviceOntObjectAuthMethod,
                hwGponDeviceOntObjectSn,
                hwGponDeviceOntObjectPassword,
                hwGponDeviceOntObjectRefAlarmProfileName,
                hwGponDeviceOntObjectDespt,
                hwGponDeviceOntObjectDbaStatus,
                hwGponDeviceOntObjectCapabProfileName,
                hwGponDeviceOntObjectTimeOut,
                hwGponDeviceOntTransparent,
                hwGponDeviceOntObjectIgmpMode,
                hwGponDeviceOntObjectIgmpSwitchVlan,
                hwGponDeviceOntObjectLastDownTime,
                hwGponDeviceOntObjectLastUpTime,
                hwGponDeviceOntObjectLastDownCause,
                hwGponDeviceOntTdmLocalInnerLoopback,
                hwGponDeviceOntTdmLocalOuterLoopback,
                hwGponDeviceOntMacAddressSwitch,
                hwGponDeviceOntObjectSnmpProfileName,
                hwGponDeviceOntObjectManageMode,
                hwGponDeviceOntUpIgmpMsgProcMode,
                hwGponDeviceOntIgmpForwardTranslationVlan,
                hwGponDeviceOntMulticastCtrlMode,
                hwGponDeviceOntObjectLoid,
                hwGponDeviceOntObjectCheckcode,
                hwGponDeviceOntObjectReregisterAuthMode,
                hwGponDeviceOntRingCheckSwitch,
                hwGponDeviceOntRingCheckAutoShutdownSwitch,
                hwGponDeviceOntRingCheckDetectingFrequency,
                hwGponDeviceOntRingCheckResumeInterval,
                hwGponDeviceOntObjectNniType
            }
            STATUS current
            DESCRIPTION
                "This trap is sent when the Gpon ONT configuration changes under distributed mode."
            ::= { hwGponCommonTraps 0 12 }



     -- hwXponCommonTraps
        hwXponOntTransmittingOperType OBJECT-TYPE
            SYNTAX      Integer32
            MAX-ACCESS  accessible-for-notify
            STATUS      current
            DESCRIPTION
                "ONT transmitting operation type."
            ::= { hwXponCommonTrapsVbOids  1 }

        hwXponOntTransmittingCrc OBJECT-TYPE
            SYNTAX      Integer32
            MAX-ACCESS  accessible-for-notify
            STATUS      current
            DESCRIPTION
                "CRC of ONT transmitting."
            ::= { hwXponCommonTrapsVbOids  2 }

        hwXponCommonDeviceOntPingResult OBJECT-TYPE
            SYNTAX     INTEGER {
                success(1),
                failure(2),
                unexpectedICMPresponse(3)
            }
            MAX-ACCESS accessible-for-notify
            STATUS     current
            DESCRIPTION
                "The result of the ONT remote ping.
                 Options:
                 1. success(1)                   - The ONT remote ping successful
                 2. failure(2)                   - Failed in the ONT remote ping
                 3. unexpectedICMPresponse(3)    - Unexpected ICMP response.
                "
            ::= { hwXponCommonTrapsVbOids 3 }

        hwXponCommonDeviceSentPackets OBJECT-TYPE
            SYNTAX     Integer32
            MAX-ACCESS accessible-for-notify
            STATUS     current
            DESCRIPTION
                "The packet of the ont send."
            ::= { hwXponCommonTrapsVbOids 4 }

        hwXponCommonDeviceReceivedPackets OBJECT-TYPE
            SYNTAX     Integer32
            MAX-ACCESS accessible-for-notify
            STATUS     current
            DESCRIPTION
                "The number of the ont remote ping received packets."
            ::= { hwXponCommonTrapsVbOids 5 }

        hwXponCommonDeviceLostPackets OBJECT-TYPE
            SYNTAX     Integer32
            MAX-ACCESS accessible-for-notify
            STATUS     current
            DESCRIPTION
                "The number of the ont remote ping lost packets."
            ::= { hwXponCommonTrapsVbOids 6 }

        hwXponCommonDeviceLostRatio OBJECT-TYPE
            SYNTAX     Integer32
            MAX-ACCESS accessible-for-notify
            STATUS     current
            DESCRIPTION
                "The ratio of the ont remote ping lost packets(percent)."
            ::= { hwXponCommonTrapsVbOids 7 }

        hwXponCommonDeviceMinDelay OBJECT-TYPE
            SYNTAX   Integer32
            MAX-ACCESS accessible-for-notify
            STATUS current
            DESCRIPTION
                "The minimum delay of the ont remote ping(milli-seconds)."
            ::= { hwXponCommonTrapsVbOids 8 }

        hwXponCommonDeviceMaxDelay OBJECT-TYPE
            SYNTAX     Integer32
            MAX-ACCESS accessible-for-notify
            STATUS     current
            DESCRIPTION
                "The maximum delay of the ont remote ping(milli-seconds)."
            ::= { hwXponCommonTrapsVbOids 9 }

        hwXponCommonDeviceAverageDelay OBJECT-TYPE
            SYNTAX   Integer32
            MAX-ACCESS accessible-for-notify
            STATUS current
            DESCRIPTION
                "The average delay of the ont remote ping(milli-seconds)."
            ::= { hwXponCommonTrapsVbOids 10 }

        hwXponModeSwitchResult OBJECT-TYPE
            SYNTAX     INTEGER {
                success(0),
                systemBusy(1),
                dataSynIncomplete(2),
                lineProfileExceedSpec(3),
                srvProfileExceedSpec(4)
            }
            MAX-ACCESS accessible-for-notify
            STATUS     current
            DESCRIPTION
                "The XPON mode switch result.
                 Options:
                 1. success(0)               - The XPON mode switch successful 
                 2. systemBusy(1)            - System busy
                 3. dataSynIncomplete(2)     - Data synchronization incomplete 
                 4. lineProfileExceedSpec(3) - The number of line profile has exceeded the maximum value after mode switch 
                 5. srvProfileExceedSpec(4)  - The number of service profile has exceeded the maximum value after mode switch
                "
            ::= { hwXponCommonTrapsVbOids 11 }

        hwXponConfigMode OBJECT-TYPE
            SYNTAX     INTEGER {
                distributeMode(0),
                profileMode(1)
            }
            MAX-ACCESS accessible-for-notify
            STATUS     current
            DESCRIPTION
                "The XPON configuration mode.
                 Options:
                 1. distributeMode(0) - Distribute mode
                 2. profileMode(1)    - Profile mode
                "
            ::= { hwXponCommonTrapsVbOids 12 }

        hwXponOltMinBandwidth OBJECT-TYPE
            SYNTAX       Integer32
            MAX-ACCESS   accessible-for-notify
            STATUS       current
            DESCRIPTION
                "Minimum bandwidth,Unit: kbps.
                 0xffff --indicates has not set the minimum bandwidth
                "
            ::= { hwXponCommonTrapsVbOids 13 }

        hwXponOltNearestDistance OBJECT-TYPE
            SYNTAX       Integer32
            MAX-ACCESS   accessible-for-notify
            STATUS       current
            DESCRIPTION
                "Nearest distance,Unit: km"
            ::= { hwXponCommonTrapsVbOids 14 }

        hwXponOltFarestDistance OBJECT-TYPE
            SYNTAX       Integer32
            MAX-ACCESS   accessible-for-notify
            STATUS       current
            DESCRIPTION
                "Farthest distance,Unit: km"
            ::= { hwXponCommonTrapsVbOids 15 }

        hwXponOltAutoFindOntFlag OBJECT-TYPE
            SYNTAX       INTEGER {
                open(1),
                close(2)
            }
            MAX-ACCESS   accessible-for-notify
            STATUS       current
            DESCRIPTION
                "Autofind flag.
                 Options:
                 1. open(1)  - Open autofind ONT
                 2. close(2) - Close autofind ONT
                "
            ::= { hwXponCommonTrapsVbOids 16 }

        hwXponOltAutoUpdateOntFlag OBJECT-TYPE
            SYNTAX       Integer32
            MAX-ACCESS   accessible-for-notify
            STATUS       current
            DESCRIPTION
                "Auto update flag.
                 -1  --indicates currently not supported ONT auto update
                "
            ::= { hwXponCommonTrapsVbOids 17 }

        hwXponOltDownFecEnableFlag OBJECT-TYPE
            SYNTAX       INTEGER {
                open(1),
                close(2)
            }
            MAX-ACCESS   accessible-for-notify
            STATUS       current
            DESCRIPTION
                "FEC downstream check flag.
                 Options:
                 1. open(1)  - Open FEC downstream check
                 2. close(2) - Close FEC downstream check
                "
            ::= { hwXponCommonTrapsVbOids 18 }

        hwGponOntPortTDMCodeMode OBJECT-TYPE
            SYNTAX       INTEGER {
                ami(1),
                hdb3(2),
                invalid(-1)
            }
            MAX-ACCESS   accessible-for-notify
            STATUS       current
            DESCRIPTION
                "TDM port coding style
                 Options:
                 1. ami(1)              - Using AMI coding
                 2. hdb3(2)             - Using HDB3 coding
                 3. invalid (-1)        - Indicates that the query fails or no information is detected
                "
            ::= { hwXponCommonTrapsVbOids 19 }

        hwGponOntPortManagementStatus OBJECT-TYPE
            SYNTAX   INTEGER {
                unlock(1),
                lock(2)
                }
            MAX-ACCESS   accessible-for-notify
            STATUS       current
            DESCRIPTION
                "ONT port management state
                 Options:
                 1. unlock(1) - Unlock state, all user functions of this circuit pack are normal
                 2. lock(2)   - All user functions of this circuit pack are blocked, and alarm for
                                this managed entity are no longer generated
                "
            ::= { hwXponCommonTrapsVbOids 20 }

     -- hwGponOntEthPortLoopback OBJECT-TYPE
     --     SYNTAX   Integer32
     --     MAX-ACCESS   accessible-for-notify
     --     STATUS       current
     --     DESCRIPTION
     --         "Ont's ethernet port loop back"
     --     ::= { hwXponCommonTrapsVbOids 21 }

        hwGponOntE1PortLoopback OBJECT-TYPE
            SYNTAX       Integer32
            MAX-ACCESS   accessible-for-notify
            STATUS       current
            DESCRIPTION
                "Ont's TDM port loop back.
                 The value (-1) indicates that the query fails.
                "
            ::= { hwXponCommonTrapsVbOids 22 }

        hwGponOntPortVlanDefault OBJECT-TYPE
            SYNTAX       Integer32
            MAX-ACCESS   accessible-for-notify
            STATUS       current
            DESCRIPTION
                "Default vlan ID of the ONT ETH port(s)."
            ::= { hwXponCommonTrapsVbOids 23 }

        hwGponOntPortVlanDefaultPriority OBJECT-TYPE
            SYNTAX       Integer32
            MAX-ACCESS   accessible-for-notify
            STATUS       current
            DESCRIPTION
                "Default priority of the ONT ETH port(s)."
            ::= { hwXponCommonTrapsVbOids 24 }

        hwXponOntPppoeSimuResult OBJECT-TYPE
            SYNTAX INTEGER {
                success(1),
                paramNegoFail(2),
                userAuthenticationFail(3),
                timeout(4),
                userStop(5),
                unknown(6),
                configurationError(7),
                peerStop(8),
                waitPadoTimeout(9),
                waitPadsTimeout(10),
                waitPppTimeout(11),
                linkAbnormal(12)
            }
            MAX-ACCESS accessible-for-notify
            STATUS current
            DESCRIPTION
                "This object indicates the result of PPPoE test.
                 Options:
                 1. success(1)                 - Indicates the PPPoE test is successful.
                 2. paramNegoFail(2)           - Indicates parameter negotiation failed.
                 3. userAuthenticationFail(3)  - Indicates user authentication failed.
                 4. timeout(4)                 - Indicates the PPPoE test is timeout.
                 5. userStop(5)                - Indicates user stopped.
                 6. unknown(6)                 - Indicates unknown.
                 7. configurationError(7)      - Indicates configuration error.
                 8. peerStop(8)                - Indicates the dialup request is denied by the peer end.
                 9. waitPadoTimeout(9)         - Indicates sending PADI and waiting for PADO time out.
                 10. waitPadsTimeout(10)       - Indicates sending PADR and waiting for PADS time out.
                 11. waitPppTimeout(11)        - Indicates waiting for PPP times out, such as an LCP timeout or an NCP timeout.
                 12. linkAbnormal(12)          - Indicates the link of the PPPoE simulation is abnormal.
                "
            ::= { hwXponCommonTrapsVbOids 25 }

        hwXponOntPppoeSimuResultSessionId OBJECT-TYPE
            SYNTAX Integer32
            MAX-ACCESS accessible-for-notify
            STATUS current
            DESCRIPTION
                "The Session ID of PPPoE test."
            ::= { hwXponCommonTrapsVbOids 26 }

        hwXponOntPppoeSimuResultUserIp OBJECT-TYPE
            SYNTAX IpAddress
            MAX-ACCESS accessible-for-notify
            STATUS current
            DESCRIPTION
                "The User IP of PPPoE test."
            ::= { hwXponCommonTrapsVbOids 27 }

        hwXponOntPppoeSimuResultGatewayIp OBJECT-TYPE
            SYNTAX IpAddress
            MAX-ACCESS accessible-for-notify
            STATUS current
            DESCRIPTION
                "The Gateway IP of PPPoE test."
            ::= { hwXponCommonTrapsVbOids 28 }

        hwXponCommonDeviceReceivedICMPErrorCode OBJECT-TYPE
            SYNTAX Integer32
            MAX-ACCESS accessible-for-notify
            STATUS current
            DESCRIPTION
                "This object indicates the received ICMP error code."
            ::= { hwXponCommonTrapsVbOids 29 }

        hwXponOltChangePasswordIntervalTime OBJECT-TYPE
            SYNTAX       Integer32
            MAX-ACCESS   accessible-for-notify
            STATUS       current
            DESCRIPTION
                "Ont's password renew time interval,Unit: minutes."
            ::= { hwXponCommonTrapsVbOids 30 }

        hwXponRogueOntManualDetectState OBJECT-TYPE
            SYNTAX   INTEGER {
                finished(0),
                unknown(-1)
            }
            MAX-ACCESS   accessible-for-notify
            STATUS       current
            DESCRIPTION
                "This object indicates the state of rogue ONT manual detect.
                 Options:
                 1. finished(0)                 - Has finished detecting.
                 2. unknown(-1)                 - The detecting state is unknown.
                "
            ::= { hwXponCommonTrapsVbOids 31 }

        hwXponCommonOntFECUncorrectCodeWordsThreshold OBJECT-TYPE
            SYNTAX       Integer32
            MAX-ACCESS   accessible-for-notify
            STATUS       current
            DESCRIPTION
                "This object indicates the threshold of the code words that were not corrected by
                 the FEC function.
                "
            ::= { hwXponCommonTrapsVbOids 32 }

        hwXponCommonOntFECCorrectCodeWordsThreshold OBJECT-TYPE
            SYNTAX       Integer32
            MAX-ACCESS   accessible-for-notify
            STATUS       current
            DESCRIPTION
                "This object indicates the threshold of the code words that were corrected by
                 the FEC function.
                "
            ::= { hwXponCommonTrapsVbOids 33 }
            
        hwXponAlarmUpperCountThreshold OBJECT-TYPE
            SYNTAX       Integer32
            MAX-ACCESS   accessible-for-notify
            STATUS       current
            DESCRIPTION
                "This object indicates the Upper threshold.
                "
            ::= { hwXponCommonTrapsVbOids 34 }

        hwXponAlarmLowerCountThreshold OBJECT-TYPE
            SYNTAX       Integer32
            MAX-ACCESS   accessible-for-notify
            STATUS       current
            DESCRIPTION
                "This object indicates the Lower threshold.
                "
            ::= { hwXponCommonTrapsVbOids 35 }
            
        hwXponAlarmCurrentCountValue OBJECT-TYPE
            SYNTAX       Integer32
            MAX-ACCESS   accessible-for-notify
            STATUS       current
            DESCRIPTION
                "This object indicates the Current Value.
                 -1 indicates the invalid value.
                "
            ::= { hwXponCommonTrapsVbOids 36 }    
            
        hwXponOntRegisterSn OBJECT-TYPE
            SYNTAX  OCTET STRING (SIZE (8))
            MAX-ACCESS   accessible-for-notify
            STATUS       current
            DESCRIPTION
                "This object indicates the ONT serial number.
                "
            ::= { hwXponCommonTrapsVbOids 37 }   
             
        hwFrameIndexOfNewConnectedOnt OBJECT-TYPE
            SYNTAX Integer32 (0..1024)
            MAX-ACCESS accessible-for-notify
            STATUS current
            DESCRIPTION
                "The index of a shelf in the device.
                "
            ::= { hwXponCommonTrapsVbOids 38 }    
                   
        hwSlotIndexOfNewConnectedOnt OBJECT-TYPE
            SYNTAX Integer32 (0..255)
            MAX-ACCESS accessible-for-notify
            STATUS current
            DESCRIPTION
                "
                A slot index is used to identify the location of a board in a shelf.
                "
            ::= { hwXponCommonTrapsVbOids 39 }  
             
        hwPortIndexOfNewConnectedOnt OBJECT-TYPE
            SYNTAX Integer32 (0..255)
            MAX-ACCESS accessible-for-notify
            STATUS current
            DESCRIPTION
            "
            Port index, indicating the physical number of the port on a board.
            "
            ::= { hwXponCommonTrapsVbOids 40 }   
                                                   
        hwXponOntFirstOnline OBJECT-TYPE
            SYNTAX   Integer32
            MAX-ACCESS   accessible-for-notify
            STATUS       current
            DESCRIPTION
                "This object indicates the state of rogue ONT manual detect.
                 Options:
                 1. FirstOnline(1)                 - The ont is online firstly.
                 2. NotFirstOnline(2)              - The ont is not online firstly.
                "
            ::= { hwXponCommonTrapsVbOids 41 }
            
        hwGponTypeBDParentRogueOntStatus OBJECT-TYPE
            SYNTAX   INTEGER {
                rogueOntExist(1),
                rogueOntNotExist(2)
            }
            MAX-ACCESS   accessible-for-notify
            STATUS       current
            DESCRIPTION
                "This object indicates the status of the GPON rogue ONTs.
                 Options:
                 1. rogueOntExist(1)       - GPON rogue ONTs are detected
                 2. rogueOntNotExist(2)    - GPON rogue ONTs are not detected"

            ::= { hwXponCommonTrapsVbOids 42 }
                
        hwXponDeviceOltPortList OBJECT-TYPE
            SYNTAX OCTET STRING (SIZE (0..32))
            MAX-ACCESS   accessible-for-notify
            STATUS       current
            DESCRIPTION
                "This object indicates the port list on the OLT device. The port list format is such as '0,1'."
            ::= { hwXponCommonTrapsVbOids 43 }
                 
        hwXponTrapParaOltPortState OBJECT-TYPE
            SYNTAX   INTEGER {
                up(1),
                down(2)
            }
            MAX-ACCESS   accessible-for-notify
            STATUS       current
            DESCRIPTION
                "This object indicates the state of xPON port.
                 Options:
                 1. up(1)      - Indicates that the port state is normal
                 2. down(2)    - Indicates that the port state is fail"

            ::= { hwXponCommonTrapsVbOids 44 }
            
        hwXponOltAdminState OBJECT-TYPE
            SYNTAX   INTEGER {
                on(1),
                off(2)
            }
            MAX-ACCESS   accessible-for-notify
            STATUS       current
            DESCRIPTION
                "This object indicates the admin state of xPON port.
                 Options:
                 1. on(1)      - Indicates that the admin state is up
                 2. off(2)     - Indicates that the admin state is down"

            ::= { hwXponCommonTrapsVbOids 45 }
            
        hwXponOltEnergySavingFlag OBJECT-TYPE
            SYNTAX   INTEGER {
                yes(1),
                no(2)
            }
            MAX-ACCESS   accessible-for-notify
            STATUS       current
            DESCRIPTION
                "This object indicates the energy saving flag of xPON port.
                 Options:
                 1. yes(1)    - Indicates that the xPON port is in energy saving state
                 2. no(2)     - Indicates that the xPON port is not in energy saving state"

            ::= { hwXponCommonTrapsVbOids 46 }
            
        hwGponOntPortTDMTxClock OBJECT-TYPE
            SYNTAX       INTEGER {
                adapt(1),
                system(2),
                invalid(-1)
            }
            MAX-ACCESS   accessible-for-notify
            STATUS       current
            DESCRIPTION
                "TDM port coding style
                 Options:
                 1. adapt(1)  - Indicates that the tx-clock mode of the ONT TDM port is adapt
                 2. system(2) - Indicates that the tx-clock mode of the ONT TDM port is system
                 3. invalid(-1) - Indicates that the query fails or no information is detected
                "
            ::= { hwXponCommonTrapsVbOids 47 }

        hwXponOltLosAffectOntNum OBJECT-TYPE
            SYNTAX Integer32
            MAX-ACCESS accessible-for-notify
            STATUS current
            DESCRIPTION
                "This object indicates the number of affected ONT when the los alarm occurred.
                 -1 indicates the information is invalid."
            ::= { hwXponCommonTrapsVbOids 48 }     
            
        hwXponOltLosDgiOntNum OBJECT-TYPE
            SYNTAX Integer32
            MAX-ACCESS accessible-for-notify
            STATUS current
            DESCRIPTION
                "This object indicates the number of DGi ONT when the los alarm occurred.
                 -1 indicates the information is invalid."            
            ::= { hwXponCommonTrapsVbOids 49 }            
            
        hwXponOntDosAttackProtocolType OBJECT-TYPE
            SYNTAX OCTET STRING (SIZE (1..16))      
            MAX-ACCESS   accessible-for-notify
            STATUS       current
            DESCRIPTION
                "This object indicates the protocol such as PLOAM,OAM,OMCI ,which ONT uses to perform DOS attack."
            ::= { hwXponCommonTrapsVbOids 50 }    
            
        hwXponOntDosAttackPeakTrafficValue OBJECT-TYPE
            SYNTAX Integer32
            MAX-ACCESS accessible-for-notify
            STATUS current
            DESCRIPTION
                "This object indicates the peak number of messages per second when DOS attack occurred."            
            ::= { hwXponCommonTrapsVbOids 51 }              
	
	hwXponOltTrafficAlarmProfileAlarmDetectTimes OBJECT-TYPE
            SYNTAX Integer32
            MAX-ACCESS accessible-for-notify
            STATUS current
            DESCRIPTION
                "This object indicates the alarm threshold of the congestion detection."            
            ::= { hwXponCommonTrapsVbOids 52 }
        
        hwXponOltTrafficAlarmProfileWarningDetectTimes OBJECT-TYPE
            SYNTAX Integer32
            MAX-ACCESS accessible-for-notify
            STATUS current
            DESCRIPTION
                "This object indicates the warning threshold of the congestion detection."            
            ::= { hwXponCommonTrapsVbOids 53 }    
            
        hwXponOltTrafficStatisticUpstreamCongestionTimes OBJECT-TYPE
            SYNTAX Integer32
            MAX-ACCESS accessible-for-notify
            STATUS current
            DESCRIPTION
                "This object indicates the Upstream congestion period number."            
            ::= { hwXponCommonTrapsVbOids 54 }
        
        hwXponOltTrafficStatisticDownstreamCongestionTimes OBJECT-TYPE
            SYNTAX Integer32
            MAX-ACCESS accessible-for-notify
            STATUS current
            DESCRIPTION
                "This object indicates the Downstream congestion period number."            
            ::= { hwXponCommonTrapsVbOids 55 } 
            
        hwXponOntFileUpLoadTrap NOTIFICATION-TYPE
            OBJECTS {
                hwXponOntTransmittingSerialNo,
                hwXponOntTransmittingOperType,
                ifIndex,
                hwXponOntIndex,
                hwXponOntTransmittingCrc
            }
            STATUS current
            DESCRIPTION
                "This trap is sent when the ONT file upload."
            ::= { hwXponCommonGeneralTrapsPrefix 1 }

        hwXponCommonDeviceOntRemotePingTrap NOTIFICATION-TYPE
            OBJECTS {
                hwReservedValue,
                ifIndex,
                hwXponDeviceOntIndex,
                hwXponOntIpIndex,
                hwXponCommonDeviceOntPingResult,
                hwXponCommonDeviceSentPackets,
                hwXponCommonDeviceReceivedPackets,
                hwXponCommonDeviceLostPackets,
                hwXponCommonDeviceLostRatio,
                hwXponCommonDeviceMinDelay,
                hwXponCommonDeviceMaxDelay,
                hwXponCommonDeviceAverageDelay,
                hwXponCommonDeviceReceivedICMPErrorCode
            }
            STATUS current
            DESCRIPTION
                "This trap is sent when ont remote ping."
            ::= { hwXponCommonGeneralTrapsPrefix 2 }

        hwXponPortStateChangeTrap NOTIFICATION-TYPE
            OBJECTS {
                hwFrameIndex,
                hwSlotIndex,
                hwPortIndex,
                hwPortPrimaryStatus,
                hwPortSecondaryStatus,
                hwXponTrapParaOltPortState,
                hwXponOltEnergySavingFlag
            }
            STATUS current
            DESCRIPTION
                "This trap is sent when XPON port state changed."
            ::= { hwXponCommonGeneralTrapsPrefix 3 }

        hwXponOntCfgStateChangeTrap NOTIFICATION-TYPE
            OBJECTS {
                hwFrameIndex,
                hwSlotIndex,
                hwPortIndex,
                hwXponDeviceOntIndex,
                hwXponDeviceOntControlPrimaryStatus,
                hwXponDeviceOntControlSecondaryStatus
            }
            STATUS current
            DESCRIPTION
               "This trap is sent when ont config state changed."
            ::= { hwXponCommonGeneralTrapsPrefix 4 }

        hwXponSwitchModeResultTrap NOTIFICATION-TYPE
            OBJECTS {
                hwConfigChangeIP,
                hwXponModeSwitchResult
            }
            STATUS current
            DESCRIPTION
                "This trap is sent when received xpon mode switch result."
            ::= { hwXponCommonGeneralTrapsPrefix 5 }

        hwXponConfigModeTrap NOTIFICATION-TYPE
            OBJECTS {
                hwConfigChangeIP,
                hwXponConfigMode
            }
            STATUS current
            DESCRIPTION
                "This trap is sent when XPON current config mode changed."
            ::= { hwXponCommonGeneralTrapsPrefix 6 }

        hwXponConfigChangeSnmpProfileTrap NOTIFICATION-TYPE
            OBJECTS {
                hwConfigChangeIP,
                hwXponTrapOperType,
                hwXponDeviceOntSnmpProfileNameIndex,
                hwXponDeviceOntSnmpVersion,
                hwXponDeviceOntSnmpTrapHostIP,
                hwXponDeviceOntSnmpTrapHostSrcUDPPort,
                hwXponDeviceOntSnmpReadCommunityName,
                hwXponDeviceOntSnmpWriteCommunityName,
                hwXponDeviceOntSnmpSecurityName
            }
            STATUS current
            DESCRIPTION
                "This trap is sent when SNMP profile config changed."
            ::= { hwXponCommonGeneralTrapsPrefix 7 }

        hwXponConfigPmConfigTrap NOTIFICATION-TYPE
            OBJECTS {
                hwConfigChangeIP,
                hwXponTrapOperType,
                ifIndex,
                hwXponOltMinBandwidth,
                hwXponOltNearestDistance,
                hwXponOltFarestDistance,
                hwXponOltAutoFindOntFlag,
                hwXponOltAutoUpdateOntFlag,
                hwXponOltDownFecEnableFlag,
                hwXponOltChangePasswordIntervalTime,
                hwXponOltAdminState
            }
            STATUS current
            DESCRIPTION
                "This trap is sent when XPON port config changed."
            ::= { hwXponCommonGeneralTrapsPrefix 8 }

        hwXponConfigOltTypeBDparentDelTrap NOTIFICATION-TYPE
            OBJECTS {
                hwConfigChangeIP,
                ifIndex
            }
            STATUS current
            DESCRIPTION
                "This trap is sent when a member in the Type-B dual-homing
                 protection group is deleted.
                "
            ::= { hwXponCommonGeneralTrapsPrefix 9 }

        hwGponConfigOltTypeBDparentTrap NOTIFICATION-TYPE
            OBJECTS {
                hwConfigChangeIP,
                ifIndex,
                hwXponDeviceOltDualparentJoin,
                hwXponDeviceOltDualparentFreeze,
                hwXponDeviceOltDualparentForceSwitch,
                hwXponDeviceOltDualparentWorkState,
                hwXponDeviceOltDualparentDesc
            }
            STATUS current
            DESCRIPTION
                "This trap is sent when a member in the Type-B dual-homing
                 protection group is modified.
                "
            ::= { hwXponCommonGeneralTrapsPrefix 10 }

        hwGponConfigOltTypeBDparentCreateTrap NOTIFICATION-TYPE
            OBJECTS {
                hwConfigChangeIP,
                ifIndex,
                hwXponDeviceOltDualparentJoin,
                hwXponDeviceOltDualparentFreeze,
                hwXponDeviceOltDualparentForceSwitch,
                hwXponDeviceOltDualparentWorkState,
                hwXponDeviceOltDualparentDesc
            }
            STATUS current
            DESCRIPTION
                "This trap is sent when a member in the Type-B dual-homing
                 protection group is added.
                "
            ::= { hwXponCommonGeneralTrapsPrefix 11 }

        hwGponOntPortSettingChangeTrap NOTIFICATION-TYPE
            OBJECTS {
                hwConfigChangeIP,
                hwXponTrapOperType,
                ifIndex,
                hwGponDeviceOntIndex,
                hwGponOntPortType,
                hwGponOntPortId,
                hwGponOntPortTDMCodeMode,
                hwGponOntPortManagementStatus,
                hwGponDeviceOntEthernetNegotiate,
                hwGponDeviceOntEthernetDuplexMode,
                hwGponDeviceOntEthernetSpeed,
                hwGponDeviceOntEthernetFlowCtrlSwitch,
                hwGponOntEthPortLoopback,
                hwGponOntE1PortLoopback,
                hwGponOntPortQinqMode,
                hwGponOntPortPriorityPolicy,
                hwGponOntEthPortUpStreamCarTrafficTableId,
                hwGponOntEthPortDownStreamCarTrafficTableId,
                hwGponOntPortTDMTxClock
            }
            STATUS current
            DESCRIPTION
                "This trap is sent when ont's port properties changed."
            ::= { hwXponCommonGeneralTrapsPrefix 12 }

        hwGponConfigOntPortNativeVlanTrap NOTIFICATION-TYPE
            OBJECTS {
                hwConfigChangeIP,
                hwXponTrapOperType,
                ifIndex,
                hwGponDeviceOntIndex,
                hwGponOntPortType,
                hwGponOntPortId,
                hwGponOntPortVlanDefault,
                hwGponOntPortVlanDefaultPriority
            }
            STATUS current
            DESCRIPTION
                "This trap is sent when ont's port native vlan config changed."
            ::= { hwXponCommonGeneralTrapsPrefix 13 }

        hwXponDBAProfileOperateTrap NOTIFICATION-TYPE
            OBJECTS {
                hwConfigChangeIP,
                hwXponTrapOperType,
                hwXponDeviceDbaProfileInfoNameIndex,
                hwXponDeviceDbaProfileType,
                hwXponDeviceDbaProfileBandwithCompensate,
                hwXponDeviceDbaProfileFixedRate,
                hwXponDeviceDbaProfileAssuredRate,
                hwXponDeviceDbaProfileMaxRate,
                hwXponDeviceDbaProfileFixDelay,
                hwXponDeviceDbaProfileAdditionalBW,
                hwXponDeviceDbaProfilePriority,
                hwXponDeviceDbaProfileWeight
            }
            STATUS current
            DESCRIPTION
                "This trap is sent when DBA profile operate."
            ::= { hwXponCommonGeneralTrapsPrefix 14 }

        hwXponCommonDeviceOntPppoeSimuTrap NOTIFICATION-TYPE
            OBJECTS {
                hwReservedValue,
                ifIndex,
                hwXponDeviceOntIndex,
                hwXponOntPppoeSimuPortID,
                hwXponOntPppoeSimuOuterCVlanID,
                hwXponOntPppoeOuterSimuCVlanPri,
                hwXponOntPppoeSimuResult,
                hwXponOntPppoeSimuResultSessionId,
                hwXponOntPppoeSimuResultUserIp,
                hwXponOntPppoeSimuResultGatewayIp
            }
            STATUS current
            DESCRIPTION
                "This trap is sent when PPPoE testing."
            ::= { hwXponCommonGeneralTrapsPrefix 15 }

        hwXponCommonRogueOntManualDetectTrap NOTIFICATION-TYPE
            OBJECTS {
                hwFrameIndex,
                hwSlotIndex,
                hwPortIndex,
                hwXponRogueOntManualDetectState
            }
            STATUS current
            DESCRIPTION
                "This trap is sent when rogue ONT manual detect finished."
            ::= { hwXponCommonGeneralTrapsPrefix 19 }
            
        hwXponCommonOntFirstOnlineTrap NOTIFICATION-TYPE
            OBJECTS {
                ifIndex,
                hwXponDeviceOntIndex,
                hwXponDeviceOntCRCSupport,
                hwXponDeviceOntCRCCode,
                hwGponDeviceOntVendorId,
                hwGponDeviceOntEquipmentId,
                hwGponDeviceOntMainSoftVer,
                hwGponProfOntDualUpstreamSupport,
                hwGponDeviceOntPGMemberRole,
                hwGponDeviceOntSoftwareWorkMode,
                hwGponDeviceProfOntIsOntUpfromReset,
                hwXponOntInfoSupportXmlVersion,
                hwXponOntFirstOnline,
                hwXponOntSupportVoipCfgMethod,
                hwEponDeviceAutoFindOntInfoOntExtendedModel,
                hwGponDeviceOntCustomizedInfo
            }
            STATUS current
            DESCRIPTION
                "This trap is sent when the ONT is online firstly."
            ::= { hwXponCommonGeneralTrapsPrefix 20 }
            
        hwGponTypeBDParentRogueOntStatusChangeTrap NOTIFICATION-TYPE
            OBJECTS {
                ifIndex,
                hwGponTypeBDParentRogueOntStatus
            }
            STATUS current
            DESCRIPTION
                "This trap is sent on one of these conditions:
                1.GPON rogue ONTs are detected;
                2.GPON rogue ONTs are not detected."
            ::= { hwXponCommonGeneralTrapsPrefix 21 }
                                   
         hwXponPortOtdrResultTrap NOTIFICATION-TYPE
            OBJECTS {
                hwFrameIndex,
                hwSlotIndex,
                hwPortIndex,
                hwXponDeviceOtdrTestResult
            }
            STATUS current
            DESCRIPTION
                "This trap is sent when OTDR testing."
            ::= { hwXponCommonGeneralTrapsPrefix 22 } 
              
        hwXponOntVoipConfigResultTrap NOTIFICATION-TYPE
           OBJECTS {
                ifIndex,
                hwXponDeviceOntIndex,
                hwGponDeviceOntVoipFtpCfgResult,
                hwGponDeviceOntVoipCfgFileVersion
            }
            STATUS current
            DESCRIPTION
                "This trap is sent when the the ONT report its voip configuration result."
            ::= { hwXponCommonGeneralTrapsPrefix 23 }
        
         hwGponOntNoAuthOntAutoFindTrap NOTIFICATION-TYPE
            OBJECTS {
                hwFrameIndex,
                hwSlotIndex,
                hwPortIndex,
                hwGponDeviceAutoFindOntInfoSn,
                hwGponDeviceAutoFindOntInfoPassword,
                hwGponDeviceAutoFindOntInfoOntVendorId,
                hwGponDeviceAutoFindOntInfoOntVer,
                hwGponDeviceAutoFindOntInfoOntMainSoftVer,
                hwGponDeviceAutoFindOntInfoOntEquipmentId,
                hwGponDeviceAutoFindOntInfoLoid,
                hwGponDeviceAutoFindOntInfoCheckcode,
                hwGponDeviceAutoFindOntInfoCustomizedInfo,
                hwGponDeviceAutoFindOntInfoOntNniType
            }
            STATUS current
            DESCRIPTION
                "This trap is sent when a ONT that does not need to be authenticated has
                 automatically discovered.
                "
            ::= { hwXponCommonGeneralTrapsPrefix 24 }
        
        hwEponOntNoAuthOntAutoFindTrap NOTIFICATION-TYPE
            OBJECTS {
                hwFrameIndex,
                hwSlotIndex,
                hwPortIndex,
                hwEponDeviceAutoFindOntInfoMacAddress,
                hwEponDeviceAutoFindOntInfoPasswordValue,
                hwEponDeviceAutoFindOntInfoVendorId,
                hwEponDeviceAutoFindOntInfoOntModel,
                hwEponDeviceAutoFindOntInfoSoftwareVersion,
                hwEponDeviceAutoFindOntInfoGeNumber,
                hwEponDeviceAutoFindOntInfoFeNumber,
                hwEponDeviceAutoFindOntInfoPotsNumber,
                hwEponDeviceAutoFindOntInfoTdmNumber,
                hwEponDeviceAutoFindOntInfoHardwareVersion,
                hwEponDeviceAutoFindOntInfoLoid,
                hwEponDeviceAutoFindOntInfoCheckcode,
                hwEponDeviceAutoFindOntNniType,
                hwEponDeviceAutoFindOntInfoOntExtendedModel,
                hwEponDeviceAutoFindOntInfoOuiVersion,
                hwEponDeviceAutoFindOntInfoCustomizedInfo
            }
            STATUS current
            DESCRIPTION
                "This trap is sent when a ONT that does not need to be authenticated has
                 automatically discovered.
                "
            ::= { hwXponCommonGeneralTrapsPrefix 25 }            
            
        hwXponOntSurvivalAlarmTrap NOTIFICATION-TYPE
            OBJECTS {
                hwFrameIndex,
                hwSlotIndex,
                hwPortIndex,
                hwXponOntIndex
            }
            STATUS current
            DESCRIPTION
                "The hwXponOntSurvivalAlarmTrap is sent when the work mode of the ONT is survival mode."
            ::= { hwXponOntAlarmTrapsPrefix 1 }

        hwXponOntSurvivalRecoverAlarmTrap NOTIFICATION-TYPE
            OBJECTS {
                hwFrameIndex,
                hwSlotIndex,
                hwPortIndex,
                hwXponOntIndex
            }
            STATUS current
            DESCRIPTION
                "This hwXponOntSurvivalRecoverAlarmTrap is sent when the work mode of the ONT recovers."
            ::= { hwXponOntAlarmTrapsPrefix 2 }

        hwGponOntFECUncorrectCodeWordsAlarmTrap NOTIFICATION-TYPE
            OBJECTS {
                hwFrameIndex,
                hwSlotIndex,
                hwPortIndex,
                hwXponOntIndex,
                hwXponCommonOntFECUncorrectCodeWordsThreshold,
                hwGponOntPerfHis15MinFecUncorrectCodeWords,
                hwGponOntPerfHis15MinFecTotalCodeWords
            }
            STATUS current
            DESCRIPTION
                "The hwGponOntFECUncorrectCodeWordsAlarmTrap is sent
                 when the ONT FEC Uncorrected code words exceed the threshold.
                "
            ::= { hwXponOntAlarmTrapsPrefix 3 }

        hwGponOntFECUncorrectCodeWordsRecoverAlarmTrap NOTIFICATION-TYPE
            OBJECTS {
                hwFrameIndex,
                hwSlotIndex,
                hwPortIndex,
                hwXponOntIndex,
                hwXponCommonOntFECUncorrectCodeWordsThreshold,
                hwGponOntPerfHis15MinFecUncorrectCodeWords,
                hwGponOntPerfHis15MinFecTotalCodeWords
            }
            STATUS current
            DESCRIPTION
                "This hwGponOntFECUncorrectCodeWordsRecoverAlarmTrap is sent
                 when the ONT FEC Uncorrected code words recovers.
                "
            ::= { hwXponOntAlarmTrapsPrefix 4 }

        hwGponOntFECCorrectCodeWordsAlarmTrap NOTIFICATION-TYPE
            OBJECTS {
                hwFrameIndex,
                hwSlotIndex,
                hwPortIndex,
                hwXponOntIndex,
                hwXponCommonOntFECCorrectCodeWordsThreshold,
                hwGponOntPerfHis15MinFecCorrectCodeWords,
                hwGponOntPerfHis15MinFecTotalCodeWords
            }
            STATUS current
            DESCRIPTION
                "The hwGponOntFECCorrectCodeWordsAlarmTrap is sent
                 when the ONT FEC corrected code words exceed the threshold.
                "
            ::= { hwXponOntAlarmTrapsPrefix 5 }

        hwGponOntFECCorrectCodeWordsRecoverAlarmTrap NOTIFICATION-TYPE
            OBJECTS {
                hwFrameIndex,
                hwSlotIndex,
                hwPortIndex,
                hwXponOntIndex,
                hwXponCommonOntFECCorrectCodeWordsThreshold,
                hwGponOntPerfHis15MinFecCorrectCodeWords,
                hwGponOntPerfHis15MinFecTotalCodeWords
            }
            STATUS current
            DESCRIPTION
                "This hwGponOntFECCorrectCodeWordsRecoverAlarmTrap is sent
                 when the ONT FEC corrected code words recovers.
                "
            ::= { hwXponOntAlarmTrapsPrefix 6 }
            
       hwXponNumerousOntsPowerOffRestoreAlarmTrap NOTIFICATION-TYPE
            OBJECTS {
                hwFrameIndex,
                hwSlotIndex,
                hwPortIndex,
                hwXponOntMask
            }
            STATUS current
            DESCRIPTION
                "This trap is sent when the ONTs which are powered off concurrently start to recover."
            ::= { hwXponOntAlarmTrapsPrefix 7 }
            
        hwGponOntDowiCountAlarmTrap NOTIFICATION-TYPE
            OBJECTS {
                hwFrameIndex,
                hwSlotIndex,
                hwPortIndex,
                hwXponOntIndex,
                hwXponAlarmUpperCountThreshold,
                hwXponAlarmLowerCountThreshold,
                hwXponAlarmCurrentCountValue
            }
            STATUS current
            DESCRIPTION
                "The hwGponOntDowiCountAlarmTrap is sent when an ONU transmission is received at an unexpected place within the US virtual frame."
            ::= { hwXponOntAlarmTrapsPrefix 8 }
        
        hwGponOntDowiCountRecoverAlarmTrap NOTIFICATION-TYPE
            OBJECTS {
                hwFrameIndex,
                hwSlotIndex,
                hwPortIndex,
                hwXponOntIndex,
                hwXponAlarmUpperCountThreshold,
                hwXponAlarmLowerCountThreshold,
                hwXponAlarmCurrentCountValue
            }
            STATUS current
            DESCRIPTION
                "The hwGponOntDowiCountRecoverAlarmTrap is sent when the OLT receives the ONUi Transmission in the correct position."
            ::= { hwXponOntAlarmTrapsPrefix 9 }
            
        hwGponOntRdiiAlarmTrap NOTIFICATION-TYPE
            OBJECTS {
                hwFrameIndex,
                hwSlotIndex,
                hwPortIndex,
                hwXponOntIndex
            }
            STATUS current
            DESCRIPTION
                "The hwGponOntRdiiAlarmTrap is sent when The OLT transmission is received with defects at the ONUi."
            ::= { hwXponOntAlarmTrapsPrefix 10 }
        
        hwGponOntRdiiRecoverAlarmTrap NOTIFICATION-TYPE
            OBJECTS {
                hwFrameIndex,
                hwSlotIndex,
                hwPortIndex,
                hwXponOntIndex
            }
            STATUS current
            DESCRIPTION
                "The hwGponOntRdiiRecoverAlarmTrap is sent when the OLT receives the ONUi Transmission in the correct position."
            ::= { hwXponOntAlarmTrapsPrefix 11 }
        
                hwGponOntDfiAlarmTrap NOTIFICATION-TYPE
            OBJECTS {
                hwFrameIndex,
                hwSlotIndex,
                hwPortIndex,
                hwXponOntIndex
            }
            STATUS current
            DESCRIPTION
                "This trap is sent when the deactivation failure of ONTi (DFi) occurs."
            ::= { hwXponOntAlarmTrapsPrefix 12 }
            
        hwGponOntDfiRecoverAlarmTrap NOTIFICATION-TYPE
            OBJECTS {
                hwFrameIndex,
                hwSlotIndex,
                hwPortIndex,
                hwXponOntIndex
            }
            STATUS current
            DESCRIPTION
                "This trap is sent when the deactivation failure of ONTi (DFi) recovers."
            ::= { hwXponOntAlarmTrapsPrefix 13 }

        hwXponOntRegisterInvalidAlarmTrap NOTIFICATION-TYPE
            OBJECTS {                                       
                hwFrameIndex,     
                hwSlotIndex,
                hwPortIndex,
                hwXponOntIndex,
                hwXponOntRegisterSn,
                hwFrameIndexOfNewConnectedOnt,
                hwSlotIndexOfNewConnectedOnt,
                hwPortIndexOfNewConnectedOnt
            }
            STATUS current
            DESCRIPTION
                "The hwXponOntRegisterInvalidAlarmTrap is sent when the authentication information of the ONT is invalid."
            ::= { hwXponOntAlarmTrapsPrefix 14 } 
             
        hwGponPortRangingFailureAlarmTrap NOTIFICATION-TYPE
            OBJECTS {
                hwFrameIndex,
                hwSlotIndex,
                hwPortIndex
            }
            STATUS current
            DESCRIPTION
                "This trap is sent when one or more ONTs under this port failed in ranging."
            ::= { hwXponOntAlarmTrapsPrefix 15 } 
        
        hwGponPortRangingFailureRecoverAlarmTrap NOTIFICATION-TYPE
            OBJECTS {
                hwFrameIndex,
                hwSlotIndex,
                hwPortIndex
            }
            STATUS current
            DESCRIPTION
                "This trap is sent when no ONT under this port failed in ranging."
            ::= { hwXponOntAlarmTrapsPrefix 16}
            
       hwXponProtectionGroupAPSProtocolFaultAlarmTrap NOTIFICATION-TYPE
            OBJECTS {
                hwPgGroupId 
            }
            STATUS current
            DESCRIPTION
                "This trap is sent when OLT can not receive response message of APS protocol from remote protection device or the 
                 response message of APS protocol from remote protection device indicate failure."
            ::= { hwXponOntAlarmTrapsPrefix 17}

        hwXponProtectionGroupAPSProtocolRecoveryAlarmTrap NOTIFICATION-TYPE
            OBJECTS {
                hwPgGroupId 
            }
            STATUS current
            DESCRIPTION
                "This trap is sent when the APS protocol of remote protection group recovers."
            ::= { hwXponOntAlarmTrapsPrefix 18 }
            
        hwPSGponOnuMemberStateInconsistentAlarmTrap NOTIFICATION-TYPE
            OBJECTS {
                hwPgGroupId
            }
            STATUS current
            DESCRIPTION
                "This trap is sent when the protect group member state of OLT is not consistent with ONU."
            ::= { hwXponOntAlarmTrapsPrefix 19}
       
       hwPSGponOnuMemberStateInconsistentRecoverAlarmTrap NOTIFICATION-TYPE
            OBJECTS {
                hwPgGroupId
            }
            STATUS current
            DESCRIPTION
                "This trap is sent when the protect group member state of OLT and ONU become consistent."
            ::= { hwXponOntAlarmTrapsPrefix 20}   

    hwGponOntDownstreamSDAlarmTrap NOTIFICATION-TYPE
        OBJECTS {
            hwFrameIndex,
            hwSlotIndex,
            hwPortIndex,
            hwXponOntIndex
        }
        STATUS current
        DESCRIPTION
            "This trap is sent when the downstream signal degrade (SD) of the ONT occurs."
        ::= { hwXponOntAlarmTrapsPrefix 21 }
    
    hwGponOntDownstreamSDRecoverAlarmTrap NOTIFICATION-TYPE
        OBJECTS {
            hwFrameIndex,
            hwSlotIndex,
            hwPortIndex,
            hwXponOntIndex
        }
        STATUS current
        DESCRIPTION
            "This trap is sent when the downstream signal degrade (SD) of the ONT recovers."
        ::= { hwXponOntAlarmTrapsPrefix 22 }
    
    hwGponOntDownstreamSFAlarmTrap NOTIFICATION-TYPE
        OBJECTS {
            hwFrameIndex,
            hwSlotIndex,
            hwPortIndex,
            hwXponOntIndex
        }
        STATUS current
        DESCRIPTION
            "This trap is sent when the downstream signal fail (SF) of the ONT occurs."
        ::= { hwXponOntAlarmTrapsPrefix 23 }
    
    hwGponOntDownstreamSFRecoverAlarmTrap NOTIFICATION-TYPE
        OBJECTS {
            hwFrameIndex,
            hwSlotIndex,
            hwPortIndex,
            hwXponOntIndex
        }
        STATUS current
        DESCRIPTION
            "This trap is sent when the downstream signal fail (SF) of the ONT recovers."
        ::= { hwXponOntAlarmTrapsPrefix 24 }
    
    hwGponOntTemperatureAlarmTrap NOTIFICATION-TYPE
        OBJECTS {
            hwFrameIndex,
            hwSlotIndex,
            hwPortIndex,
            hwXponOntIndex
        }
        STATUS current
        DESCRIPTION
            "This trap is sent when the ONT temperature exceeds the alarm threshold."
        ::= { hwXponOntAlarmTrapsPrefix 25 }
    
    hwGponOntTemperatureRecoverAlarmTrap NOTIFICATION-TYPE
        OBJECTS {
            hwFrameIndex,
            hwSlotIndex,
            hwPortIndex,
            hwXponOntIndex
        }
        STATUS current
        DESCRIPTION
            "This trap is sent when the ONT temperature becomes normal."
        ::= { hwXponOntAlarmTrapsPrefix 26 }
    
    hwGponOntVoltageAlarmTrap NOTIFICATION-TYPE
        OBJECTS {
            hwFrameIndex,
            hwSlotIndex,
            hwPortIndex,
            hwXponOntIndex
        }
        STATUS current
        DESCRIPTION
            "This trap is sent when the ONT voltage exceeds the alarm threshold."
        ::= { hwXponOntAlarmTrapsPrefix 27 }
    
    hwGponOntVoltageRecoverAlarmTrap NOTIFICATION-TYPE
        OBJECTS {
            hwFrameIndex,
            hwSlotIndex,
            hwPortIndex,
            hwXponOntIndex
        }
        STATUS current
        DESCRIPTION
            "This trap is sent when the ONT voltage becomes normal."
        ::= { hwXponOntAlarmTrapsPrefix 28 }
        
    hwGponOntLoociCountAlarmTrap NOTIFICATION-TYPE
       OBJECTS {
            hwFrameIndex,
            hwSlotIndex,
            hwPortIndex,
            hwXponOntIndex,
            hwXponAlarmUpperCountThreshold,
            hwXponAlarmLowerCountThreshold,
            hwXponAlarmCurrentCountValue
        }
        STATUS current
        DESCRIPTION
            "This trap is sent when the number of abnormalities occuring on the OMCI channel exceeds the threshold."
        ::= { hwXponOntAlarmTrapsPrefix 29 }
    
    hwGponOntLoociCountRecoverAlarmTrap NOTIFICATION-TYPE
        OBJECTS {
            hwFrameIndex,
            hwSlotIndex,
            hwPortIndex,
            hwXponOntIndex,
            hwXponAlarmUpperCountThreshold,
            hwXponAlarmLowerCountThreshold,
            hwXponAlarmCurrentCountValue
        }
        STATUS current
        DESCRIPTION
            "This trap is sent when the number of abnormalities occuring on the OMCI channel becomes normal."
        ::= { hwXponOntAlarmTrapsPrefix 30 }
   
    hwXponOntInitiativeDownAlarmTrap NOTIFICATION-TYPE
        OBJECTS {
            hwFrameIndex,
            hwSlotIndex,
            hwPortIndex,
            hwXponOntIndex
        }
        STATUS current
        DESCRIPTION
            "This trap is sent when the ONT initiative to go offline."
        ::= { hwXponOntAlarmTrapsPrefix 31 }
        
    hwXponOntInitiativeDownAlarmRecoverTrap NOTIFICATION-TYPE
        OBJECTS {
            hwFrameIndex,
            hwSlotIndex,
            hwPortIndex,
            hwXponOntIndex
        }
        STATUS current
        DESCRIPTION
            "This trap is sent when the ONT initiative to go offline recovers."
        ::= { hwXponOntAlarmTrapsPrefix 32 }
        
    hwGponOntPowerOverloadAlarmTrap NOTIFICATION-TYPE
        OBJECTS {
            hwFrameIndex,
            hwSlotIndex,
            hwPortIndex,
            hwXponOntIndex
        }
        STATUS current
        DESCRIPTION
            "This trap is sent when the power consumption of the ONT is overloaded."
        ::= { hwXponOntAlarmTrapsPrefix 33 }
    
    hwGponOntPowerOverloadRecoverAlarmTrap NOTIFICATION-TYPE
        OBJECTS {
            hwFrameIndex,
            hwSlotIndex,
            hwPortIndex,
            hwXponOntIndex
        }
        STATUS current
        DESCRIPTION
            "This trap is sent when the power supply of the ONT is normal."
        ::= { hwXponOntAlarmTrapsPrefix 34 }   
             
    hwXponOntDosAttackAlarmTrap NOTIFICATION-TYPE
        OBJECTS {
            hwFrameIndex,
            hwSlotIndex,
            hwPortIndex,
            hwXponOntIndex,
            hwXponOntDosAttackProtocolType,
            hwXponOntDosAttackPeakTrafficValue
        }
        STATUS current
        DESCRIPTION
            "This trap is sent when the ONT is performing a DOS attack by sending burst messages."
        ::= { hwXponOntAlarmTrapsPrefix 35 }  
        
    hwXponOntDosAttackAlarmRecoverTrap NOTIFICATION-TYPE
        OBJECTS {
            hwFrameIndex,
            hwSlotIndex,
            hwPortIndex,
            hwXponOntIndex,
            hwXponOntDosAttackProtocolType
        }
        STATUS current
        DESCRIPTION
            "This trap is sent when the ONT which has performed DOS attack becomes normal."
        ::= { hwXponOntAlarmTrapsPrefix 36 }        

	  hwGponOltTrafficUpstreamAlarmTrap NOTIFICATION-TYPE
        OBJECTS {
            hwFrameIndex,
            hwSlotIndex,
            hwPortIndex,
            hwXponOltTrafficAlarmProfileAlarmDetectTimes,
            hwXponOltTrafficStatisticUpstreamCongestionTimes
            }
        STATUS current
        DESCRIPTION
            "This trap is sent when the upstream congestion period number exceeds 
             the alarm threshold in the traffic alarm profile bound to the port."
        ::= { hwXponOltAlarmTrapsPrefix 1 }  
	            
	   hwGponOltTrafficUpstreamRecoverAlarmTrap NOTIFICATION-TYPE
        OBJECTS {
            hwFrameIndex,
            hwSlotIndex,
            hwPortIndex,
            hwXponOltTrafficAlarmProfileAlarmDetectTimes,
            hwXponOltTrafficStatisticUpstreamCongestionTimes
            }
        STATUS current
        DESCRIPTION
            "This trap is sent when the upstream congestion period number is within  
             the alarm threshold in the traffic alarm profile bound to the port."
        ::= { hwXponOltAlarmTrapsPrefix 2 }  
	            
	   hwGponOltTrafficUpstreamWarningTrap NOTIFICATION-TYPE
        OBJECTS {
            hwFrameIndex,
            hwSlotIndex,
            hwPortIndex,
            hwXponOltTrafficAlarmProfileWarningDetectTimes,
            hwXponOltTrafficStatisticUpstreamCongestionTimes
            }
        STATUS current
        DESCRIPTION
            "This trap is sent when the upstream congestion period number exceeds 
             the alarm threshold in the traffic warning profile bound to the port."
        ::= { hwXponOltAlarmTrapsPrefix 3 } 
	             
	   hwGponOltTrafficUpstreamRecoverWarningTrap NOTIFICATION-TYPE
        OBJECTS {
            hwFrameIndex,
            hwSlotIndex,
            hwPortIndex,
            hwXponOltTrafficAlarmProfileWarningDetectTimes,
            hwXponOltTrafficStatisticUpstreamCongestionTimes
            }
        STATUS current
        DESCRIPTION
            "This trap is sent when the upstream congestion period number is within
             the alarm threshold in the traffic warning profile bound to the port."
        ::= { hwXponOltAlarmTrapsPrefix 4 }       
	            
	                                          
	   hwGponOltTrafficDownstreamAlarmTrap NOTIFICATION-TYPE
        OBJECTS {
            hwFrameIndex,
            hwSlotIndex,
            hwPortIndex,
            hwXponOltTrafficAlarmProfileAlarmDetectTimes,
            hwXponOltTrafficStatisticDownstreamCongestionTimes
            } 
        STATUS current
        DESCRIPTION
            "This trap is sent when the downstream congestion period number exceeds 
             the alarm threshold in the traffic alarm profile bound to the port."
        ::= { hwXponOltAlarmTrapsPrefix 5 } 
	            
	   hwGponOltTrafficDownstreamRecoverAlarmTrap NOTIFICATION-TYPE
        OBJECTS {
            hwFrameIndex,
            hwSlotIndex,
            hwPortIndex,
            hwXponOltTrafficAlarmProfileAlarmDetectTimes,
            hwXponOltTrafficStatisticDownstreamCongestionTimes
            }
        STATUS current
        DESCRIPTION
            "This trap is sent when the downstream congestion period number is within 
             the alarm threshold in the traffic alarm profile bound to the port."
        ::= { hwXponOltAlarmTrapsPrefix 6 } 
	            
	   hwGponOltTrafficDownstreamWarningTrap NOTIFICATION-TYPE
        OBJECTS {
            hwFrameIndex,
            hwSlotIndex,
            hwPortIndex,
            hwXponOltTrafficAlarmProfileWarningDetectTimes,
            hwXponOltTrafficStatisticDownstreamCongestionTimes
            }
        STATUS current
        DESCRIPTION
            "This trap is sent when the downstream congestion period number exceeds 
             the alarm threshold in the traffic warning profile bound to the port."
        ::= { hwXponOltAlarmTrapsPrefix 7 } 
	            
	   hwGponOltTrafficDownstreamRecoverWarningTrap NOTIFICATION-TYPE
        OBJECTS {
            hwFrameIndex,
            hwSlotIndex,
            hwPortIndex,
            hwXponOltTrafficAlarmProfileWarningDetectTimes,
            hwXponOltTrafficStatisticDownstreamCongestionTimes
            }
        STATUS current
        DESCRIPTION
            "This trap is sent when the downstream congestion period number is within 
             the alarm threshold in the traffic warning profile bound to the port.W"
        ::= { hwXponOltAlarmTrapsPrefix 8 }

        hwXponPortFaultAlarmTrap NOTIFICATION-TYPE
            OBJECTS {
                hwFrameIndex,
                hwSlotIndex,
                hwPortIndex
            }
            STATUS current
            DESCRIPTION
                "This trap is sent when the service of the port is faulty.
                "
            ::= { hwXponOltAlarmTrapsPrefix 9 }

        hwXponPortFaultAlarmRecoverTrap NOTIFICATION-TYPE
            OBJECTS {
                hwFrameIndex,
                hwSlotIndex,
                hwPortIndex
            }
            STATUS current
            DESCRIPTION
                "This trap is sent when the service of the port recovers from the fault.
                "
            ::= { hwXponOltAlarmTrapsPrefix 10 }
    END
