-- ============================================================================
-- Copyright (C) 2015 by  HUAWEI TECHNOLOGIES. All rights reserved.
-- Description:  This MIB module defines MIB objects that provide H248 management.
-- Reference:  
-- Version: V1.38
-- ============================================================================

 HUAWEI-VOIP-H248-MIB DEFINITIONS ::= BEGIN
      IMPORTS
        	MODULE-IDENTITY, OBJECT-TYPE, NOTIFICATION-TYPE, private
        		FROM SNMPv2-SMI
        	MODULE-COMPLIANCE, OBJECT-GROUP, NOTIFICATION-GROUP
        		FROM SNMPv2-CONF
        	TEXTUAL-CONVENTION
        		FROM SNMPv2-TC
        	IpAddress,TimeTicks,Counter32, Integer32, Unsigned32
        		FROM SNMPv2-SMI
        	RowStatus,DisplayString
        		FROM SNMPv2-TC
        	huaweiUtility
        		FROM HUAWEI-MIB;
          
      hwVoip MODULE-IDENTITY
                LAST-UPDATED "201507090000Z"
                ORGANIZATION "Huawei Technologies Co.,Ltd."
                CONTACT-INFO                                        
                             "Huawei Industrial Base                
             	              Bantian, Longgang                     
             	              Shenzhen 518129                       
             	              People's Republic of China            
             	              Website: http://www.huawei.com        
             	              Email: support@huawei.com             
             	             "                                      
                DESCRIPTION 
                        "
                        This MIB module defines MIB objects that provide H248 management.
                        "
                --  Revision history
                REVISION     "201507090000Z"
                DESCRIPTION  "V1.38, modify the Description of hwH248MgSoftParameter38 in hwH248MgSoftParameterTable"
                
                REVISION     "201505130000Z"
                DESCRIPTION  "V1.37, modify the value range of hwH248MedGwyHeartBeatTimerCur in hwH248MedGwyCurTableTable"
                             
                REVISION     "201504230000Z"
                DESCRIPTION  "V1.36, modify the value range of hwH248MedGwyCfgHeartBeatTimer, hwH248MedGwyCurHeartBeatTimer and hwH248MedGwyheartbeatretranstimer in hwH248MedGwyConfigTable
                             modify the value range of hwH248MedGwyHeartBeatTimerCur in hwH248MedGwyCurTableTable"
                
                REVISION     "201501230000Z"
                DESCRIPTION  "V1.35, correct compile error" 
                                
                REVISION     "201412130000Z"
                DESCRIPTION  "V1.34, Add hwH248MgSoftParameter38 in hwH248MgSoftParameterTable" 
                
                REVISION     "201412060000Z"
                DESCRIPTION  "V1.33,  correct misspelt"
                
                REVISION     "201410160000Z"
                DESCRIPTION  "V1.32,  added hwH248ExtMgcTable"  
                
                REVISION     "201406280000Z"
                DESCRIPTION  "V1.31, modified the following not normative nodes to satisfy for the new OMSYS tool.     
                             ORGANIZATION     
                             hwH248MedGwyId      
                             hwH248MedGwyTransMode       
                             hwH248MedGwyOperStatus      
                             hwH248MedGwyKeepActiveFlag      
                             hwMgEphemeralTerminationCodeC
                             hwH248ParaRetransfailoption
                             hwH248MgSoftParameter1
                             hwH248MgSoftParameter15
                             hwVpuDspFailReason
                             hwVpuFeReson"  
                
                REVISION     "201402140000Z"
                DESCRIPTION  "V1.30, modified the comment of hwH248ParaSecurity"
                
                REVISION     "201402070000Z"
                DESCRIPTION  "V1.30, modified the comment of hwH248MedGwyAuthInitialKey and hwH248MedGwyAuthMgId" 
                
		REVISION     "201312160000Z"
                DESCRIPTION  "V1.29, added hwIASH248CommonTrapsPrefix to hwIASH248CommonTraps"     

                REVISION     "201312160000Z"
                DESCRIPTION  "V1.29, added hwIASH248AlarmTrapsPrefix to hwIASH248AlarmTraps"     

		REVISION     "201312160000Z"
                DESCRIPTION  "V1.29, modify the value range of hwH248MgSoftParameter16 in hwH248MgSoftParameterTable"  
		
                REVISION     "201312160000Z"
                DESCRIPTION  "V1.28, modify the attribute Max Access of hwH248MedGwyTopH248Version in hwH248MedGwyConfigTable"  
		
                REVISION     "201307090000Z"
                DESCRIPTION  "V1.28, modify the value range of hwH248MedGwyCallHoldTimer in hwH248MedGwyConfigTable"     
                                
                REVISION     "201302180000Z"
                DESCRIPTION  "V1.28, modify the value range of hwH248MgSoftParameter15, from 1-2 to 1-3"     

				REVISION     "201210110000Z"
                DESCRIPTION  "V1.27, modify the value range of hwH248MedGwyRegisterKey, hwH248MedGwyOperKeyNew in hwH248MedGwyConfigTable from 1-32 to 0-32"
            		
                REVISION     "201207160000Z"
                DESCRIPTION  "V1.26, modify the status of hwH248MgSoftParameter0 hwH248MgSoftParameter1 hwH248MgSoftParameter3 hwH248MgSoftParameter5 
                              hwH248MgSoftParameter8 hwH248MgSoftParameter9 hwH248MgSoftParameter10 hwH248MgSoftParameter12 hwH248MgSoftParameter14 hwH248MgSoftParameter17 
                              hwH248MgSoftParameter18 hwH248MgSoftParameter19 hwH248MgSoftParameter20 hwH248MgSoftParameter21 from current to deprecated"  
            		
                REVISION     "201207110000Z"
                DESCRIPTION  "V1.26, modify the value range of hwH248MedGwyCurHeartBeatTimer from 5-655 to 1-32 and the description"      
                
                REVISION     "201109290000Z"
                DESCRIPTION  "V1.25, modify the value range of hwH248ProfileNegoNameCur, hwH248MedGwyCurHeartBeatTimer and hwH248MedGwyHeartBeatTimerCur"
                
                REVISION     "201108160000Z"
                DESCRIPTION  "V1.24, added hwH248MedGwyKeepActiveFlag, hwH248MedGwyKeepActivePeriod, hwH248MgSoftParameter37"
                                
                REVISION     "201011160000Z"
                DESCRIPTION  "V1.23, modified hwH248MedGwyCfgHeartBeatTimer, revised the description errors"

                REVISION     "201009200000Z"
                DESCRIPTION  "V1.22, modified hwH248MedGwyCfgHeartBeatTimer"
                
                REVISION     "201009140000Z"
                DESCRIPTION  "V1.21, modified node description"
                            
                REVISION     "201006170000Z"
                DESCRIPTION  "V1.20, DT MIB standard, modified and fixed spell error"
    
                REVISION     "201006170000Z"
                DESCRIPTION  "V1.19, corrected the description"
                
                REVISION     "201005050000Z"
                DESCRIPTION  "V1.18, revised the errors"
    
                REVISION     "201004100000Z"
                DESCRIPTION  "V1.17, corrected the enumerate name"
    
                REVISION     "201003220000Z"
                DESCRIPTION  "V1.16, corrected test errors"
    
                REVISION     "201001300000Z"
                DESCRIPTION  "V1.15, added trap notification"
    
                REVISION     "200912180000Z"
                DESCRIPTION  "V1.14, added hwH248MedGwySigIPAddrName, hwH248MedGwyMediaIPAddrName, hwH248MedGwySigIPAddrNameCur,hwH248MedGwyMediaIPAddrNameCur,hwH248MedGwySigIPAddress1Cur, and hwH248MedGwyMediaIPAddress1Cur to support DHCP"
    
                REVISION     "200911060000Z"        
                DESCRIPTION  "V1.13, modified hwH248MgSoftParameter29's value range"    
    
                REVISION     "200910150000Z"        
                DESCRIPTION  "V1.12, added hwH248MgSoftParameter32, hwH248MgSoftParameter33 to set the minimal length of port auto register timer and MG heartbeat switch"

                       ::= { huaweiUtility 36 }
 
                       
 hwIASVoipAlarmOids OBJECT IDENTIFIER ::= { hwIASVoipTraps 1 }
 
 hwIASVoipAlarmTraps OBJECT IDENTIFIER ::= { hwIASVoipTraps 0 }

 hwIASVoipObjects OBJECT IDENTIFIER ::= { hwVoip 1 }
 
 hwIASVoipTraps OBJECT IDENTIFIER ::= { hwVoip 2 }
 
 hwIASH248TrapsVbOids OBJECT IDENTIFIER ::= { hwVoip 3 }
 
 hwIASH248Traps OBJECT IDENTIFIER ::= { hwVoip 4 }
 
 hwIASH248CommonTraps OBJECT IDENTIFIER ::= { hwIASH248Traps 1 }
 hwIASH248CommonTrapsPrefix OBJECT IDENTIFIER ::= { hwIASH248CommonTraps 0 }
 
 hwIASH248AlarmTraps OBJECT IDENTIFIER ::= { hwIASH248Traps 2 }
 hwIASH248AlarmTrapsPrefix OBJECT IDENTIFIER ::= { hwIASH248AlarmTraps 0 }   
 
 
--Start IASV500R002-SRV C003 modified hwH248MedGwyConfigTable and hwH248MedGwyCtrlTable libiao 2005-09-08 

     hwH248MedGwyConfigTable OBJECT-TYPE
     SYNTAX      SEQUENCE OF HwH248MedGwyConfigEntry
     MAX-ACCESS  not-accessible
     STATUS      current
     DESCRIPTION
       "
       This table is used to manage H248 media gateway.
       The index of this table is hwH248MedGwyId.
       "
     ::= { hwIASVoipObjects 1 }
 
     hwH248MedGwyConfigEntry OBJECT-TYPE
     SYNTAX      HwH248MedGwyConfigEntry
     MAX-ACCESS  not-accessible
     STATUS      current
     DESCRIPTION
       "
       This table is used to manage H248 media gateway.
       The index of this entry is hwH248MedGwyId.
       "
     INDEX    {  
               hwH248MedGwyId
              }
     ::= { hwH248MedGwyConfigTable 1 }
 
    HwH248MedGwyConfigEntry::=
     SEQUENCE
     {
       hwH248MedGwyId	              Integer32,
       hwH248MedGwyDomainName	      OCTET STRING,
       hwH248MedGwyDesc 	          OCTET STRING,
       hwH248MedGwySigIPAddress1	  IpAddress,
       hwH248MedGwyIPAddress2	      IpAddress,
       hwH248MedGwySigUDPPort	      Integer32,
       hwH248MedGwyProtocol	          INTEGER,
       hwH248MedGwyCodeType	          INTEGER,
       hwH248MedGwyTransMode	      INTEGER,
       hwH248MedGwyRegisterKey	      OCTET STRING,
       hwH248MedGwyOperKey	          OCTET STRING,
       hwH248MedGwyOperKeyNew	      OCTET STRING,
       hwH248MedGwyAdminStatus	      INTEGER,
       hwH248MedGwyOperStatus	      INTEGER,
       hwH248MedGwyRowStatus	      RowStatus,
       hwH248MedGwyLastChange	      TimeTicks,
       hwH248MedGwyProfile1           OCTET STRING,
       hwH248MedGwyProfile2           OCTET STRING,
       hwH248MedGwyProfile3           OCTET STRING,
       hwH248MedGwyProfileUsing       OCTET STRING,
       hwH248MedGwyTopH248Version     INTEGER,
       hwH248MedGwyCurH248Version     INTEGER,
       hwH248MedGwyCurUsedDspNum      Integer32,
       hwH248MedGwyAuthInitialKey     OCTET STRING,
       hwH248MedGwyAuthMgId           OCTET STRING,
       hwH248MedGwyAuthAlgorithm      INTEGER,
       hwH248MedGwy2833Encrypt        OCTET STRING,
       hwH248MedGwyCfgHeartBeatTimer  Integer32,
       hwH248MedGwyCurHeartBeatTimer  Integer32,
       hwH248MedGwyCallHoldTimer      Integer32,
       hwH248MedGwyMediaIPAddress1    IpAddress,
       hwH248MedGwyMIDType            INTEGER,
       hwH248MedGwyDeviceName         OCTET STRING,
       hwH248MedGwyheartbeattimes     Integer32,
       hwH248MedGwyheartbeatretranstimer Integer32,
       hwH248MedGwyCurMIDType         INTEGER,
       hwH248MedGwyCurDeviceName      OCTET STRING,
       hwH248MedGwyGracefulTimer      Integer32,
       hwH248MedGwyBeginNegotiationH248Version  Integer32,
       hwH248MedGwyProfileIndex	      Integer32,
       hwH248MedGwyProfileIndexUsing  Integer32,
       hwH248ProfileParaNegotiationSupport INTEGER,
       hwH248MgProfileCfgName       OCTET STRING,
       hwH248MgProfileNegoName      OCTET STRING,
       hwH248MedGwyMediaIPAddress2	  IpAddress,
       hwH248MedGwyOperReasonCode     Integer32,
       hwH248MedGwySigIPAddrDhcpClientIndex  Integer32,
       hwH248MedGwyMediaIPAddrDhcpClientIndex  Integer32,
       hwH248MedGwyRestrans                    INTEGER,
       hwH248MedGwySigIPAddrName                OCTET STRING,  
       hwH248MedGwyMediaIPAddrName            OCTET STRING,
       hwH248MedGwyKeepActiveFlag     INTEGER,
       hwH248MedGwyKeepActivePeriod   Integer32
     }
 
   hwH248MedGwyId OBJECT-TYPE
     SYNTAX      Integer32(0..16777215)
     MAX-ACCESS  accessible-for-notify
     STATUS      current
     DESCRIPTION
         "
         Media Gateway ID.
         "
     ::= { hwH248MedGwyConfigEntry 1 }

   hwH248MedGwyDomainName OBJECT-TYPE
     SYNTAX      OCTET STRING(SIZE (0..64))
     MAX-ACCESS  read-write
     STATUS      current
     DESCRIPTION
         "
         Indicates the domain name of the MG, null means clear the value of this parameter.
         "
     ::= { hwH248MedGwyConfigEntry 2 }
 
   hwH248MedGwyDesc OBJECT-TYPE
     SYNTAX      OCTET STRING(SIZE (0..32))
     MAX-ACCESS  read-write
     STATUS      current
     DESCRIPTION
         "
         Indicates the interface description.
         "
     ::= { hwH248MedGwyConfigEntry 3 }
        
     hwH248MedGwySigIPAddress1 OBJECT-TYPE
     SYNTAX      IpAddress
     MAX-ACCESS  read-write
     STATUS      current
     DESCRIPTION
         "
         Indicates the signaling IP address of the MG.
         "
     ::= { hwH248MedGwyConfigEntry 4 }
 
   hwH248MedGwyIPAddress2 OBJECT-TYPE
     SYNTAX      IpAddress
     MAX-ACCESS  read-write
     STATUS      current
     DESCRIPTION
         "
         The second IP address that the Media Gateway Controller will use to communicate with the Media Gateway. 
         The system does not support setting it now.
         "
     ::= { hwH248MedGwyConfigEntry 5 }
 
   hwH248MedGwySigUDPPort OBJECT-TYPE
     SYNTAX      Integer32(2900..2999|65535)
     MAX-ACCESS  read-write
     STATUS      current
     DESCRIPTION
         "
         Signalling UDP port that the Media Gateway Controller will use to communicate with the Media Gateway.
         65535 means this parameter is not configurated.
         "
     ::= { hwH248MedGwyConfigEntry 6 }
 
   hwH248MedGwyProtocol OBJECT-TYPE
     SYNTAX      INTEGER{h248(1)}
     MAX-ACCESS  read-only
     STATUS      current
     DESCRIPTION
         "
         Type of the control protocol in use.
         Options:
         1. h248(1) -H.248
         "
     ::= { hwH248MedGwyConfigEntry 7 }
 
   hwH248MedGwyCodeType OBJECT-TYPE
     SYNTAX      INTEGER{
                         txt(1), -- text
                         bin(2)  -- binary
                        } 
     MAX-ACCESS  read-write
     STATUS      current
     DESCRIPTION
         "
         Indicates the coding type.
         Options:
         1. txt(1) -text
         2. bin(2) -binary
         "
     ::= { hwH248MedGwyConfigEntry 8 }
   hwH248MedGwyTransMode OBJECT-TYPE
     SYNTAX      INTEGER{
                         noConfig(-1),
                         tcp(1),      -- tcp
                         udp(2),      -- udp
                         alfUdp(3),  -- udp with alf
                         sctp(4)      -- sctp
                         }     
     MAX-ACCESS  read-write
     STATUS      current
     DESCRIPTION
         "
         Indicates the transmission mode.
         Options:
         1. noConfig(-1) -not configured
         2. tcp(1) -tcp
         3. udp(2) -udp
         4. alfUdp(3) -udp with alf
         5. sctp(4) -sctp
         "
     ::= { hwH248MedGwyConfigEntry 9 }
 
   hwH248MedGwyRegisterKey OBJECT-TYPE
     SYNTAX      OCTET STRING(SIZE (0..32))
     MAX-ACCESS  read-write
     STATUS      current
     DESCRIPTION
         "
         Indicates the key that is registered with the MGC. The key cannot be modified, read, or written by the operator without authority, so the hwH248MedGwyRegisterKey and hwH248MedGwyOperKey must be also provided to query and modify the hwH248MedGwyRegisterKey. The conditions for querying and modifying the hwH248MedGwyRegisterKey are as follows: 1) The hwH248MedGwyRegisterKey can return the correct query result only when the hwH248MedGwyOperKey is correct. Otherwise, the query fails; 2) The hwH248MedGwyRegisterKey can be set successfully only when the hwH248MedGwyOperKey is correct. Otherwise, the setting fails.
         This parameters must be 8..32 characters long to set. 
         0 indicate invalid string.
         "
     ::= { hwH248MedGwyConfigEntry 10 }
 
   hwH248MedGwyOperKey OBJECT-TYPE
     SYNTAX      OCTET STRING(SIZE (0..32))
     MAX-ACCESS  read-only
     STATUS      current
     DESCRIPTION
         "
         Indicates the key for operating the MG. The hwH248MedGwyOperKey cannot be read. The functions of this key are as follows: 1) The hwH248MedGwyRegisterKey and hwH248MedGwyOperKey must be provided for modifying the hwH248MedGwyRegisterKey. The hwH248MedGwyRegisterKey can return the correct query result only when the hwH248MedGwyOperKey is correct. Otherwise, the query fails. The hwH248MedGwyRegisterKey can be set successfully only when the hwH248MedGwyOperKey is correct. Otherwise, the setting fails. 2) The hwH248MedGwyOperKey must work with the hwH248MedGwyOperKeyNew for modifying the hwH248MedGwyOperKey itself. The hwH248MedGwyOperKeyNew and hwH248MedGwyOperKey must be provided at the same time. The value of the hwH248MedGwyOperKeyNew can replace the value of the hwH248MedGwyOperKey and the hwH248MedGwyOperKeyNew can become the new operation key only when the hwH248MedGwyOperKey is correct. Otherwise, the modification fails and the hwH248MedGwyOperKey operation key is retained.
         "
     ::= { hwH248MedGwyConfigEntry 11 }
 
   hwH248MedGwyOperKeyNew OBJECT-TYPE
     SYNTAX      OCTET STRING(SIZE (0..32))
     MAX-ACCESS  read-write
     STATUS      current
     DESCRIPTION
         "
         Indicates the new operation key. The hwH248MedGwyOperKeyNew is a temporary variable, and cannot be read. If you query one hwH248MedGwyOperKeyNew, the system always returns a null value.
         This parameters must be 8..32 charactor long to set.
         0 indicate invalid string.
         "
     DEFVAL      { ''b }
     ::= { hwH248MedGwyConfigEntry 12 }
 
   hwH248MedGwyAdminStatus OBJECT-TYPE
     SYNTAX      INTEGER{up(1),                -- normal
                         down(2),              -- disconnect with MGC
                         resetrestortserve(3), -- restore service
                         reset(4),             -- cold boot
                         shutdownforce(5),     -- force to shutdowm
                         shutdowngraceful(6)   -- graceful shutdown
                         }
     MAX-ACCESS  read-write
     STATUS      current
     DESCRIPTION
         "
         Administrative status for this media gateway control group.
         The default reason code relates to the status is as follows:
            reset             -- ColdBoot(901)
            shutdown force    -- TerminationTakenOutOfService(905)
            shutdown graceful -- MGImpendingFailure(908)
         Options:
         1. up(1) -normal, invalid in P300 product
         2. down(2) -disconnect with MGC, invalid in P300 product
         3. resetrestortserve(3) -restore service
         4. reset(4) -cold reboot
         5. shutdownforce(5) -force to shutdowm
         6. shutdowngraceful(6) -graceful shutdown
         "
     ::= { hwH248MedGwyConfigEntry 13 } 
      
     hwH248MedGwyOperStatus OBJECT-TYPE
     SYNTAX      INTEGER{
                         up(1),             -- normal
                         localClosed(2),   -- local closed
                         fault(3),          -- fault
                         waitingAck(4),    -- waiting for ack
                         unknown(5),        -- unknown
                         notStart(6),      -- not start
                         remoteClosed(7),  -- remote closed
                         gracefulClosed(8) -- graceful closed
                         }
     MAX-ACCESS  read-only
     STATUS      current
     DESCRIPTION
         "
         Current operational status of the signaling link.
         Options:
         1. up(1) -normal
         2. localClosed(2) -local closed
         3. fault(3) -fault
         4. waitingAck(4) -waiting for ack
         5. unknown(5) -unknown
         6. notStart(6) -not start
         7. remoteClosed(7) -remote closed
         8. gracefulClosed(8) -graceful closed
         "
     ::= { hwH248MedGwyConfigEntry 14 }
 
   hwH248MedGwyRowStatus OBJECT-TYPE
     SYNTAX      RowStatus
     MAX-ACCESS  read-write
     STATUS      current
     DESCRIPTION
         "
         This is used to create new rows in this table, modify existing rows, and delete existing rows.
         "
     ::= { hwH248MedGwyConfigEntry 15 }
 
   hwH248MedGwyLastChange OBJECT-TYPE
     SYNTAX      TimeTicks
     MAX-ACCESS  read-only
     STATUS      current
     DESCRIPTION
         "
         The value of sysUpTime at the time the associated link entered its current operational status. If the current status was entered prior to the last re-initialization of the local network management subsystem, then this object contains a zero value.
         "
     ::= { hwH248MedGwyConfigEntry 16 }
     
   hwH248MedGwyProfile1 OBJECT-TYPE
     SYNTAX      OCTET STRING(SIZE (1..67))
     MAX-ACCESS  read-write
     STATUS      obsolete
     DESCRIPTION
         "
         Indicates the name of the first H.248 profile of the MG (including / + version; version is a number).
         "
     ::= { hwH248MedGwyConfigEntry 17 }
   
    hwH248MedGwyProfile2 OBJECT-TYPE
     SYNTAX      OCTET STRING(SIZE (1..67))
     MAX-ACCESS  read-write
     STATUS      obsolete
     DESCRIPTION
         "
         Indicates the name of the second H.248 profile of the MG (including / + version; version is a number).
         "
     ::= { hwH248MedGwyConfigEntry 18 } 
     hwH248MedGwyProfile3 OBJECT-TYPE
     SYNTAX      OCTET STRING(SIZE (1..67))
     MAX-ACCESS  read-write
     STATUS      obsolete
     DESCRIPTION
         "
         Indicates the name of the third H.248 profile of the MG (including / + version; version is a number).
         "
     ::= { hwH248MedGwyConfigEntry 19 }  
  
     
    
    hwH248MedGwyProfileUsing    OBJECT-TYPE
     SYNTAX      OCTET STRING(SIZE (1..67))
     MAX-ACCESS  read-only
     STATUS      obsolete
     DESCRIPTION
         "
         Indicates the name of the profile that is currently in use.
         "
     ::= { hwH248MedGwyConfigEntry 20 } 
     
    hwH248MedGwyTopH248Version  OBJECT-TYPE
     SYNTAX      INTEGER{v1(1),v2(2),v3(3)}
     MAX-ACCESS  read-only
     STATUS      obsolete
     DESCRIPTION
         "
         Indicates the latest H.248 version that is supported by the MG. In the P300, this parameter is read-only.
         Options:
         1. v1(1) -version 1
         2. v2(2) -version 2
         3. v3(3) -version 3
         "
     ::= { hwH248MedGwyConfigEntry 21 } 
    
   hwH248MedGwyCurH248Version   OBJECT-TYPE
     SYNTAX      INTEGER{v1(1),v2(2),v3(3)}
     MAX-ACCESS  read-only
     STATUS      current
     DESCRIPTION
         "
         Indicates the current H.248 version of the MG.
         Options:
         1. v1(1) -version 1
         2. v2(2) -version 2
         3. v3(3) -version 3
         "
     ::= { hwH248MedGwyConfigEntry 22 }  
   
   hwH248MedGwyCurUsedDspNum   OBJECT-TYPE
     SYNTAX      Integer32(0..1000)
     MAX-ACCESS  read-only
     STATUS      current
     DESCRIPTION
         "
         Indicates the count of currently occupied DSPs of the interface.
         "
     ::= { hwH248MedGwyConfigEntry 23 }
      hwH248MedGwyAuthInitialKey    OBJECT-TYPE
     SYNTAX      OCTET STRING(SIZE (1..16))
     MAX-ACCESS  read-write
     STATUS      current
     DESCRIPTION
         "
         Indicates the authentication initial key.
         Default:0123456789ABCDEF
         "
     ::= { hwH248MedGwyConfigEntry 24 } 
     
   hwH248MedGwyAuthMgId    OBJECT-TYPE
     SYNTAX      OCTET STRING(SIZE (1..16))
     MAX-ACCESS  read-write
     STATUS      current
     DESCRIPTION
         "
         Indicates the authentication MG ID.
         Default:AG
         "
     ::= { hwH248MedGwyConfigEntry 25 } 
     
   hwH248MedGwyAuthAlgorithm  OBJECT-TYPE
     SYNTAX      INTEGER{md5(1)}
     MAX-ACCESS  read-only
     STATUS      current
     DESCRIPTION
         "
         Indicates the authentication encryption algorithm.
         Options:
         1. md5(1) -MD5
         "
     ::= { hwH248MedGwyConfigEntry 26 } 
    
   hwH248MedGwy2833Encrypt    OBJECT-TYPE
     SYNTAX      OCTET STRING(SIZE (0..16))
     MAX-ACCESS  read-write
     STATUS      current
     DESCRIPTION
         "
         Indicates the 2833 encryption key.
         "
     ::= { hwH248MedGwyConfigEntry 27 } 

   hwH248MedGwyCfgHeartBeatTimer  OBJECT-TYPE
     SYNTAX      Integer32(1..65535)
     MAX-ACCESS  read-write
     STATUS      current
     DESCRIPTION
         "
         Indicates the configured timer of the initial heartbeat.
         Unit: second
         "
     ::= { hwH248MedGwyConfigEntry 28 } 
     
   hwH248MedGwyCurHeartBeatTimer  OBJECT-TYPE
     SYNTAX      Integer32(0|1..65535)
     MAX-ACCESS  read-only
     STATUS      current
     DESCRIPTION
         "
         Indicates the current timer of the initial heartbeat.
         The valid value range is 1..65535, if the value is 0, the heartbeat is not started.
         Unit: second
         "
     ::= { hwH248MedGwyConfigEntry 29 } 
   hwH248MedGwyCallHoldTimer  OBJECT-TYPE
     SYNTAX      Integer32(0..86400)
     MAX-ACCESS  read-only
     STATUS      current
     DESCRIPTION
         "
         Indicates the timer of holding the call after the MG interface is interrupted.
         Unit: second
         "
     ::= { hwH248MedGwyConfigEntry 30 } 
    hwH248MedGwyMediaIPAddress1 OBJECT-TYPE
     SYNTAX      IpAddress
     MAX-ACCESS  read-write
     STATUS      current
     DESCRIPTION
         "
         Indicates the first media IP address of the MG.
         "
     ::= { hwH248MedGwyConfigEntry 31 }
     hwH248MedGwyMIDType OBJECT-TYPE
     SYNTAX      INTEGER{ip4Address(1), -- IP address 
                         domainName(2), -- domain name
                         deviceName(3)  -- device name
                         }
     MAX-ACCESS  read-write
     STATUS      current
     DESCRIPTION
         "
         Indicates the MID type of the MG message.
         Options:
         1. ip4Address(1) -IP address
         2. domainName(2) -domain name
         3. deviceName(3) -device name
         "
     ::= { hwH248MedGwyConfigEntry 32 }
     hwH248MedGwyDeviceName OBJECT-TYPE
     SYNTAX      OCTET STRING(SIZE (0..64))
     MAX-ACCESS  read-write
     STATUS      current
     DESCRIPTION
         "
         Indicates the name of the MG device.
         "
     ::= { hwH248MedGwyConfigEntry 33 }
     hwH248MedGwyheartbeattimes OBJECT-TYPE
     SYNTAX      Integer32(0..20)
     MAX-ACCESS  read-write
     STATUS      current
     DESCRIPTION
         "
         Indicates the count of heartbeat re-transmission.
         "
     ::= { hwH248MedGwyConfigEntry 34 }
     
   hwH248MedGwyheartbeatretranstimer OBJECT-TYPE
     SYNTAX      Integer32(0..65535)
     MAX-ACCESS  read-write
     STATUS      current
     DESCRIPTION
         "
         Indicates the interval of heartbeat re-transmission.
         "
     ::= { hwH248MedGwyConfigEntry 35 }     
     
   hwH248MedGwyCurMIDType OBJECT-TYPE
     SYNTAX      INTEGER{ip4Address(1), -- IP address
                         domainName(2), -- domain name
                         deviceName(3)} -- device name
     MAX-ACCESS  read-only
     STATUS      current
     DESCRIPTION
         "
         Indicates the current MID type of the MG message.
         Options:
         1. ip4Address(1) -IP address
         2. domainName(2) -domain name
         3. deviceName(3) -device name
         "
     ::= { hwH248MedGwyConfigEntry 36 }
     
   hwH248MedGwyCurDeviceName OBJECT-TYPE
     SYNTAX      OCTET STRING(SIZE (0..64))
     MAX-ACCESS  read-only
     STATUS      current
     DESCRIPTION
         "
         Indicates the current name of the MG device.
         "
     ::= { hwH248MedGwyConfigEntry 37 }          
     
   hwH248MedGwyGracefulTimer OBJECT-TYPE
     SYNTAX      Integer32(0..86400)
     MAX-ACCESS  read-write
     STATUS      current
     DESCRIPTION
         "
         Indicates the graceful timer of the MG interface.
         This parameter is effective only when it is delivered with the shutdown graceful command.
         0 means no time limit.
         Unit: second.         
         "
     ::= { hwH248MedGwyConfigEntry 38 }
     hwH248MedGwyBeginNegotiationH248Version OBJECT-TYPE
     SYNTAX      Integer32(0..3)
     MAX-ACCESS  read-write
     STATUS      current
     DESCRIPTION
         "
         Indicates the H.248 version at the beginning of the negotiation.
         0:depend on profile
         1:v1
         2:v2
         3:v3
         "
     ::= { hwH248MedGwyConfigEntry 39 }  
  hwH248MedGwyProfileIndex OBJECT-TYPE
     SYNTAX      Integer32(0..254)
     MAX-ACCESS  read-write
     STATUS      current
     DESCRIPTION
         "
         Indicates the profile index configured for the MG. This parameter is effective only after the MG is reset.
         "
     ::= { hwH248MedGwyConfigEntry 40 }
     
   hwH248MedGwyProfileIndexUsing OBJECT-TYPE
     SYNTAX      Integer32(0..254)
     MAX-ACCESS  read-only
     STATUS      current
     DESCRIPTION
         "
         Indicates the profile index that is currently used by the MG.
         "
     ::= { hwH248MedGwyConfigEntry 41 }
   hwH248ProfileParaNegotiationSupport OBJECT-TYPE
     SYNTAX      INTEGER{disable(1), enable(2)}
     MAX-ACCESS  read-write
     STATUS      current
     DESCRIPTION
         "
         Indicates whether the MG supports the negotiated profile parameters.
         Options:
         1. disable(1) -not support
         2. enable(2)  -support
         "
     ::= { hwH248MedGwyConfigEntry 42 }
     
   hwH248MgProfileCfgName OBJECT-TYPE
   SYNTAX      OCTET STRING(SIZE (1..67))
   MAX-ACCESS  read-only
   STATUS      current
   DESCRIPTION
       "
       Indicates the configured name of the H.248 profile of the MG.
       "
   ::= { hwH248MedGwyConfigEntry 43 }
   hwH248MgProfileNegoName OBJECT-TYPE
   SYNTAX      OCTET STRING(SIZE (0..67))
   MAX-ACCESS  read-only
   STATUS      current
   DESCRIPTION
       "
       Indicates the negotiated name of the H.248 profile of the MG.
       "
   ::= { hwH248MedGwyConfigEntry 44 }
   hwH248MedGwyMediaIPAddress2 OBJECT-TYPE
   SYNTAX      IpAddress
   MAX-ACCESS  read-write
   STATUS      current
   DESCRIPTION
       "
       Indicates the second media IP of MG.
       "
   ::= { hwH248MedGwyConfigEntry 45 }  
   
   hwH248MedGwyOperReasonCode OBJECT-TYPE
   SYNTAX      Integer32(-1|1..6)
   MAX-ACCESS  read-write
   STATUS      current
   DESCRIPTION
       "
       Indicates the reason code of reset or shutdown interface.It's valid when set hwH248MedGwyAdminStatus to 4,5 or 6 at the same time.
       The leaf is optional,if not set,use the default reason code relates to the status, and the leaf  does not support get.
       And the leaf is valid begin with VSPV200R002 version.
       1:ServiceRestored(900)      --reason code of reset MG interface
       2:ColdBoot(901)             --reason code of reset MG interface
       3:WarmBoot(902)             --reason code of reset MG interface
       4:TerminationTakenOutOfService(905)   --reason code of shutdown MG interface
       5:MGImpendingFailure(908)             --reason code of shutdown MG interface
       6:CapabilitiesChange(917)   --reason code of reset MG interface.
       If the value of the ACCESS clause is 'write-only',
       then the value of the MAX-ACCESS clause MUST be 'read-write', 
       and the DESCRIPTION clause SHALL note that reading this 
       object will result in implementation-specific results."

   ::= { hwH248MedGwyConfigEntry 46 } 
   hwH248MedGwySigIPAddrDhcpClientIndex OBJECT-TYPE
   SYNTAX      Integer32(-1|1..4093)
   MAX-ACCESS  read-write
   STATUS      current
   DESCRIPTION
       "
       Dhcp Signal vlan id.
       The valid value range is 1..4093,if the value is -1, the static signal ip will be used.
       "
   ::= { hwH248MedGwyConfigEntry 47 }
   hwH248MedGwyMediaIPAddrDhcpClientIndex OBJECT-TYPE
   SYNTAX      Integer32(-1|1..4093)
   MAX-ACCESS  read-write
   STATUS      current
   DESCRIPTION
       "
       Dhcp Media vlan id.
       The valid value range is 1..4093,if the value is -1, the static media ip will be used.
       "
   ::= { hwH248MedGwyConfigEntry 48 }
    hwH248MedGwyRestrans OBJECT-TYPE
   SYNTAX      INTEGER{enable(1), disable(2)}
   MAX-ACCESS  read-write
   STATUS      current
   DESCRIPTION
       "
       Indicates whether the MG supports retrans.
       Options:
       1. enable(1)  -support
       2. disable(2) -not support
       "
   ::= { hwH248MedGwyConfigEntry 49 }   
   
   hwH248MedGwySigIPAddrName OBJECT-TYPE
   SYNTAX      OCTET STRING(SIZE (0..64))
   MAX-ACCESS  read-write
   STATUS      current
   DESCRIPTION
       "
       Dynamic signal IP name.
       "     

   ::= { hwH248MedGwyConfigEntry 50 }   
   
   hwH248MedGwyMediaIPAddrName OBJECT-TYPE
   SYNTAX      OCTET STRING(SIZE (0..64))
   MAX-ACCESS  read-write
   STATUS      current
   DESCRIPTION
       "
       Dynamic media IP name.
       "     
   
   
   ::= { hwH248MedGwyConfigEntry 51 }      

   hwH248MedGwyKeepActiveFlag OBJECT-TYPE
   SYNTAX      INTEGER{enable(1), disable(2)}
   MAX-ACCESS  read-write
   STATUS      current
   DESCRIPTION
       "
       The switch for transfer connect regular renovate.
       Options:
       1. enable(1)  -enable
       2. disable(2) -disable
       Default: disable(2)
       "     
       DEFVAL     { disable }
   ::= { hwH248MedGwyConfigEntry 52 }      
   
   hwH248MedGwyKeepActivePeriod OBJECT-TYPE
   SYNTAX      Integer32(1..3600)
   MAX-ACCESS  read-write
   STATUS      current
   DESCRIPTION
       "
       Indicates the configured period of transfer connect regular renovate.
       Unit: second
       Default:30
       "     
       DEFVAL     { 30 }
   ::= { hwH248MedGwyConfigEntry 53 }    
     
   hwH248MedGwyCtrlTable OBJECT-TYPE
     SYNTAX      SEQUENCE OF HwH248MedGwyCtrlEntry
     MAX-ACCESS  not-accessible
     STATUS      current
     DESCRIPTION
       "
       This table is used to config addresses of Media Gateway Controllers.
       The indexes of this table are hwH248MedGwyCtrlGatewayId, hwH248MedGwyCtrlIdx.
       "
     ::= { hwIASVoipObjects 2 }
 
   hwH248MedGwyCtrlEntry OBJECT-TYPE
     SYNTAX      HwH248MedGwyCtrlEntry
     MAX-ACCESS  not-accessible
     STATUS      current
     DESCRIPTION
       "
       This table is used to config addresses of Media Gateway Controllers.
       The indexes of this entry are hwH248MedGwyCtrlGatewayId, hwH248MedGwyCtrlIdx.
       "
     INDEX    {  
               hwH248MedGwyCtrlGatewayId,
               hwH248MedGwyCtrlIdx
              }
     ::= { hwH248MedGwyCtrlTable 1 }
 
   HwH248MedGwyCtrlEntry ::=
     SEQUENCE
     {
       hwH248MedGwyCtrlGatewayId	Integer32,
       hwH248MedGwyCtrlIdx	Integer32,
       hwH248MedGwyCtrlIPAddress	IpAddress,
       hwH248MedGwyCtrlDnsName	OCTET STRING,
       hwH248MedGwyCtrlDnsIp	IpAddress,
       hwH248MedGwyCtrlPort	Integer32,
       hwH248MedGwyCtrlAdminStatus	INTEGER,
       hwH248MedGwyCtrlOperStatus	INTEGER,
       hwH248MedGwyCtrlRowStatus	RowStatus,
       hwH248MedGwyCtrlLastChange	TimeTicks,
       hwH248MedGwyCtrlIPAddress2	IpAddress
     }
 
   hwH248MedGwyCtrlGatewayId OBJECT-TYPE
     SYNTAX      Integer32(0..16777215)
     MAX-ACCESS  not-accessible
     STATUS      current
     DESCRIPTION
         "
         Indicates the MG ID.
         "
     ::= { hwH248MedGwyCtrlEntry 1 }
 
   hwH248MedGwyCtrlIdx OBJECT-TYPE
     SYNTAX      Integer32(0..2)
     MAX-ACCESS  not-accessible
     STATUS      current
     DESCRIPTION
         "
         Indicates the MGC index.
         "
     ::= { hwH248MedGwyCtrlEntry 2 }
 
   hwH248MedGwyCtrlIPAddress OBJECT-TYPE
     SYNTAX      IpAddress
     MAX-ACCESS  read-write
     STATUS      current
     DESCRIPTION
         "
         The IP address of the Media Gateway Controller. The value 255.255.255.255 is returned if the entry is invalid.
         "
     ::= { hwH248MedGwyCtrlEntry 3 }
 
   hwH248MedGwyCtrlDnsName OBJECT-TYPE
     SYNTAX      OCTET STRING(SIZE (0..64))
     MAX-ACCESS  read-write
     STATUS      current
     DESCRIPTION
         "
         Indicates the DNS name of the MGC.
         "
     ::= { hwH248MedGwyCtrlEntry 4 }
 
   hwH248MedGwyCtrlDnsIp OBJECT-TYPE
     SYNTAX      IpAddress
     MAX-ACCESS  read-only
     STATUS      current
     DESCRIPTION
         "
         Indicates the IP address that is obtained through the MGC domain name.
         DEFVAL  { false }
         "
     
     ::= { hwH248MedGwyCtrlEntry 5 }
 
   hwH248MedGwyCtrlPort OBJECT-TYPE
     SYNTAX      Integer32(1..65535)
     MAX-ACCESS  read-write
     STATUS      current
     DESCRIPTION
         "
         UDP port of the Media Gateway Controller. The value 65535 is returned if the entry is invalid.
         "
     ::= { hwH248MedGwyCtrlEntry 6 }
 
   hwH248MedGwyCtrlAdminStatus OBJECT-TYPE
     SYNTAX      INTEGER{active(1)}
     MAX-ACCESS  read-write
     STATUS      current
     DESCRIPTION
         "
         Indicates to set the MGC as the active MGC.
         Options:
         1. active(1) -active state
         "
     ::= { hwH248MedGwyCtrlEntry 7 }
 
   hwH248MedGwyCtrlOperStatus OBJECT-TYPE
     SYNTAX      INTEGER{up(1),     -- up
                         down(2),   -- down
                         standby(3) -- standby
                         }
     MAX-ACCESS  read-only
     STATUS      current
     DESCRIPTION
         "
         Status of the Media Gateway Controller (and/or) its transportLink.
         Options:
         1. up(1)      -normal
         2. down(2)    -fault
         3. standby(3) -standby
         "
     ::= { hwH248MedGwyCtrlEntry 8 }
 
   hwH248MedGwyCtrlRowStatus OBJECT-TYPE
     SYNTAX      RowStatus
     MAX-ACCESS  read-write
     STATUS      current
     DESCRIPTION
         "
         Indicates the row status.
         "
     ::= { hwH248MedGwyCtrlEntry 9 }
 
   hwH248MedGwyCtrlLastChange OBJECT-TYPE
     SYNTAX      TimeTicks
     MAX-ACCESS  read-only
     STATUS      current
     DESCRIPTION
         "
         The value of sysUpTime at the time the associated link entered its current operational status. If the current status was entered prior to the last re-initialization of the local network management subsystem, then this object contains a zero value.
         "
     ::= { hwH248MedGwyCtrlEntry 10 }
     
   hwH248MedGwyCtrlIPAddress2 OBJECT-TYPE
     SYNTAX      IpAddress
     MAX-ACCESS  read-write
     STATUS      current
     DESCRIPTION
         "         
         The IP address of the Media Gateway Controller for SCTP dual homing. The value 255.255.255.255 is returned if the entry is invalid.
         "
     ::= { hwH248MedGwyCtrlEntry 11 }  
       
 --  End IASV500R002-SRV C003 modified hwH248MedGwyConfigTable and hwH248MedGwyCtrlTable libiao 2005-09-08
    
       
   hwMgPhyTerminationCfgTable OBJECT-TYPE
     SYNTAX      SEQUENCE OF HwMgPhyTerminationCfgEntry
     MAX-ACCESS  not-accessible
     STATUS      current
     DESCRIPTION
       "
       This table is used to config the physical termination of the MG.
       The index of this table is hwMgPhyTerminationIndex.
       "
     ::= { hwIASVoipObjects 3 }
 
   hwMgPhyTerminationCfgEntry OBJECT-TYPE
     SYNTAX      HwMgPhyTerminationCfgEntry
     MAX-ACCESS  not-accessible
     STATUS      current
     DESCRIPTION
       "
       This table is used to config the physical termination of the MG.
       The index of this entry is hwMgPhyTerminationIndex.
       "
     INDEX    {  
               hwMgPhyTerminationIndex
              }
     ::= { hwMgPhyTerminationCfgTable 1 }
 
   HwMgPhyTerminationCfgEntry ::=
     SEQUENCE
     {
       hwMgPhyTerminationIndex	Integer32,
       hwMgPhyTerminationMgId	Integer32,
       hwMgPhyTerminationID	OCTET STRING,
       hwMgPhyTerminationTelNo	OCTET STRING,
       hwMgPhyTerminationSrvState	INTEGER,
       hwMgPhyTerminationOperate	INTEGER,
       hwMgPhyTerminationRowStatus	RowStatus,
       hwMgPhyTerminationContexID	Integer32,
       hwMgPhyTerminationLayerFlag	INTEGER,
       hwMgPhyTerminationLastChange	TimeTicks,
       hwMgPhyTerminationPriorityFlag	INTEGER,
       hwMgPhyTerminationSrvAlarmState	INTEGER,
       hwMgPhyTerminationSrvAlarmType	INTEGER
     }
 
   hwMgPhyTerminationIndex OBJECT-TYPE
     SYNTAX      Integer32
     MAX-ACCESS  not-accessible
     STATUS      current
     DESCRIPTION
         "
         Indicates the shelf/slot/port.
         "
     ::= { hwMgPhyTerminationCfgEntry 1 }
 
   hwMgPhyTerminationMgId OBJECT-TYPE
     SYNTAX      Integer32(0..16777215)
     MAX-ACCESS  read-create
     STATUS      current
     DESCRIPTION
         "
         Indicates the MG ID.
         "
     ::= { hwMgPhyTerminationCfgEntry 2 }
 
   hwMgPhyTerminationID OBJECT-TYPE
     SYNTAX      OCTET STRING(SIZE(0..64))
     MAX-ACCESS  read-create
     STATUS      current
     DESCRIPTION
         "
         Indicates the termination ID.
         "
     ::= { hwMgPhyTerminationCfgEntry 3 }
 
   hwMgPhyTerminationTelNo OBJECT-TYPE
     SYNTAX      OCTET STRING(SIZE(0..16))
     MAX-ACCESS  read-create
     STATUS      current
     DESCRIPTION
         "
         Indicates the telephone number.
         "
     ::= { hwMgPhyTerminationCfgEntry 4 }
 
   hwMgPhyTerminationSrvState OBJECT-TYPE
     SYNTAX      INTEGER{serviceStopLocal(1),   -- stop local service
                         serviceStopRemote(2),  -- stop remote service
                         serviceStopAuto(3),    -- stop service automatically
                         serviceStart(4),       -- start service
                         serviceStopGraceful(5) -- Stop service graceful
                         }
     MAX-ACCESS  read-only
     STATUS      current
     DESCRIPTION
         "
         Indicates the service status. 
         Options:
         1. serviceStopLocal(1) -stop local service
         2. serviceStopRemote(2) -stop remote service
         3. serviceStopAuto(3) -stop service automatically
         4. serviceStart(4) -start service 
         5. serviceStopGraceful(5) -stop service graceful
         "
     ::= { hwMgPhyTerminationCfgEntry 5 }
 
   hwMgPhyTerminationOperate OBJECT-TYPE
     SYNTAX      INTEGER{stop(1), -- stop service
                         start(2) -- start service
                         }
     MAX-ACCESS  read-write
     STATUS      current
     DESCRIPTION
         "
         Indicates the service operation. 
         Options:
         1. stop(1) -stop service 
         2. start(2) -start service
         "
     ::= { hwMgPhyTerminationCfgEntry 6 }
 
   hwMgPhyTerminationRowStatus OBJECT-TYPE
     SYNTAX      RowStatus
     MAX-ACCESS  read-write
     STATUS      current
     DESCRIPTION
         "
         Indicates the row status.
         "
     ::= { hwMgPhyTerminationCfgEntry 7 }
 
   hwMgPhyTerminationContexID OBJECT-TYPE
     SYNTAX      Integer32(0..65535)
     MAX-ACCESS  read-only
     STATUS      current
     DESCRIPTION
         "
         Indicates the context ID of the termination.
         "
     ::= { hwMgPhyTerminationCfgEntry 8 }
 
   hwMgPhyTerminationLayerFlag OBJECT-TYPE
     SYNTAX      INTEGER{nolayer(1), -- not to layer
                         layer(2)    -- to layer
                         }
     MAX-ACCESS  read-only
     STATUS      current
     DESCRIPTION
         "
         Indicates the layering flag. 
         Currently, only the value nolayer(1) is supported.
         Options:
         1. nolayer(1) -not to layer 
         2. layer(2) -to layer
         "
     ::= { hwMgPhyTerminationCfgEntry 9 }
 
   hwMgPhyTerminationLastChange OBJECT-TYPE
     SYNTAX      TimeTicks
     MAX-ACCESS  read-only
     STATUS      current
     DESCRIPTION
         "
         Indicates the service status changing time.
         "
     ::= { hwMgPhyTerminationCfgEntry 10 }
 
   hwMgPhyTerminationPriorityFlag OBJECT-TYPE
     SYNTAX      INTEGER{cat1(1),cat2(2),cat3(3)}
     MAX-ACCESS  read-write
     STATUS      current
     DESCRIPTION
         "
         Indicates the priority of the termination. 
         Options:
         1. cat1(1) -cat1
         2. cat2(2) -cat2
         3. cat3(3) -cat3
         "
         DEFVAL      { cat3 }
     ::= { hwMgPhyTerminationCfgEntry 11 }
  
   hwMgPhyTerminationSrvAlarmState OBJECT-TYPE
     SYNTAX      INTEGER{no(1),yes(2)}
     MAX-ACCESS  read-only
     STATUS      current
     DESCRIPTION
         "
         Indicates the alarm state of service port.
         Options:
         1. no(1)  -has no alarm
         2. yes(2) -has alarm
         "
     ::= { hwMgPhyTerminationCfgEntry 12 }
     
   hwMgPhyTerminationSrvAlarmType OBJECT-TYPE
     SYNTAX      INTEGER{portFailure(1),           -- port failure
                         vagInterfaceInterrupt(2), -- VAG Interrupt
                         noDsp(3),                 -- no DSP resource alarm
                         portBlock(4),             -- port block
                         portLocked(5),            -- port locked
                         circuitryFailure(6)       -- circuitry failure
                         }
     MAX-ACCESS  read-only
     STATUS      current
     DESCRIPTION
         "
         Indicates the alarm type of service port.
         Options:
         1. portFailure(1) -port failure
         2. vagInterfaceInterrupt(2) -VAG Interrupt
         3. noDsp(3) -no DSP resource alarm
         4. portBlock(4) -port block
         5. portLocked(5) -port locked
         6. circuitryFailure(6) -circuitry failure
         "
     ::= { hwMgPhyTerminationCfgEntry 13 }
 
 
   hwMgPhyTerminationOperTable OBJECT-TYPE
     SYNTAX      SEQUENCE OF HwMgPhyTerminationOperEntry
     MAX-ACCESS  not-accessible
     STATUS      current
     DESCRIPTION
       "
       This table is used to query the port status of the physical termination of the MG.
       The index of this table is hwMgPhyTermIndex.
       "
     ::= { hwIASVoipObjects 4 }
 
   hwMgPhyTerminationOperEntry OBJECT-TYPE
     SYNTAX      HwMgPhyTerminationOperEntry
     MAX-ACCESS  not-accessible
     STATUS      current
     DESCRIPTION
       "
       This table is used to query the port status of the physical termination of the MG.
       The index of this entry is hwMgPhyTermIndex.
       "
     INDEX    {  
               hwMgPhyTermIndex
              }
     ::= { hwMgPhyTerminationOperTable 1 }
 
   HwMgPhyTerminationOperEntry ::=
     SEQUENCE
     {
       hwMgPhyTermIndex	Integer32,
       hwMgPhyTerminationPortState	INTEGER,
       hwMgPhyTerminationSrvType	INTEGER,
       hwMgPhyTerminationAdminStatus	INTEGER,
       hwMgPhyTerminationStateChange	TimeTicks,
       hwMgPhyTerminationConfigState	INTEGER,
       hwMgPhyTerminationOperOperate	INTEGER,
       hwMgPhyTerminationMaxCOBTime	Integer32,
       hwMgPhyTerminationOnExpire	INTEGER,
       hwMgPhyTerminationUpTimeSinceLastRTS	TimeTicks,
       hwMgPhyTerminationEndServiceLastTime	TimeTicks,
       hwMgPhyTerminationEndServiceMode	Integer32
     }
 
   hwMgPhyTermIndex OBJECT-TYPE
     SYNTAX      Integer32
     MAX-ACCESS  not-accessible
     STATUS      current
     DESCRIPTION
         "
         Indicates the shelf/slot/port.
         "
     ::= { hwMgPhyTerminationOperEntry 1 }
 
   hwMgPhyTerminationPortState OBJECT-TYPE
     SYNTAX      INTEGER{idle(1),        -- idle
                         fault(2),       -- fault
                         test(3),        -- testing
                         lock(4),        -- locked
                         busy(5),        -- busy
                         localLoop(6),   -- local loopback
                         remoteLoop(7),  -- remote loopback
                         powerdeny(8),   -- powerdeny
                         ring(9)         -- ringing
                         }
     MAX-ACCESS  read-only
     STATUS      current
     DESCRIPTION
         "
         Indicates the physical status of the port. 
         Options:
         1. idle(1) -idle
         2. fault(2) -faulty
         3. test(3) -test
         4. lock(4) -locked
         5. busy(5) -busy
         6. localLoop(6) -local loopback
         7. remoteLoop(7) -remote loopback
         8. powerdeny(8) -low power consumption
         9. ring(9) -ring
         "
     ::= { hwMgPhyTerminationOperEntry 2 }
 
   hwMgPhyTerminationSrvType OBJECT-TYPE
     SYNTAX      INTEGER{normal(1),     -- instant service
                         innerSpc(2),   -- inner SPC
                         v5spc(3),      -- V5 SPC
                         v5pre(4),      -- V5 pre-connection
                         privateSpc(5), -- V5 private SPC
                         ipSpc(6)}      -- IP SPC
     MAX-ACCESS  read-only
     STATUS      current
     DESCRIPTION
         "
         Indicates the service type of the port. 
         Options:
         1. normal(1)-instant service
         2. innerSpc(2) -inner SPC
         3. v5spc(3) -V5 SPC
         4. v5pre(4) -V5 pre-connection
         5. privateSpc(5) -private line service
         6. ipSpc(6) -IP SPC
         "
     ::= { hwMgPhyTerminationOperEntry 3 }
 
   hwMgPhyTerminationAdminStatus OBJECT-TYPE
     SYNTAX      INTEGER{reset(1),      -- reset
                         localloop(2),  -- local loopback
                         remoteloop(3), -- remote loopback
                         cancelloop(4), -- cancel loopback
                         startagc(5)    -- start automatic gain control
                         }
     MAX-ACCESS  read-write
     STATUS      current
     DESCRIPTION
         "
         Indicates the maintenance operation of the port. 
         Options:
         1. reset(1) -reset
         2. localloop(2) -local loopback
         3. remoteloop(3) -remote loopback
         4. cancelloop(4) -cancel loopback
         5. startagc(5) -start automatic gain control
         "
     ::= { hwMgPhyTerminationOperEntry 4 }
 
   hwMgPhyTerminationStateChange OBJECT-TYPE
     SYNTAX      TimeTicks
     MAX-ACCESS  read-only
     STATUS      current
     DESCRIPTION
         "
         Indicates the physical status changing time of the port.
         "
     ::= { hwMgPhyTerminationOperEntry 5 }

   hwMgPhyTerminationConfigState OBJECT-TYPE
     SYNTAX      INTEGER{configedMgUser(1), -- configured MG subscriber 
                         configedV5User(2), -- configured V5 subscriber 
                         notConfiged(3),    -- not configured 
                         spcmcfged(4),      -- configured SPCM subscriber 
                         mglicensed(5),     -- configured and licensed MG subscriber 
                         v5licensed(6)      -- configured and licensed V5 subscriber
                         }
     MAX-ACCESS  read-only
     STATUS      current
     DESCRIPTION
         " 
         Indicates the configured subscriber type. 
         Options:
         1. configedMgUser(1) -configured MG subscriber
         2. configedV5User(2) -configured V5 subscriber
         3. notConfiged(3) -not configured
         4. spcmcfged(4) -configured SPCM subscriber
         5. mglicensed(5) -configured and licensed MG subscriber
         6. v5licensed(6) -configured and licensed V5 subscriber
         "
     ::= { hwMgPhyTerminationOperEntry 6 }
   hwMgPhyTerminationOperOperate OBJECT-TYPE
     SYNTAX      INTEGER{stop(1), -- stop service
                         start(2) -- start service
                         }
     MAX-ACCESS  read-write
     STATUS      current
     DESCRIPTION
         "
         Indicates the service operation. 
         Options:
         1. stop(1) -stop service 
         2. start(2) -start service
         "
     ::= { hwMgPhyTerminationOperEntry 7 }

   hwMgPhyTerminationMaxCOBTime OBJECT-TYPE
     SYNTAX      Integer32(1..1440)
     MAX-ACCESS  read-write
     STATUS      current
     DESCRIPTION
         "
         The longest time of out of service gracefully.
         Unit:minute
         "
     DEFVAL { 240 }
     ::= { hwMgPhyTerminationOperEntry 8 }

   hwMgPhyTerminationOnExpire OBJECT-TYPE
     SYNTAX      INTEGER{forced(1), -- force to stop service
                         cancel(2)  -- cancel operation
                         }
     MAX-ACCESS  read-write
     STATUS      current
     DESCRIPTION
         "
         The disposal method when the port get out of service gracefully.
         Options:
         1. forced(1) -force to stop service
         2. cancel(2) -cancel operation
         "
     DEFVAL { forced }
     ::= { hwMgPhyTerminationOperEntry 9 }

   hwMgPhyTerminationUpTimeSinceLastRTS OBJECT-TYPE
     SYNTAX      TimeTicks
     MAX-ACCESS  read-only
     STATUS      current
     DESCRIPTION
         "
         The time since PSTN port get in service latest
         "
     ::= { hwMgPhyTerminationOperEntry 10 }

   hwMgPhyTerminationEndServiceLastTime OBJECT-TYPE
     SYNTAX      TimeTicks
     MAX-ACCESS  read-only
     STATUS      current
     DESCRIPTION
         "
         Remanent time before the timer overtime
         "
     ::= { hwMgPhyTerminationOperEntry 11 }

   hwMgPhyTerminationEndServiceMode OBJECT-TYPE
     SYNTAX      Integer32(1..2)
     MAX-ACCESS  read-write
     STATUS      current
     DESCRIPTION
         "
         Endservice mode.
         1-Immediate, 2-Graceful.
         "
     ::= { hwMgPhyTerminationOperEntry 12 }

   hwMgEphemeralTerminationTable OBJECT-TYPE
     SYNTAX      SEQUENCE OF HwMgEphemeralTerminationEntry
     MAX-ACCESS  not-accessible
     STATUS      current
     DESCRIPTION
       "
       This table is used to config the virtual termination configuration of the MG.
       The indexes of this table are hwMgEphemeralTerminationMgId, hwMgEphemeralTerminationID.
       "
     ::= { hwIASVoipObjects 5 }
 
   hwMgEphemeralTerminationEntry OBJECT-TYPE
     SYNTAX      HwMgEphemeralTerminationEntry
     MAX-ACCESS  not-accessible
     STATUS      current
     DESCRIPTION
       "
       This table is used to config the virtual termination configuration of the MG.
       The indexes of this entry are hwMgEphemeralTerminationMgId, hwMgEphemeralTerminationID.
       "
     INDEX    {  
               hwMgEphemeralTerminationMgId,
               hwMgEphemeralTerminationID
              }
     ::= { hwMgEphemeralTerminationTable 1 }
 
   HwMgEphemeralTerminationEntry ::=
     SEQUENCE
     {
       hwMgEphemeralTerminationMgId	Integer32,
       hwMgEphemeralTerminationID	Integer32,
       hwMgEphemeralTerminationPacketTime	Integer32,
       hwMgEphemeralTerminationVAD	INTEGER,
       hwMgEphemeralTerminationEC	INTEGER,
       hwMgEphemeralTerminationJitBuffer	Integer32,
       hwMgEphemeralTerminationTransGain	Integer32,
       hwMgEphemeralTerminationRecvGain	Integer32,
       hwMgEphemeralTerminationCodeC	INTEGER,
       hwMgEphemeralTerminationLocalIPAddr	IpAddress,
       hwMgEphemeralTerminationLocalPort	Integer32,
       hwMgEphemeralTerminationPeerIPAddr	IpAddress,
       hwMgEphemeralTerminationPeerPort	Integer32,
       hwMgEphemeralTerminationPlace	Integer32,
       hwMgEphemeralTerminationContexID	Integer32
     }
 
   hwMgEphemeralTerminationMgId OBJECT-TYPE
     SYNTAX      Integer32(0..16777215)
     MAX-ACCESS  not-accessible
     STATUS      current
     DESCRIPTION
         "
         Indicates the MG ID.
         "
     ::= { hwMgEphemeralTerminationEntry 1 }
 
   hwMgEphemeralTerminationID OBJECT-TYPE
     SYNTAX      Integer32
     MAX-ACCESS  not-accessible
     STATUS      current
     DESCRIPTION
         "
         Indicates the virtual termination ID.
         "
     ::= { hwMgEphemeralTerminationEntry 2 }
 
   hwMgEphemeralTerminationPacketTime OBJECT-TYPE
     SYNTAX      Integer32
     MAX-ACCESS  read-only
     STATUS      current
     DESCRIPTION
         "
         Indicates the packetizing time.
         Unit: millisecond.
         "
     ::= { hwMgEphemeralTerminationEntry 3 }
 
   hwMgEphemeralTerminationVAD OBJECT-TYPE
     SYNTAX      INTEGER{true(1), -- enable VAD
                         false(2) -- disable VAD
                         }
     MAX-ACCESS  read-only
     STATUS      current
     DESCRIPTION
         "
         Indicates voice activity detection.
         Options:
         1. true(1) -enable VAD
         2. false(2) -disable VAD
         "
     ::= { hwMgEphemeralTerminationEntry 4 }
 
   hwMgEphemeralTerminationEC OBJECT-TYPE
     SYNTAX      INTEGER{true(1), -- enable EC
                         false(2) -- disable EC
                         }
     MAX-ACCESS  read-only
     STATUS      current
     DESCRIPTION
         "
         Indicates echo cancel.
         Options:
         1. true(1) -enable EC
         2. false(2) -disable EC
         "
     ::= { hwMgEphemeralTerminationEntry 5 }
 
   hwMgEphemeralTerminationJitBuffer OBJECT-TYPE
     SYNTAX      Integer32
     MAX-ACCESS  read-only
     STATUS      current
     DESCRIPTION
         "
         Indicates the value of JitBuffer.
         Unit: second.
         "
     ::= { hwMgEphemeralTerminationEntry 6 }
 
   hwMgEphemeralTerminationTransGain OBJECT-TYPE
     SYNTAX      Integer32
     MAX-ACCESS  read-only
     STATUS      current
     DESCRIPTION
         "
         Indicates the transmit gain.
         Unit: dB.
         "
     ::= { hwMgEphemeralTerminationEntry 7 }
 
   hwMgEphemeralTerminationRecvGain OBJECT-TYPE
     SYNTAX      Integer32
     MAX-ACCESS  read-only
     STATUS      current
     DESCRIPTION
         "
         Indicates the receive gain.
         Unit: dB.
         "
     ::= { hwMgEphemeralTerminationEntry 8 }
 
   hwMgEphemeralTerminationCodeC OBJECT-TYPE
     SYNTAX      INTEGER{acG711ALaw(1),acG711uLaw(2),acG726R16(3),acG726R24(4),acG726R32(5),acG726R40(6),acG727R16(7),acG727R24R16(8),acG727R24(9),acG727R32R16(10),acG727R32R24(11),acG727R32(12),acG727R40R16(13),acG727R40R24(14),acG727R40R32(15),acG723Low(16),acG723High(17),acG729(18),acReserved18(19),acGSM610(20),acGSM610MS(21),acReserved21(22),acTransparent(23),acG728(24),acHDLCcoder(25),acNetCoderR4R8(26),acNetCoderR5R6(27),acNetCoderR6R4(28),acNetCoderR7R2(29),acNetCoderR8(30),acNetCoderR8R8(31),acNetCoderR9R6(32),acEVRC(33),acEVRCRTFO(34),acQCELPR8(35),acQCELPR8RTFO(36),acQCELPR13(37),acQCELPR13RTFO(38),acReserved38(39),acReserved39(40),acNoCoder(41),acModemAnswer(42),acModemCall(43),acReserved43(44),acReserved44(45),acG711ALawR5R5(46),acG711uLawR5R5(47),acG726R32R5R5(48),acReserved48(49),acReserved49(50),acAMRR4R75(51),acAMRR5R15(52),acAMRR5R9(53),acAMRR6R7(54),acAMRR7R4(55),acAMRR7R95(56),acAMRR10R2(57),acAMRR12R2(58),t38Fax(59),g722(60)}
     MAX-ACCESS  read-only
     STATUS      current
     DESCRIPTION
         "
         Indicates the enumerated definition of the VoiceCode. Note that several items in the enumerated definition are not consecutive.
         In the definition above, acG723Low(16) and acG723High(17) need not be distinguished and can be directly presented as G.723.
         Options:
         1. acG711ALaw(1)    -G711A
         2. acG711uLaw(2)    -G711U
         3. acG726R16(3)      -G726-16
         4. acG726R24(4)      -G726-24
         5. acG726R32(5)      -G726-32
         6. acG726R40(6)      -G726-40
         7. acG727R16(7)      -G727-16
         8. acG727R24R16(8)   -G727-24-16
         9. acG727R24(9)      -G727-24
         10. acG727R32R16(10) -G727-32-16
         11. acG727R32R24(11) -G727-32-24
         12. acG727R32(12)    -G727-32
         13. acG727R40R16(13) -G727-40-16
         14. acG727R40R24(14) -G727-40-24
         15. acG727R40R32(15) -G727-40-32
         16. acG723Low(16)    -G723 low speed
         17. acG723High(17)   -G723 high speed
         18. acG729(18)       -G729
         19. acReserved18(19) -system reserved
         20. acGSM610(20)     -GSM610
         21. acGSM610MS(21)   -GSM610MS
         22. acReserved21(22) -system reserved
         23. acTransparent(23) -transparent
         24. acG728(24)        -G728
         25. acHDLCcoder(25)   -HDLCcoder
         26. acNetCoderR4R8(26) -NetCoder-4-8
         27. acNetCoderR5R6(27) -NetCoder-5-6
         28. acNetCoderR6R4(28) -NetCoder-6-4
         29. acNetCoderR7R2(29) -NetCoder-7-2
         30. acNetCoderR8(30)   -NetCoder-8
         31. acNetCoderR8R8(31) -NetCoder-8-8
         32. acNetCoderR9R6(32) -NetCoder-9-6
         33. acEVRC(33)         -EVRC
         34. acEVRCRTFO(34)     -EVRC-TFO
         35. acQCELPR8(35)      -QCELP-8
         36. acQCELPR8RTFO(36)  -QCELP-8-TFO
         37. acQCELPR13(37)     -QCELP-13
         38. acQCELPR13RTFO(38) -QCELP-13-TFO
         39. acReserved38(39)   -system reserved
         40. acReserved39(40)   -system reserved
         41. acNoCoder(41)      -No coder
         42. acModemAnswer(42)  -ModemAnswer
         43. acModemCall(43)    -ModemCall
         44. acReserved43(44)   -system reserved
         45. acReserved44(45)   -system reserved
         46. acG711ALawR5R5(46) -G711A-law-5-5
         47. acG711uLawR5R5(47) -G711u-law-5-5
         48. acG726R32R5R5(48)   -G726-32-5-5
         48. acReserved48(49)    -system reserved
         50. acReserved49(50)    -system reserved
         51. acAMRR4R75(51)      -AMR-4-75
         52. acAMRR5R15(52)      -AMR-5-15
         53. acAMRR5R9(53)       -AMR-5-9
         54. acAMRR6R7(54)       -AMR-6-7
         55. acAMRR7R4(55)       -AMR-7-4
         56. acAMRR7R95(56)      -AMR-7-95
         57. acAMRR10R2(57)      -AMR-10-2
         58. acAMRR12R2(58)      -AMR-12-2
         59. t38Fax(59)          -t38Fax
         60. g722(60)            -G722
         "
     ::= { hwMgEphemeralTerminationEntry 9 }
 
   hwMgEphemeralTerminationLocalIPAddr OBJECT-TYPE
     SYNTAX      IpAddress
     MAX-ACCESS  read-only
     STATUS      current
     DESCRIPTION
         "
         Indicates the local IP address.
         "
     ::= { hwMgEphemeralTerminationEntry 10 }
 
   hwMgEphemeralTerminationLocalPort OBJECT-TYPE
     SYNTAX      Integer32(0..65535)
     MAX-ACCESS  read-only
     STATUS      current
     DESCRIPTION
         "
         Indicates the local RTP port.
         "
     ::= { hwMgEphemeralTerminationEntry 11 }
 
   hwMgEphemeralTerminationPeerIPAddr OBJECT-TYPE
     SYNTAX      IpAddress
     MAX-ACCESS  read-only
     STATUS      current
     DESCRIPTION
         "
         Indicates the peer IP address.
         "
     ::= { hwMgEphemeralTerminationEntry 12 }
 
   hwMgEphemeralTerminationPeerPort OBJECT-TYPE
     SYNTAX      Integer32(0..65535)
     MAX-ACCESS  read-only
     STATUS      current
     DESCRIPTION
         "
         Indicates the peer RTP port.
         "
     ::= { hwMgEphemeralTerminationEntry 13 }
 
   hwMgEphemeralTerminationPlace OBJECT-TYPE
     SYNTAX      Integer32
     MAX-ACCESS  read-only
     STATUS      current
     DESCRIPTION
         "
         Indicates the DSP channel (shelf/slot/subboard/channel index) of the virtual terminal of the MG.
         Bits 31-26 (six bits): shelf index
         Bits 25-20 (six bits): slot index
         Bits 19-16 (four bits): subboard index
         Bits 15-0 (16 bits): channel index
         "
     ::= { hwMgEphemeralTerminationEntry 14 }
 
   hwMgEphemeralTerminationContexID OBJECT-TYPE
     SYNTAX      Integer32
     MAX-ACCESS  read-only
     STATUS      current
     DESCRIPTION
         "
         Indicates the context ID.
         "
     ::= { hwMgEphemeralTerminationEntry 15 }
 
   hwMgContexTable OBJECT-TYPE
     SYNTAX      SEQUENCE OF HwMgContexEntry
     MAX-ACCESS  not-accessible
     STATUS      current
     DESCRIPTION
       "
       This table is used to config the context of the MG.
       The indexes of this table are hwMgContexMgId, hwMgContexlID.
       "
     ::= { hwIASVoipObjects 6 }
 
   hwMgContexEntry OBJECT-TYPE
     SYNTAX      HwMgContexEntry
     MAX-ACCESS  not-accessible
     STATUS      current
     DESCRIPTION
       "
       This table is used to config the context of the MG.
       The indexes of this entry are hwMgContexMgId, hwMgContexlID.
       "
     INDEX    {  
               hwMgContexMgId,
               hwMgContexlID
              }
     ::= { hwMgContexTable 1 }
 
   HwMgContexEntry ::=
     SEQUENCE
     {
       hwMgContexMgId	Integer32,
       hwMgContexlID	Integer32,
       hwMgTerminationID1	Integer32,
       hwMgTerminationID2	Integer32
     }
 
   hwMgContexMgId OBJECT-TYPE
     SYNTAX      Integer32(0..16777215)
     MAX-ACCESS  not-accessible
     STATUS      current
     DESCRIPTION
         "
         Indicates the MG ID.
         "
     ::= { hwMgContexEntry 1 }
 
   hwMgContexlID OBJECT-TYPE
     SYNTAX      Integer32
     MAX-ACCESS  not-accessible
     STATUS      current
     DESCRIPTION
         "
         Indicates the context ID.
         "
     ::= { hwMgContexEntry 2 }
 
   hwMgTerminationID1 OBJECT-TYPE
     SYNTAX      Integer32(0..65535)
     MAX-ACCESS  read-only
     STATUS      current
     DESCRIPTION
         "
         Indicates the physical termination ID.
         "
     ::= { hwMgContexEntry 3 }
 
   hwMgTerminationID2 OBJECT-TYPE
     SYNTAX      Integer32
     MAX-ACCESS  read-only
     STATUS      current
     DESCRIPTION
         "
         Indicates the virtual termination ID.
         "
     ::= { hwMgContexEntry 4 }
 
     
   hwH248ParaTable OBJECT-TYPE
     SYNTAX      SEQUENCE OF HwH248ParaEntry
     MAX-ACCESS  not-accessible
     STATUS      current
     DESCRIPTION
       "
       This table is used to config the H.248 parameter. 
       The index of this table is hwH248ParaMgId.
       "
     ::= { hwIASVoipObjects 17 }
 
   hwH248ParaEntry OBJECT-TYPE
     SYNTAX      HwH248ParaEntry
     MAX-ACCESS  not-accessible
     STATUS      current
     DESCRIPTION
       "
       This table is used to config the H.248 parameter. 
       The index of this entry is hwH248ParaMgId.
       "
     INDEX    {  
               hwH248ParaMgId
              }
     ::= { hwH248ParaTable 1 }
 
   HwH248ParaEntry ::=
     SEQUENCE
     {
       hwH248ParaMgId	Integer32,
       hwH248ParaTransReliable	INTEGER,
       hwH248ParaLongTimer	Integer32,
       hwH248ParaMaxRetransTimer	Integer32,
       hwH248ParaMinRetransTimer	Integer32,
       hwH248ParaMgProvRespTimer	Integer32,
       hwH248ParaMaxRetrans	Integer32,
       hwH248ParaSecurity	INTEGER,
       hwH248ParaSdpEncodeType	INTEGER,
       hwH248ParaResponseAckCtrl  INTEGER,
       hwH248ParaRetransMode   INTEGER,
       hwH248ParaRetransTimer  Integer32,
       hwH248ParaTMax  Integer32,
       hwH248ParaRetransfailoption INTEGER,
       hwH248ParaFormatoption INTEGER, 
       hwH248ParaMTU Integer32,
       hwH248ParaMessagesegmentation  INTEGER,
       hwH248ParaMgcProvRespTimer      Integer32,
       hwH248ParaMgOriginatedPendingLimit Integer32,
       hwH248ParaMgcOriginatedPendingLimit Integer32
     }
                                      
   hwH248ParaMgId OBJECT-TYPE
     SYNTAX      Integer32(0..16777215)
     MAX-ACCESS  not-accessible
     STATUS      current
     DESCRIPTION
         "
         Indicates the MG ID.
         "
     ::= { hwH248ParaEntry 1 }
 
   hwH248ParaTransReliable OBJECT-TYPE
     SYNTAX      INTEGER{yes(1), -- enable retransmission
                         no(2)   -- disable retransmission
                         }
     MAX-ACCESS  read-write
     STATUS      current
     DESCRIPTION
         "
         Indicates the transaction reliability. The transaction reliability queue and the re-transmission timer are initialized when the protocol is initialized. Therefore, the transaction reliability can be set dynamically based on the current network conditions. The transaction reliability of different ports can be set differently.
         It only supports query in VSPV3R1 and after VSPV3R1.
         Options:
         1. yes(1) -enable retransmission
         2. no(2)  -disable retransmission
         "
     ::= { hwH248ParaEntry 2 }
 
   hwH248ParaLongTimer OBJECT-TYPE
     SYNTAX      Integer32(10000..40000)
     MAX-ACCESS  read-write
     STATUS      current
     DESCRIPTION
         "
         Indicates the length of the long timer. This parameter is a concept in the transaction reliability of the H.248 protocol stack. The protocol recommends a value of 30000 ms. The value can be set dynamically according to the current network conditions. The length of the long timer of different ports can be set differently.
         "
     DEFVAL      { 30000 }
     ::= { hwH248ParaEntry 3 }
 
   hwH248ParaMaxRetransTimer OBJECT-TYPE
     SYNTAX      Integer32(500..16000)
     MAX-ACCESS  read-write
     STATUS      current
     DESCRIPTION
         "
         Indicates the maximum length of the re-transmission timer. This parameter is a concept in the transaction reliability of the H.248 protocol stack. The protocol recommends a value of 4000 ms. When the H.248 protocol stack re-transmits messages, it calculates the length of the re-transmission timer by using the maximum and the minimum length of the re-transmission timer. The value can be set dynamically according to the current network conditions. The maximum length of the re-transmission timer of different ports can be set differently.
         "
     DEFVAL      { 4000 }
     ::= { hwH248ParaEntry 4 }
 
   hwH248ParaMinRetransTimer OBJECT-TYPE
     SYNTAX      Integer32(100..4000)
     MAX-ACCESS  read-write
     STATUS      current
     DESCRIPTION
         "
         Indicates the minimum length of the re-transmission timer. This parameter is a concept in the transaction reliability of the H.248 protocol stack. The protocol recommends a value of 1000 ms. When the H.248 protocol stack re-transmits messages, it calculates the length of the re-transmission timer by using the maximum and the minimum length of the re-transmission timer. The value can be set dynamically according to the current network conditions. The minimum length of the re-transmission timer of different ports can be set differently.
         "
     DEFVAL      { 500 }
     ::= { hwH248ParaEntry 5 }
 
   hwH248ParaMgProvRespTimer OBJECT-TYPE
     SYNTAX      Integer32(6000..10000)
     MAX-ACCESS  read-write
     STATUS      current
     DESCRIPTION
         "
         Indicates the length of the timer for provisional responses. By default, it is 8000 ms.
         Unit: millisecond.
         "
     DEFVAL      { 8000 }
     ::= { hwH248ParaEntry 6 }
 
   hwH248ParaMaxRetrans OBJECT-TYPE
     SYNTAX      Integer32(1..9)
     MAX-ACCESS  read-write
     STATUS      current
     DESCRIPTION
         "
         Indicates the maximum count of re-transmission. This parameter is a concept in the transaction reliability of the H.248 protocol stack. The value can be set dynamically based on different network conditions. By default, it is 7.
         "
     DEFVAL      { 7 }
     ::= { hwH248ParaEntry 7 }
 
   hwH248ParaSecurity OBJECT-TYPE
     SYNTAX      INTEGER{noah(1),md5(2),sha1(3)}
     MAX-ACCESS  read-write
     STATUS      current
     DESCRIPTION
         "
         Indicates the authorization type.
         Options:
         1. noah(1) -no authorization
         2. md5(2)  -MD5
         3. sha1(3) -SHA1
         The configuration will no longer take effect, and the value of hwH248MgSoftParameter7 will do that. 
         When hwH248MgSoftParameter7 is set to 0, megaco message will carry security header encrypted by md5 algorithm,
         when set to 1, megaco message will not carry security header.
         "
     ::= { hwH248ParaEntry 8 }
     
   hwH248ParaSdpEncodeType OBJECT-TYPE
     SYNTAX      INTEGER{text(1),hex(2)}
     MAX-ACCESS  read-write
     STATUS      current
     DESCRIPTION
         "
         Indicates the SDP encapsulation type.
         Options:
         1. text(1) -text
         2. hex(2)  -hex   
         "
     ::= { hwH248ParaEntry 9 }     
 
    hwH248ParaResponseAckCtrl OBJECT-TYPE
     SYNTAX      INTEGER{false(1), -- disable three-way handshake
                         true(2)   -- enable three-way handshake
                         }
     MAX-ACCESS  read-write
     STATUS      current
     DESCRIPTION
         "
         Indicates the switch of the three-way handshake signal.
         Options:
         1. false(1) -disable three-way handshake
         2. true(2)  -enable three-way handshake
         "
     ::= { hwH248ParaEntry 10 }     

    hwH248ParaRetransMode OBJECT-TYPE
     SYNTAX      INTEGER{auto(1),fixed(2)}
     MAX-ACCESS  read-write
     STATUS      current
     DESCRIPTION
         "
         Indicates the retransmission mode.
         Options:
         1. auto(1)  -auto
         2. fixed(2) -fixed
         "
     ::= { hwH248ParaEntry 11 }     

    hwH248ParaRetransTimer OBJECT-TYPE
     SYNTAX      Integer32(100..4000)
     MAX-ACCESS  read-write
     STATUS      current
     DESCRIPTION
         "
         Indicates the fixed re-transmission interval (this parameter is effective when the re-transmission mode is the fixed mode; by default, it is 2000).
         "
     ::= { hwH248ParaEntry 12 }     
     
   hwH248ParaTMax OBJECT-TYPE
     SYNTAX      Integer32(10000..30000)
     MAX-ACCESS  read-write
     STATUS      current
     DESCRIPTION
         "
         Indicates the re-transmission length of the H.248 protocol stack (by default, it is 25000).
         "
     ::= { hwH248ParaEntry 13 }    
     
   hwH248ParaRetransfailoption OBJECT-TYPE
     SYNTAX      INTEGER{times(1), -- times
                         tMax(2)  -- max time
                         }
     MAX-ACCESS  read-only
     STATUS      current
     DESCRIPTION
         "
         Indicates the retransmission failure option of the H.248 protocol stack.
         Options:
         1. times(1) -times
         2. tMax(2) -max time
         "
     ::= { hwH248ParaEntry 14 }    

   hwH248ParaFormatoption OBJECT-TYPE
     SYNTAX      INTEGER{short(1),long(2)}
     MAX-ACCESS  read-write
     STATUS      current
     DESCRIPTION
         "
         Indicates the message format of the H.248 protocol stack.
         Options:
         1. short(1) -short format
         2. long(2)  -long format
         Default: short(1)
         "
     ::= { hwH248ParaEntry 15 }           
   hwH248ParaMTU OBJECT-TYPE
     SYNTAX      Integer32(1..10000)
     MAX-ACCESS  read-write
     STATUS      current
     DESCRIPTION
         "
         Indicates the value of the maximum transmission unit of the H.248 protocol stack.
         Default: 1500
         "
     ::= { hwH248ParaEntry 16 }  
   hwH248ParaMessagesegmentation OBJECT-TYPE
     SYNTAX      INTEGER{support(1),notsupport(2)}
     MAX-ACCESS  read-write
     STATUS      current
     DESCRIPTION
         "
         Indicates the message format of the H.248 protocol stack.
         Options:
         1. support(1)    -support format message
         2. notsupport(2) -not support format message
         Default: support(1)
         "
     ::= { hwH248ParaEntry 17 }  
  hwH248ParaMgcProvRespTimer OBJECT-TYPE
     SYNTAX      Integer32(6000..10000)
     MAX-ACCESS  read-write
     STATUS      current
     DESCRIPTION
         "
         Indicates the length of MGC provisional response timer.
         Unit: millisecond
         "
     DEFVAL      { 8000 }
     ::= { hwH248ParaEntry 18 }
 
   hwH248ParaMgOriginatedPendingLimit OBJECT-TYPE
     SYNTAX      Integer32(1..10)
     MAX-ACCESS  read-write
     STATUS      current
     DESCRIPTION
         "
         Indicates the max times of MG sends provisional response.
         "
     DEFVAL      { 5 }
     ::= { hwH248ParaEntry 19 }
     
     hwH248ParaMgcOriginatedPendingLimit OBJECT-TYPE
     SYNTAX      Integer32(1..10)
     MAX-ACCESS  read-write
     STATUS      current
     DESCRIPTION
         "
         Indicates the max times of MGC sends provisional response.
         "
     DEFVAL      { 5 }
     ::= { hwH248ParaEntry 20 }
--

--    hwDigitmapInner OBJECT-TYPE
--    SYNTAX      OCTET STRING(SIZE(0..255))
--    MAX-ACCESS  read-write
--    STATUS      current
--    DESCRIPTION
--      " 
--      Indicates the common inner telephone digitmap. 
--      "
--    ::= { hwDigitmapTable 1 }
--
--  hwDigitmapEmergency OBJECT-TYPE
--    SYNTAX      OCTET STRING(SIZE(0..255))
--    MAX-ACCESS  read-write
--    STATUS      current
--    DESCRIPTION
--      " 
--      Indicates the emergency channel digitmap. 
--      "
--    ::= { hwDigitmapTable 2 }
--
--  hwDigitmapDualdial OBJECT-TYPE
--    SYNTAX      OCTET STRING(SIZE(0..15))
--    MAX-ACCESS  read-write
--    STATUS      current
--    DESCRIPTION
--      " 
--      Indicates the automatic re-dial digitmap. 
--      "
--    ::= { hwDigitmapTable 3 }
--    
--  hwDigitmapOverLoadUrgent OBJECT-TYPE
--    SYNTAX      OCTET STRING(SIZE(0..255))
--    MAX-ACCESS  read-write
--    STATUS      current
--    DESCRIPTION
--      " 
--      Indicates the overload emergency call digitmap. 
--      "
--    ::= { hwDigitmapTable 4 }
 
   hwH248DigitmapTable OBJECT-TYPE
     SYNTAX      SEQUENCE OF HwH248DigitmapEntry
     MAX-ACCESS  not-accessible
     STATUS      current
     DESCRIPTION
       "
       This table is used to config the inner digitmap configuration.
       The index of this table is hwH248DigitmapMgId.
       "
     ::= { hwIASVoipObjects 23 }
 
   hwH248DigitmapEntry OBJECT-TYPE
     SYNTAX      HwH248DigitmapEntry
     MAX-ACCESS  not-accessible
     STATUS      current
     DESCRIPTION
       "
       This table is used to config the inner digitmap configuration.
       The index of this entry is hwH248DigitmapMgId.
       "
     INDEX    {  
               hwH248DigitmapMgId
              }
     ::= { hwH248DigitmapTable 1 }
 
   HwH248DigitmapEntry ::=
     SEQUENCE
     {
       hwH248DigitmapMgId	Integer32,
       hwH248DigitmapInner OCTET STRING,
       hwH248DigitmapEmergency OCTET STRING,
       hwH248DigitmapDualdial OCTET STRING,
       hwH248DigitmapOverLoadUrgent OCTET STRING
     }
 
   hwH248DigitmapMgId OBJECT-TYPE
     SYNTAX      Integer32(0..16777215)
     MAX-ACCESS  not-accessible
     STATUS      current
     DESCRIPTION
         "
         Indicates the MG interface ID.
         "
     ::= { hwH248DigitmapEntry 1 }
 
 
 
   hwH248DigitmapInner OBJECT-TYPE
     SYNTAX      OCTET STRING(SIZE(0..127))
     MAX-ACCESS  read-write
     STATUS      current
     DESCRIPTION
         "
         Indicates the inner call digitmap.
         "
     ::= { hwH248DigitmapEntry 2 }
 
   hwH248DigitmapEmergency OBJECT-TYPE
     SYNTAX      OCTET STRING(SIZE(0..127))
     MAX-ACCESS  read-write
     STATUS      current
     DESCRIPTION
         "
         Indicates the emergency channel digitmap.
         "
     ::= { hwH248DigitmapEntry 3 }
 
   hwH248DigitmapDualdial OBJECT-TYPE
     SYNTAX      OCTET STRING(SIZE(0..14))
     MAX-ACCESS  read-write
     STATUS      current
     DESCRIPTION
         "
         Indicates the automatic re-dial digitmap.
         "
     ::= { hwH248DigitmapEntry 4 }
     
   hwH248DigitmapOverLoadUrgent OBJECT-TYPE
     SYNTAX      OCTET STRING(SIZE(0..127))
     MAX-ACCESS  read-write
     STATUS      current
     DESCRIPTION
         "
         Indicates the emergency call digitmap in case of overload or insufficient bandwidth.
         "
     ::= { hwH248DigitmapEntry 5 }

   hwStandaloneParaTable OBJECT-TYPE
     SYNTAX      SEQUENCE OF HwStandaloneParaEntry
     MAX-ACCESS  not-accessible
     STATUS      current
     DESCRIPTION
       "
       This table is used to config the stand-alone parameter.
       The index of this table is hwStandaloneParaMgId.
       "
     ::= { hwIASVoipObjects 24 }
 
   hwStandaloneParaEntry OBJECT-TYPE
     SYNTAX      HwStandaloneParaEntry
     MAX-ACCESS  not-accessible
     STATUS      current
     DESCRIPTION
       "
       This table is used to config the stand-alone parameter.
       The index of this entry is hwStandaloneParaMgId.
       "
     INDEX    {  
               hwStandaloneParaMgId
              }
     ::= { hwStandaloneParaTable 1 }
 
   HwStandaloneParaEntry ::=
     SEQUENCE
     {
       hwStandaloneParaMgId	Integer32,
       hwStandAloneDialTone Integer32,
       hwStandAloneRing Integer32,
       hwStandAloneBusyTone Integer32
     }
 
   hwStandaloneParaMgId OBJECT-TYPE
     SYNTAX      Integer32(0..16777215)
     MAX-ACCESS  not-accessible
     STATUS      current
     DESCRIPTION
         "
         Indicates the MG interface ID.
         "
     ::= { hwStandaloneParaEntry 1 }
     
     
   hwStandAloneDialTone OBJECT-TYPE
     SYNTAX      Integer32(1..120)
     MAX-ACCESS  read-write
     STATUS      current
     DESCRIPTION
       " 
       Indicates the duration of the dial tone. 
       Unit: second
       "
     ::= { hwStandaloneParaEntry 2 }
   
   hwStandAloneRing OBJECT-TYPE
     SYNTAX      Integer32(1..120)
     MAX-ACCESS  read-write
     STATUS      current
     DESCRIPTION
       " 
       Indicates the duration of the ring. 
       Unit: second
       "
     ::= { hwStandaloneParaEntry 3 }
   
   hwStandAloneBusyTone OBJECT-TYPE
     SYNTAX      Integer32(1..120)
     MAX-ACCESS  read-write
     STATUS      current
     DESCRIPTION
       " 
       Indicates the duration of the busy tone. 
       Unit: second
       "
     ::= { hwStandaloneParaEntry 4 } 

 hwH248MgSoftParameterTable OBJECT-TYPE
     SYNTAX      SEQUENCE OF HwH248MgSoftParameterEntry
     MAX-ACCESS  not-accessible
     STATUS      current
     DESCRIPTION
       "
       This table is to indicates the MG software parameter.
       The index of this table is hwH248MgInterfaceIndex.
       "
     ::= { hwIASVoipObjects 28 }
 
   hwH248MgSoftParameterEntry OBJECT-TYPE
     SYNTAX      HwH248MgSoftParameterEntry
     MAX-ACCESS  not-accessible
     STATUS      current
     DESCRIPTION
       "
       This table is to indicates the MG software parameter.
       The index of this entry is hwH248MgInterfaceIndex.
       "
     INDEX    {  
               hwH248MgInterfaceIndex
              }
     ::= { hwH248MgSoftParameterTable 1 }
 
   HwH248MgSoftParameterEntry ::=
     SEQUENCE
     {
       hwH248MgInterfaceIndex	        Integer32,
       hwH248MgSoftParameter0	        INTEGER,
       hwH248MgSoftParameter1	        INTEGER,
       hwH248MgSoftParameter2	        INTEGER,
       hwH248MgSoftParameter3	        INTEGER,
       hwH248MgSoftParameter4	        INTEGER,
       hwH248MgSoftParameter5	        INTEGER,
       hwH248MgSoftParameter6	        INTEGER,
       hwH248MgSoftParameter7	        INTEGER,
       hwH248MgSoftParameter8	        Integer32,
       hwH248MgSoftParameter9	        INTEGER,
       hwH248MgSoftParameter10	        INTEGER,
-- BEGIN: modified by wuguowang 20050725 FOR BT VAG */
       hwH248MgSoftParameter11	        INTEGER,
       hwH248MgSoftParameter12	        INTEGER,
       hwH248MgSoftParameter13	        INTEGER,
       hwH248MgSoftParameter14	        INTEGER,
-- END: modified by wuguowang 20050725 FOR BT VAG */
       hwH248MgSoftParameter15	        INTEGER,
       hwH248MgSoftParameter16	        Integer32,
       hwH248MgSoftParameter17	        INTEGER,
       hwH248MgSoftParameter18	        INTEGER,
       hwH248MgSoftParameter19	        INTEGER,
       hwH248MgSoftParameter20	        INTEGER,
       hwH248MgSoftParameter21	        INTEGER,
       hwH248MgSoftParameter22	        INTEGER,
       hwH248MgSoftParameter23	        Integer32,
       hwH248MgSoftParameter24	        Integer32,
       hwH248MgSoftParameter25	        Integer32,
       hwH248MgSoftParameter26	        INTEGER,
       hwH248MgSoftParameter27	        INTEGER,
       hwH248MgSoftParameter28	        Integer32,
       hwH248MgSoftParameter29	        Integer32,
       hwH248MgSoftParameter30	        Integer32,
       hwH248MgSoftParameter31          INTEGER,
       hwH248MgSoftParameter32          Integer32,
       hwH248MgSoftParameter33          INTEGER, 
       hwH248MgSoftParameter34          INTEGER,
       hwH248MgSoftParameter35          INTEGER,
       hwH248MgSoftParameter36          Integer32,
       hwH248MgSoftParameter37          INTEGER,
       hwH248MgSoftParameter38          INTEGER
     }
 
   hwH248MgInterfaceIndex OBJECT-TYPE
     SYNTAX      Integer32(0..16777215)
     MAX-ACCESS  not-accessible
     STATUS      current
     DESCRIPTION
         "
         Indicates the MG interface index.
         "
     ::= { hwH248MgSoftParameterEntry 1 }
 
   hwH248MgSoftParameter0 OBJECT-TYPE
     SYNTAX      INTEGER{yes(1),
                         no(2),
                         nolayer(3),
                         type1layer(4),
                         type2layer(5)
                         }
     MAX-ACCESS  read-write
     STATUS      deprecated
     DESCRIPTION
         "
         Parameter name index 0. It indicates whether the terminal ID of the MG interface is layered. 
         In the P300, the values of 1 and 2 are unavailable.
         Options:
         1. yes(1) -layered
         2. no(2) -not layered
         3. nolayer(3) -not layered
         4. type1layer(4) -type 1 layer (the shelf and the slot are at the same layer)
         5. type2layer(5) -type 2 layer (the shelf and the slot are not at the same layer)          
         Default: yes(1)
         "
      --DEFVAL      { yes(1) }
     ::= { hwH248MgSoftParameterEntry 2 } 
     
    hwH248MgSoftParameter1 OBJECT-TYPE
     SYNTAX      INTEGER{holdingToResume(1),no(2),holdingAllAlong(3)}
     MAX-ACCESS  read-write
     STATUS      deprecated
     DESCRIPTION
         "
         Parameter name index 1. It indicates whether the ongoing calls are maintained after MG is disconnected from MGC. (It is unavailable in the VSPV1R2.)
         Options:
         1. holdingToResume(1) -hold to resume
         2. no(2) -not maintained
         3. holdingAllAlong(3) -hold all along  
         Default: no(2)
         "
      --DEFVAL      { no(2) }
     ::= { hwH248MgSoftParameterEntry 3 }   
       
   hwH248MgSoftParameter2 OBJECT-TYPE
     SYNTAX      INTEGER{no(1),             -- not support multiple homing
                         multiHome(2),       -- support multiple homing, but the active MGC does not switch over automatically
                         autoSwitchOver(3)  -- support multiple homing, and the active MGC switch over automatically
                         }
     MAX-ACCESS  read-write
     STATUS      current
     DESCRIPTION
         "
         Parameter name index 2. It indicates whether the MG interface supports multiple homing. 
         It is unavailable in the VSPV1R2.
         Options:
         1. no(1)             -not support multiple homing
         2. multiHome(2)      -support multiple homing, but the active MGC does not switch over automatically
         3. autoSwitchOver(3) -support multiple homing, and the active MGC switch over automatically          
         Default: no(1)
         "
      --DEFVAL      { no(1) }
     ::= { hwH248MgSoftParameterEntry 4 }   
     
   hwH248MgSoftParameter3 OBJECT-TYPE
     SYNTAX      INTEGER{heartbeat(1),            -- heartbeat
                         messageRetransmission(2) -- retransmission
                         }
     MAX-ACCESS  read-write
     STATUS      deprecated
     DESCRIPTION
         "
         Parameter name index 3. It indicates the MG interface interruption detecting mode. It is unavailable in the P300.
         Options:
         1. heartbeat(1)             -heartbeat
         2. messageRetransmission(2) -retransmission
         Default: heartbeat(1)   
         "
      --DEFVAL      { Heartbeat(1) }
     ::= { hwH248MgSoftParameterEntry 5 } 
     
   hwH248MgSoftParameter4 OBJECT-TYPE
     SYNTAX      INTEGER{yes(1), -- use wildcard in registration
                         no(2)   -- do not use wildcard in registration
                         }
     MAX-ACCESS  read-write
     STATUS      current
     DESCRIPTION
         "
         Parameter name index 4. It indicates whether the wildcard is used in registration.
         Options:
         1. yes(1) -use wildcard in registration
         2. no(2)  -do not use wildcard in registration 
         Default: yes(1)
         "
      --DEFVAL      { yes(1) }
     ::= { hwH248MgSoftParameterEntry 6 }      

   hwH248MgSoftParameter5 OBJECT-TYPE
     SYNTAX      INTEGER{yes(1),  -- the port fault and auto-block is reported to the MGC
                         no(2)    -- the port fault and auto-block is not reported to the MGC
                         }
     MAX-ACCESS  read-write
     STATUS      deprecated
     DESCRIPTION
         "
         Parameter name index 5. It indicates whether the port fault and auto-block is reported to the MGC.
         Options:
         1. yes(1) -the port fault and auto-block is reported to the MGC
         2. no(2)  -the port fault and auto-block is not reported to the MGC 
         Default: yes(1)
         "
      --DEFVAL      { yes(1) }
     ::= { hwH248MgSoftParameterEntry 7 }
           
   hwH248MgSoftParameter6 OBJECT-TYPE
     SYNTAX      INTEGER{yes(1), -- support authentication
                         no(2)   -- not support authentication
                         }
     MAX-ACCESS  read-write
     STATUS      current
     DESCRIPTION
         "
         Parameter name index 6. It indicates whether authentication is supported.
         Options:
         1. yes(1) -support authentication
         2. no(2)  -not support authentication
         Default: no(2)
         "
      --DEFVAL      { no(2) }
     ::= { hwH248MgSoftParameterEntry 8 }   
     
   hwH248MgSoftParameter7 OBJECT-TYPE
     SYNTAX      INTEGER{yes(1),  -- support the security header
                         no(2)    -- not support the security header
                         }
     MAX-ACCESS  read-write
     STATUS      current
     DESCRIPTION
         "
         Parameter name index 7. It indicates whether the security header is supported.
         Options:
         1. yes(1) -support the security header
         2. no(2)  -not support the security header 
         Default: no(2)
         "
      --DEFVAL      { no(2) }
     ::= { hwH248MgSoftParameterEntry 9 }  
     
    hwH248MgSoftParameter8 OBJECT-TYPE
     SYNTAX      Integer32(0..1000)
     MAX-ACCESS  read-write
     STATUS      deprecated
     DESCRIPTION
         "
         Parameter name index 8. It indicates the maximum count of DSPs supported by the VAG. It is unavailable in the P300.
         "
     ::= { hwH248MgSoftParameterEntry 10 }
     
    hwH248MgSoftParameter9 OBJECT-TYPE
     SYNTAX      INTEGER{yes(1), -- support overload control
                         no(2)   -- not support overload control
                         }
     MAX-ACCESS  read-write
     STATUS      deprecated
     DESCRIPTION
         "
         Parameter name index 9. It indicates whether overload control is supported. It is unavailable in the P300.
         Options:
         1. yes(1) -support overload control
         2. no(2)  -not support overload control 
         Default: no(2)
         "
      --DEFVAL      { no(2) }
     ::= { hwH248MgSoftParameterEntry 11 } 

    hwH248MgSoftParameter10 OBJECT-TYPE
     SYNTAX      INTEGER{yes(1),no(2)}
     MAX-ACCESS  read-write
     STATUS      deprecated
     DESCRIPTION
         "
         Parameter name index 10. It indicates whether the SDP contains the o=,s=,t= row. It is unavailable in the VSPV1R2.
         Options:
         1. yes(1) -SDP contain the o=,s=,t= row
         2. no(2)  -SDP not contain the o=,s=,t= row 
         Default: no(2)   
         "
      --DEFVAL      { no(2) }
     ::= { hwH248MgSoftParameterEntry 12 } 
                                            
-- BEGIN: modified by wuguowang 20050725 FOR BT VAG */                                                        
    hwH248MgSoftParameter11 OBJECT-TYPE
     SYNTAX      INTEGER{none(1),      -- not support stand alone
                         inner(2),     -- support inner call
                         emergency(3), -- support emergence call
                         both(4)       -- support inner call and emergence call
                         }
     MAX-ACCESS  read-write
     STATUS      current
     DESCRIPTION
         "
         Parameter name index 11. It indicates the stand-alone flag.
         Options:
         1. none(1)      -not support stand alone
         2. inner(2)     -support inner call
         3. emergency(3) -support emergence call
         4. both(4)      -support inner call and emergence call 
         Default: none(1)
         "
      --DEFVAL      { none(1) }
     ::= { hwH248MgSoftParameterEntry 13 }        
     
     hwH248MgSoftParameter12 OBJECT-TYPE
     SYNTAX      INTEGER{no(1),yes(2)}
     MAX-ACCESS  read-write
     STATUS      deprecated
     DESCRIPTION
         "
         Parameter name index 12. It indicates the stand-alone interruption flag. It is unavailable in the VSPV1R2.
         Options:
         1. no(1)  -no
         2. yes(2) -yes 
         Default: no(1)
         "
      --DEFVAL      { no(1) }
     ::= { hwH248MgSoftParameterEntry 14 }       

     hwH248MgSoftParameter13 OBJECT-TYPE
     SYNTAX      INTEGER{min(1),max(2),auto(3),autoadapt(4)}
     MAX-ACCESS  read-write
     STATUS      current
     DESCRIPTION
         "
         Parameter name index 13. It indicates the DMM match mode. 
         Options:
         1. min(1)       -shortest
         2. max(2)       -longest
         3. auto(3)      -protocol define   
         4. autoadapt(4) -auto adapter 
         Default: min(1)
         "
      --DEFVAL      { min(1) }
     ::= { hwH248MgSoftParameterEntry 15 }  
     
     hwH248MgSoftParameter14 OBJECT-TYPE
     SYNTAX      INTEGER{min(1),max(5000)}
     MAX-ACCESS  read-write
     STATUS      deprecated
     DESCRIPTION
         "
         Parameter name index 14. It indicates the value of the maximum transmission unit.
         Options:
         1. min(1)    -min
         2. max(5000) -max 
         "
      --DEFVAL      { (1500) }
     ::= { hwH248MgSoftParameterEntry 16 } 
   
                                                        
-- END: modified by wuguowang 20050725 FOR BT VAG */         

     hwH248MgSoftParameter15 OBJECT-TYPE
     SYNTAX      INTEGER{no(1),yes(2),alwaysNo(3)}
     MAX-ACCESS  read-write
     STATUS      current
     DESCRIPTION
         "
         Parameter name index 15. It indicates the RTP source port filtering switch. 
         Options:
         1. no(1)  -not filter without remote media.
         2. yes(2) -filter without remote media.   
         3. alwaysNo(3) -always not filter.
         Default: no(1)
         "
      --DEFVAL      { no(1) }
     ::= { hwH248MgSoftParameterEntry 17 }       
     
     
     hwH248MgSoftParameter16 OBJECT-TYPE
     SYNTAX      Integer32(1..30)
     MAX-ACCESS  read-write
     STATUS      current
     DESCRIPTION
         "
         Parameter name index 16. It indicates the length of the RTP source port filtering timer. This parameter is valid only when the RTP filtering is enabled. 
         Range: 1-400(VSP is 1-30S) 
         Default: 5
         Unit: second          
         "
      --DEFVAL      { (5) }
     ::= { hwH248MgSoftParameterEntry 18 }     
     
     hwH248MgSoftParameter17 OBJECT-TYPE
     SYNTAX      INTEGER{yes(1),no(2)}
     MAX-ACCESS  read-write
     STATUS      deprecated
     DESCRIPTION
         "
         Parameter name index 17. It indicates the context protection switch. It is unavailable in the VSPV1R2.
         Options:
         1. yes(1) -the system releases the resource automatically
         2. no(2)  -the system does not release the resource automatically
         Default: no(2)
         "
      --DEFVAL      { no(2) }
     ::= { hwH248MgSoftParameterEntry 19 }                                                   
     
     hwH248MgSoftParameter18 OBJECT-TYPE
     SYNTAX      INTEGER{yes(1),no(2)}
     MAX-ACCESS  read-write
     STATUS      deprecated
     DESCRIPTION
         "
         Parameter name index 18. It indicates the point-to-point fault report flag. 
         Options:
         1. yes(1) -report
         2. no(2)  -not report
         Default: yes(1)
         "
      --DEFVAL      { yes(1) }
     ::= { hwH248MgSoftParameterEntry 20 }
       
     hwH248MgSoftParameter19 OBJECT-TYPE
     SYNTAX      INTEGER{yes(1),no(2)}
     MAX-ACCESS  read-write
     STATUS      deprecated
     DESCRIPTION
         "
         Parameter name index 19. It indicates the point-to-multipoint fault report flag. 
         Options:
         1. yes(1) -report
         2. no(2)  -not report
         Default: no(2)
         "
      --DEFVAL      { no(2) }
     ::= { hwH248MgSoftParameterEntry 21 }
   
     hwH248MgSoftParameter20 OBJECT-TYPE
     SYNTAX      INTEGER{highest(1),lowest(2),no(3)}
     MAX-ACCESS  read-write
     STATUS      deprecated
     DESCRIPTION
         "
         Parameter name index 20. It indicates the protocol version negotiation strategy. It is unavailable in the VSPV1R2.
         Options:
         1. highest(1) -negotiate from the latest version
         2. lowest(2)  -negotiate from the earliest version
         3. no(3)      -not to negotiate the version   
         "
      --DEFVAL      { Negotiate from highest version(1) }
     ::= { hwH248MgSoftParameterEntry 22 }    
          
     hwH248MgSoftParameter21 OBJECT-TYPE
     SYNTAX      INTEGER{yes(1),no(2)}
     MAX-ACCESS  read-write
     STATUS      deprecated
     DESCRIPTION
         "
         Parameter name index 21. It is reserved in the system.
         Options:
         1. yes(1) -yes
         2. no(2)  -no
         "
     ::= { hwH248MgSoftParameterEntry 23 }
     
     hwH248MgSoftParameter22 OBJECT-TYPE
     SYNTAX      INTEGER{bT(1),eET(2),announcement(3)}
     MAX-ACCESS  read-write
     STATUS      current
     DESCRIPTION
         "
         Parameter name index 22. It indicates the type of the prompt tone that is played after MG is disconnected from MGC. 
         Options:
         1. bT(1) -busy tone
         2. eET(2) -equipment engaged tone
         3. announcement(3) -announcement
         Default: bT(1)
         "
      --DEFVAL      { BT(1) }
     ::= { hwH248MgSoftParameterEntry 24 }                                      
     
     hwH248MgSoftParameter23 OBJECT-TYPE
     SYNTAX      Integer32(0..120)
     MAX-ACCESS  read-write
     STATUS      current
     DESCRIPTION
         "
         Parameter name index 23.It indicates the length of synchronize-delay timer of port config state.
         Default: 35 
         Unit: second
         "
      --DEFVAL      { (35) }
     ::= { hwH248MgSoftParameterEntry 25 }
     
     hwH248MgSoftParameter24 OBJECT-TYPE
     SYNTAX      Integer32(0..65535)
     MAX-ACCESS  read-write
     STATUS      current
     DESCRIPTION
         "
         Parameter name index 24. It indicates the number of rtp terminal. The maximum value is limited by product specification.
         "
      --DEFVAL      { 1000 }
     ::= { hwH248MgSoftParameterEntry 26 }
          
     hwH248MgSoftParameter25 OBJECT-TYPE
     SYNTAX      Integer32(30000..300000)
     MAX-ACCESS  read-write
     STATUS      current
     DESCRIPTION
         "
         Parameter name index 25. It indicates max random value of the avalanche prevention system of the interface. 
         Default: 60000 
         Unit: millisecond
         "
      --DEFVAL      { 60000 }
     ::= { hwH248MgSoftParameterEntry 27 }   
     
     hwH248MgSoftParameter26 OBJECT-TYPE
     SYNTAX      INTEGER{busyTone(1),congestionTone(2),muteTone(3),userDefineTone1(4),userDefineTone2(5)}
     MAX-ACCESS  read-write
     STATUS      current
     DESCRIPTION
         "
         Parameter name index 26.  It indicates the local block tone type. 
         Options: 
         1. busyTone(1)        -busy tone
         2. congestionTone(2)  -congestion tone
         3. muteTone(3)        -mute tone
         4. userDefineTone1(4) -user defined tone1
         5. userDefineTone2(5) -user defined tone2
         Default: busyTone(1)
         "
      --DEFVAL      { busyTone(1) }
     ::= { hwH248MgSoftParameterEntry 28 }
     
     hwH248MgSoftParameter27 OBJECT-TYPE
     SYNTAX      INTEGER{busyTone(1),congestionTone(2),muteTone(3),userDefineTone1(4),userDefineTone2(5)}
     MAX-ACCESS  read-write
     STATUS      current
     DESCRIPTION
         "
         Parameter name index 27.  It indicates the remote block tone type. 
         Options: 
         1. busyTone(1)        -busy tone
         2. congestionTone(2)  -congestion tone
         3. muteTone(3)        -mute tone
         4. userDefineTone1(4) -user defined tone1
         5. userDefineTone2(5) -user defined tone2
         Default: busyTone(1)
         "
      --DEFVAL      { busyTone(1) }
     ::= { hwH248MgSoftParameterEntry 29 }
     
     hwH248MgSoftParameter28 OBJECT-TYPE
     SYNTAX      Integer32(1..65535)
     MAX-ACCESS  read-write
     STATUS      current
     DESCRIPTION
         "
         Parameter name index 28.  It indicates the length of howler tone. 
         Default: 60 
         Unit: second
         "
      --DEFVAL      { 60 }
     ::= { hwH248MgSoftParameterEntry 30 }
     
     hwH248MgSoftParameter29 OBJECT-TYPE
     SYNTAX      Integer32(1..60000)
     MAX-ACCESS  read-write
     STATUS      current
     DESCRIPTION
         "
         Parameter name index 29.  It indicates the length of message waiting tone.
         Default: 3 
         Unit: second
         "
      --DEFVAL      { 3 }
     ::= { hwH248MgSoftParameterEntry 31 }
     
     hwH248MgSoftParameter30 OBJECT-TYPE
     SYNTAX      Integer32(1..65535)
     MAX-ACCESS  read-write
     STATUS      current
     DESCRIPTION
         "
         Parameter name index 30.  It indicates the length of long connect alarm.
         Default: 60 
         Unit: minute
         "
      --DEFVAL      { 60 }
     ::= { hwH248MgSoftParameterEntry 32 }
     
     hwH248MgSoftParameter31 OBJECT-TYPE
     SYNTAX      INTEGER{enable(1),disable(2)}
     MAX-ACCESS  read-write
     STATUS      current
     DESCRIPTION
         "
         Parameter name index 31.  It indicates whether MG send long connect alarm.  
         Options:
         1. enable(1)  -enable send long connect alarm 
         2. disable(2) -disable send long connect alarm
         Default: disable(2)
         "
      --DEFVAL      { disable(2) }
     ::= { hwH248MgSoftParameterEntry 33 }
     
      hwH248MgSoftParameter32 OBJECT-TYPE
     SYNTAX      Integer32(0..60000)
     MAX-ACCESS  read-write
     STATUS      current
     DESCRIPTION
         "
         Parameter name index 32.  The minimal length of port auto register timer.  
         Default: 1800
         Unit: second
         "
      --DEFVAL      { 1800 }
      ::= { hwH248MgSoftParameterEntry 34 }
 
       hwH248MgSoftParameter33 OBJECT-TYPE
     SYNTAX      INTEGER{shutdown(1),enable(2)}
     MAX-ACCESS  read-write
     STATUS      current
     DESCRIPTION
         "
         Parameter name index 33.  It indicates whether MG shutdown heartbeat.  
         Options:
         1. shutdown(1) -shutdown heartbeat
         2. enable(2)   -enable heartbeat
         Default: enable(2)
         "
      --DEFVAL      { 2 }
     ::= { hwH248MgSoftParameterEntry 35 }
      
      hwH248MgSoftParameter34 OBJECT-TYPE
     SYNTAX      INTEGER{yes(1),no(2)}
     MAX-ACCESS  read-write
     STATUS      current
     DESCRIPTION
         "
         Parameter name index 34.  It indicates whether the gateway actively sets up or cancels the link for the BRA user when the softswitch issues the in-service or out-of-service message.  
         Options:
         1. yes(1) -yes
         2. no(2)  -no
         Default: yes(1)
         "
      --DEFVAL      { 1 }
      ::= { hwH248MgSoftParameterEntry 36 }
      
        hwH248MgSoftParameter35 OBJECT-TYPE
     SYNTAX      INTEGER{both(1),singlechannel(2),wildcard(3)}
     MAX-ACCESS  read-write
     STATUS      current
     DESCRIPTION
         "
         Parameter name index 35. It indicates the mode for ISDN port is in service and out service.
         Options:
         1. both(1)          -supports in-service and out-of-service in single channel mode and wildcard mode
         2. singlechannel(2) -supports in-service and out-of-service in single channel mode
         3. wildcard(3)      -supports in-service and out-of-service in wildcard mode
         Default: singlechannel(2)
         "
      --DEFVAL      { 2 }
      ::= { hwH248MgSoftParameterEntry 37 }
      
     hwH248MgSoftParameter36 OBJECT-TYPE
     SYNTAX      Integer32(1..1800)
     MAX-ACCESS  read-write
     STATUS      current
     DESCRIPTION
         "
         Parameter name index 36. Indicates the baseline interval of sending the registration message during the switchover between multi-homing MGCs.
         Default: 40 
         Unit: second
         "
      --DEFVAL      { 40 }
     ::= { hwH248MgSoftParameterEntry 38 }  
            
          hwH248MgSoftParameter37 OBJECT-TYPE
     SYNTAX      INTEGER{enable(1),disable(2)}
     MAX-ACCESS  read-write
     STATUS      current
     DESCRIPTION
         "
         Parameter name index 37. The switch for the pulse signal switch to the DTMF signal.
         Options:
         1. enable(1)   -enable
         2. disable(2)  -disable
         Default: disable(2) 
         "
      --DEFVAL      { 2 }
     ::= { hwH248MgSoftParameterEntry 39 } 
     
     	hwH248MgSoftParameter38 OBJECT-TYPE
     SYNTAX      INTEGER{yes(1),no(2)}
     MAX-ACCESS  read-write
     STATUS      current
     DESCRIPTION
         "
         Parameter name index 38. Whether to send out-of-service message during on-hook line tests.
         Options:
         1. yes(1) -yes
         2. no(2)  -no
         Default: yes(1) 
         "
      --DEFVAL      { 1 }
     ::= { hwH248MgSoftParameterEntry 40 }        
              

    hwH248DmmParaTable OBJECT-TYPE
     SYNTAX      SEQUENCE OF HwH248DmmParaEntry
     MAX-ACCESS  not-accessible
     STATUS      current
     DESCRIPTION
       "
       This table is used to config the digitmap.
       The index of this table is hwH248DmmParaMgId.
       "
     ::= { hwIASVoipObjects 29 }
 
   hwH248DmmParaEntry OBJECT-TYPE
     SYNTAX      HwH248DmmParaEntry
     MAX-ACCESS  not-accessible
     STATUS      current
     DESCRIPTION
       "
       This table is used to config the digitmap.
       The index of this entry is hwH248DmmParaMgId.
       "
     INDEX    {  
               hwH248DmmParaMgId
              }
     ::= { hwH248DmmParaTable 1 }
 
   HwH248DmmParaEntry ::=
     SEQUENCE
     {
       hwH248DmmParaMgId	   Integer32,
       hwH248DmmParaStartTimer Integer32,
       hwH248DmmParaShortTimer Integer32,
       hwH248DmmParaLongTimer  Integer32,
       hwH248DmmParaDurationTimer  Integer32

     }
 
   hwH248DmmParaMgId OBJECT-TYPE
     SYNTAX      Integer32(0..16777215)
     MAX-ACCESS  not-accessible
     STATUS      current
     DESCRIPTION
         "
         Indicates the MG ID.
         "
     ::= { hwH248DmmParaEntry 1 }
 
   hwH248DmmParaStartTimer OBJECT-TYPE
     SYNTAX      Integer32(0..99)
     MAX-ACCESS  read-write
     STATUS      current
     DESCRIPTION
         "
         Indicates the length of the DMM start timer.
         Unit: second
         "
     ::= { hwH248DmmParaEntry 2 }
 
   hwH248DmmParaShortTimer OBJECT-TYPE
     SYNTAX      Integer32(1..99)
     MAX-ACCESS  read-write
     STATUS      current
     DESCRIPTION
         "
         Indicates the length of the DMM short timer.
         Unit: second
         "
     ::= { hwH248DmmParaEntry 3 }

   hwH248DmmParaLongTimer OBJECT-TYPE
     SYNTAX      Integer32(1..99)
     MAX-ACCESS  read-write
     STATUS      current
     DESCRIPTION
         "
         Indicates the length of the DMM long timer
         Unit: second
         "
     ::= { hwH248DmmParaEntry 4 }
     
   hwH248DmmParaDurationTimer OBJECT-TYPE
     SYNTAX      Integer32(100..9900)
     MAX-ACCESS  read-write
     STATUS      current
     DESCRIPTION
         "
         Indicates the length of the DMM duration timer.
         Unit: millisecond
         "
     ::= { hwH248DmmParaEntry 6 }

     
     hwOverloadReservalTable OBJECT-TYPE 
     SYNTAX      SEQUENCE OF HwOverloadReservalEntry
     MAX-ACCESS  not-accessible
     STATUS      current
     DESCRIPTION
       "
       This table is used to config the DSP reserved parameter.
       The index of this table is hwDspOverloadReservalMgId.
       "
     ::= { hwIASVoipObjects 31 }
 
   hwOverloadReservalEntry OBJECT-TYPE
     SYNTAX      HwOverloadReservalEntry
     MAX-ACCESS  not-accessible
     STATUS      current
     DESCRIPTION
       "
       This table is used to config the DSP reserved parameter.
       The index of this entry is hwDspOverloadReservalMgId.
       "
     INDEX    {  
               hwDspOverloadReservalMgId
              }
     ::= { hwOverloadReservalTable 1 }
 
   HwOverloadReservalEntry ::=
     SEQUENCE
     {
       hwDspOverloadReservalMgId 	 Integer32,
       hwTotalDspNum                     Integer32,
       hwTotalDspUseNum                  Integer32,
       
       hwReservalCat1DspNum              Integer32,
       hwActualCat1DspUseNum             Integer32,
       hwActualCat1CallUseDspNum         Integer32,
       
       hwReservalCat2DspNum              Integer32,
       hwActualCat2DspUseNum             Integer32,
       hwActualCat2CallUseDspNum         Integer32,
       
       hwDspReservalCommonNum            Integer32,
       hwActualCommonDspUseNum           Integer32,
       hwActualCommonCallUseDspNum       Integer32
     }
 
    hwDspOverloadReservalMgId OBJECT-TYPE
    SYNTAX      Integer32(0..16777215)           
    MAX-ACCESS  not-accessible
    STATUS      current
    DESCRIPTION
      "
      Indicates the MG ID to be configured.
      "
    ::= { hwOverloadReservalEntry 1 } 
    
    hwTotalDspNum OBJECT-TYPE
    SYNTAX      Integer32(0..3072)           
    MAX-ACCESS  read-write
    STATUS      current
    DESCRIPTION
      "
      Indicates the total count of DSPs.
      "   
   
    ::= { hwOverloadReservalEntry 2 }   
    
    hwTotalDspUseNum OBJECT-TYPE
    SYNTAX      Integer32(0..3072)           
    MAX-ACCESS  read-only
    STATUS      current
    DESCRIPTION
      "
      Indicates the total count of occupied DSPs.
      Default: 0
      "  
        
    ::= { hwOverloadReservalEntry 3 }  
    
    hwReservalCat1DspNum OBJECT-TYPE
    SYNTAX      Integer32(0..3072)           
    MAX-ACCESS  read-write
    STATUS      current
    DESCRIPTION
      "
      Indicates the count of the DSPs of category 1.
      "  
      DEFVAL      { 0 }  
    ::= { hwOverloadReservalEntry 4 }  
    
    hwActualCat1DspUseNum OBJECT-TYPE
    SYNTAX      Integer32(0..3072)           
    MAX-ACCESS  read-only
    STATUS      current
    DESCRIPTION
      "
      Indicates the count of the occupied DSPs of category 1.
      Default: 0
      "    
      
    ::= { hwOverloadReservalEntry 5 }  
    
    hwActualCat1CallUseDspNum OBJECT-TYPE
    SYNTAX      Integer32(0..3072)           
    MAX-ACCESS  read-only
    STATUS      current
    DESCRIPTION
      "
      Indicates the count of the DSPs of category 1 occupied by calls.
      Default: 0
      "  
        
    ::= { hwOverloadReservalEntry 6 }  
    
    hwReservalCat2DspNum OBJECT-TYPE
    SYNTAX      Integer32(0..3072)           
    MAX-ACCESS  read-write
    STATUS      current
    DESCRIPTION
      "
      Indicates the count of the DSPs of category 2.
      "  
      DEFVAL      { 0 }  
    ::= { hwOverloadReservalEntry 7 } 
    
    hwActualCat2DspUseNum OBJECT-TYPE
    SYNTAX      Integer32(0..3072)           
    MAX-ACCESS  read-only
    STATUS      current
    DESCRIPTION
      "
      Indicates the count of the occupied DSPs of category 2.
      Default: 0
      "    
      
    ::= { hwOverloadReservalEntry 8 }   
    
    hwActualCat2CallUseDspNum OBJECT-TYPE
    SYNTAX      Integer32(0..3072)           
    MAX-ACCESS  read-only
    STATUS      current
    DESCRIPTION
      "
      Indicates the count of the DSPs of category 2 occupied by calls.
      Default: 0
      "
         
    ::= { hwOverloadReservalEntry 9 }   
         
    hwDspReservalCommonNum OBJECT-TYPE
    SYNTAX      Integer32(0..3072)           
    MAX-ACCESS  read-only
    STATUS      current
    DESCRIPTION
      "
      Indicates the count of common DSPs reserved for configuration.
      "    
    ::= { hwOverloadReservalEntry 10 } 
    
    hwActualCommonDspUseNum OBJECT-TYPE
    SYNTAX      Integer32(0..3072)           
    MAX-ACCESS  read-only
    STATUS      current
    DESCRIPTION
      "
      Indicates the count of occupied common DSPs.
      Default: 0
      " 
         
    ::= { hwOverloadReservalEntry 11 } 
    
    hwActualCommonCallUseDspNum OBJECT-TYPE
    SYNTAX      Integer32(0..3072)           
    MAX-ACCESS  read-only
    STATUS      current
    DESCRIPTION
      "
      Indicates the count of the common DSPs occupied by calls.
      Default: 0
      " 
         
    ::= { hwOverloadReservalEntry 12 }   
    
        

     hwH248TIDConfigTable  OBJECT-TYPE
     SYNTAX      SEQUENCE OF HwH248TIDConfigEntry
     MAX-ACCESS  not-accessible
     STATUS      current
     DESCRIPTION
       "
       This table is used to config H248 terminal ID.
       The index of this table is hwVAGId.
       "
     ::= { hwIASVoipObjects 32 }
 
     hwH248TIDConfigEntry OBJECT-TYPE
     SYNTAX      HwH248TIDConfigEntry
     MAX-ACCESS  not-accessible
     STATUS      current
     DESCRIPTION
       "
       This table is used to config H248 terminal ID.
       The index of this entry is hwVAGId.
       "
     INDEX    {  
               hwVAGId
              }
     ::= { hwH248TIDConfigTable 1 }
 
     HwH248TIDConfigEntry ::=
     SEQUENCE
     {
       hwVAGId	Integer32,
       hwH248BraPrefix           OCTET STRING,
       hwH248PraPrefix           OCTET STRING,
       hwH248PstnPrefix          OCTET STRING,
       hwH248RtpPrefix           OCTET STRING,
       hwH248Separator           OCTET STRING,
       hwH248R2Prefix            OCTET STRING,
       hwH248DpnssPrefix         OCTET STRING,
       hwH248Dass2Prefix         OCTET STRING,
       hwH248BraTemplateIndex    Integer32,
       hwH248PraTemplateIndex    Integer32,
       hwH248PstnTemplateIndex   Integer32,
       hwH248RtpTemplateIndex    Integer32,
       hwH248R2TemplateIndex     Integer32,
       hwH248DpnssTemplateIndex  Integer32,
       hwH248Dass2TemplateIndex  Integer32,
       hwH248IsNeedToConfigTID   Integer32
     }
 
     hwVAGId OBJECT-TYPE
     SYNTAX      Integer32(0..16777215)
     MAX-ACCESS  not-accessible
     STATUS      current
     DESCRIPTION
         "
         Media Gateway ID.
         "
     ::= { hwH248TIDConfigEntry 1 }
 
     hwH248BraPrefix OBJECT-TYPE
     SYNTAX      OCTET STRING(SIZE (1..64))
     MAX-ACCESS  read-write
     STATUS      current
     DESCRIPTION
         "
         Indicates the BRA terminal prefix.
         "
     ::= { hwH248TIDConfigEntry 2 }
        
     hwH248PraPrefix OBJECT-TYPE
     SYNTAX      OCTET STRING(SIZE (1..64))
     MAX-ACCESS  read-write
     STATUS      current
     DESCRIPTION
         "
         Indicates the PRA terminal prefix.
         "
     ::= { hwH248TIDConfigEntry 3 }
        
     hwH248PstnPrefix OBJECT-TYPE
     SYNTAX      OCTET STRING(SIZE (1..64))
     MAX-ACCESS  read-write
     STATUS      current
     DESCRIPTION
         "
         Indicates the PSTN terminal prefix.
         "
     ::= { hwH248TIDConfigEntry 4 }
          
     hwH248RtpPrefix OBJECT-TYPE
     SYNTAX      OCTET STRING(SIZE (1..64))
     MAX-ACCESS  read-write
     STATUS      current
     DESCRIPTION
         "
         Indicates the RTP terminal prefix.
         "
     ::= { hwH248TIDConfigEntry 5 }
     
     hwH248Separator OBJECT-TYPE
     SYNTAX      OCTET STRING(SIZE (0..7))
     MAX-ACCESS  read-only
     STATUS      current
     DESCRIPTION
         "
         Indicates the terminal separator.
         "
     ::= { hwH248TIDConfigEntry 6 }
     
     hwH248R2Prefix OBJECT-TYPE
     SYNTAX      OCTET STRING(SIZE (1..64))
     MAX-ACCESS  read-write
     STATUS      current
     DESCRIPTION
         "
         Indicates the R2 terminal prefix.
         "
     ::= { hwH248TIDConfigEntry 7 }
     
     hwH248DpnssPrefix OBJECT-TYPE
     SYNTAX      OCTET STRING(SIZE (1..64))
     MAX-ACCESS  read-write
     STATUS      current
     DESCRIPTION
         "
         Indicates the DPNSS terminal prefix.
         "
     ::= { hwH248TIDConfigEntry 8 }   
     
     hwH248Dass2Prefix OBJECT-TYPE
     SYNTAX      OCTET STRING(SIZE (1..64))
     MAX-ACCESS  read-write
     STATUS      current
     DESCRIPTION
         "
         Indicates the DASS2 terminal prefix.
         "
     ::= { hwH248TIDConfigEntry 9 }    
     
     hwH248BraTemplateIndex OBJECT-TYPE
     SYNTAX      Integer32(0..63)
     MAX-ACCESS  read-write
     STATUS      current
     DESCRIPTION
         "
         Indicates the index of the BRA TID profile.
         "
     ::= { hwH248TIDConfigEntry 10 }     
     
     hwH248PraTemplateIndex OBJECT-TYPE
     SYNTAX      Integer32(0..63)
     MAX-ACCESS  read-write
     STATUS      current
     DESCRIPTION
         "
         Indicates the index of the PRA TID profile.
         "
     ::= { hwH248TIDConfigEntry 11 }     
     
     hwH248PstnTemplateIndex OBJECT-TYPE
     SYNTAX      Integer32(0..63)
     MAX-ACCESS  read-write
     STATUS      current
     DESCRIPTION
         "
         Indicates the index of the PSTN TID profile.
         "
     ::= { hwH248TIDConfigEntry 12 }       
     
     hwH248RtpTemplateIndex OBJECT-TYPE
     SYNTAX      Integer32(0..63)
     MAX-ACCESS  read-write
     STATUS      current
     DESCRIPTION
         "
         Indicates the index of the RTP TID profile.
         "
     ::= { hwH248TIDConfigEntry 13 }     
     
     hwH248R2TemplateIndex OBJECT-TYPE
     SYNTAX      Integer32(0..63)
     MAX-ACCESS  read-write
     STATUS      current
     DESCRIPTION
         "
         Indicates the index of the R2 TID profile.
         "
     ::= { hwH248TIDConfigEntry 14 } 
     
     hwH248DpnssTemplateIndex OBJECT-TYPE
     SYNTAX      Integer32(0..63)
     MAX-ACCESS  read-write
     STATUS      current
     DESCRIPTION
         "
         Indicates the index of the DPNSS TID profile.
         "
     ::= { hwH248TIDConfigEntry 15 }     
     
     hwH248Dass2TemplateIndex OBJECT-TYPE
     SYNTAX      Integer32(0..63)
     MAX-ACCESS  read-write
     STATUS      current
     DESCRIPTION
         "
         Indicates the index of the DASS2 TID profile.
         "
     ::= { hwH248TIDConfigEntry 16 }  
     
     hwH248IsNeedToConfigTID OBJECT-TYPE
     SYNTAX      Integer32
     MAX-ACCESS  read-only
     STATUS      current
     DESCRIPTION
         "
         Indicates whether the terminal ID needs to be configured for the subscriber. Bit0 (low) to bit31 (high) respectively represent PSTN, BRA, PRA, DPNSS, DASS2, and R2. The remaining bits are reserved. (It is unavailable in the R17.)
         "
     ::= { hwH248TIDConfigEntry 17 }        


     hwFEifIndex OBJECT-TYPE
     SYNTAX      Integer32
     MAX-ACCESS  read-only
     STATUS      current
     DESCRIPTION
       "
       Indicates the interface index (interface type + shelf + slot + port).
       "
     ::= { hwIASVoipAlarmOids 1 }
 
     hwVpuDspFailReason OBJECT-TYPE
     SYNTAX      INTEGER{dspFault(1),voipMoudleSoftwareOverload(2),voipMoudleFault(3)}
     MAX-ACCESS  read-only
     STATUS      current
     DESCRIPTION
       "
       Indicates the definition of the cause of the DSP chip fault.
       Options:
       1. dspFault(1) -dsp fault
       2. voipMoudleSoftwareOverload(2) -voip module software overload
       3. voipMoudleFault(3) -voip module fault
       "
     ::= { hwIASVoipAlarmOids 2 }
 
     hwVpuFeReson OBJECT-TYPE
     SYNTAX      INTEGER{peerNonautoneg(1),autonegSucc(2),nonautonegOnlineSucc(3),autonegOnlineFail(4),portOffline(5)}
     MAX-ACCESS  read-only
     STATUS      current
     DESCRIPTION
       "
       Indicates the definition of the cause of the VPU FE port fault.
       Options:
       1. peerNonautoneg(1) -peer nonautoneg
       2. autonegSucc(2) -autoneg succeed
       3. nonautonegOnlineSucc(3) -nonautoneg online succeed
       4. autonegOnlineFail(4) -autoneg online fail
       5. portOffline(5) -port offline
       "
     ::= { hwIASVoipAlarmOids 3 }
 
     hwVpuSubBIndex OBJECT-TYPE
     SYNTAX      Integer32
     MAX-ACCESS  read-only
     STATUS      current
     DESCRIPTION
       "
       Indicates the VPU subboard index.
       "
     ::= { hwIASVoipAlarmOids 4 }
 
     hwVpuDspChipIndex OBJECT-TYPE
     SYNTAX      Integer32
     MAX-ACCESS  read-only
     STATUS      current
     DESCRIPTION
       "
       Indicates the VPU DSP chip index.
       "
     ::= { hwIASVoipAlarmOids 5 }
 
     hwMedGwyAlarmMgId OBJECT-TYPE
     SYNTAX      Integer32(0..16777215)
     MAX-ACCESS  read-only
     STATUS      current
     DESCRIPTION
       "
       Indicates the MG ID.
       "
     ::= { hwIASVoipAlarmOids 6 }


 --  Notification type under Node hwIASVoipAlarmTraps
 	hwVpuDspChipFail NOTIFICATION-TYPE
 	OBJECTS { hwFEifIndex,hwVpuSubBIndex,hwVpuDspChipIndex,hwVpuDspFailReason }
 	STATUS current
 	DESCRIPTION
 		"
 		This notification indicates that the vpu dsp chip fail.
 		"
 	::= { hwIASVoipAlarmTraps 1 }
 	hwVpuDspChipRestore NOTIFICATION-TYPE
 	OBJECTS { hwFEifIndex,hwVpuSubBIndex,hwVpuDspChipIndex,hwVpuDspFailReason }
 	STATUS current
 	DESCRIPTION
 		"
 		This notification indicates that the vpu dsp chip restore form fault.
 		"
 	::= { hwIASVoipAlarmTraps 2 }
 	hwVpuFeInterfaceFail NOTIFICATION-TYPE
 	OBJECTS { hwFEifIndex,hwVpuFeReson }
 	STATUS current
 	DESCRIPTION
 		"
 		This notification indicates that the vpu fe port fail.
 		"
 	::= { hwIASVoipAlarmTraps 3 }
 	hwVpuFeInterfaceRestore NOTIFICATION-TYPE
 	OBJECTS { hwFEifIndex,hwVpuFeReson }
 	STATUS current
 	DESCRIPTION
 		"
 		This notification indicates that the vpu fe port restore from fault.
 		"
 	::= { hwIASVoipAlarmTraps 4 }
 	hwMedGwyFailAlarm NOTIFICATION-TYPE
 	OBJECTS { hwMedGwyAlarmMgId }
 	STATUS current
 	DESCRIPTION
 		"
 		This notification indicates that the mg interface failed.
 		"
 	::= { hwIASVoipAlarmTraps 5 }
 	hwMedGwyRestoreAlarm NOTIFICATION-TYPE
 	OBJECTS { hwMedGwyAlarmMgId }
 	STATUS current
 	DESCRIPTION
 		"
 		This notification indicates that the mg interface restore.
 		"
 	::= { hwIASVoipAlarmTraps 6 }  
 	hwVpuSubbFail NOTIFICATION-TYPE
 	OBJECTS { hwFEifIndex,hwVpuSubBIndex,hwVpuDspFailReason }
 	STATUS current
 	DESCRIPTION
 		"
 		This notification indicates that the vpu dsp sub board fail.
 		"
 	::= { hwIASVoipAlarmTraps 7 }
 	hwVpuSubbRestore NOTIFICATION-TYPE
 	OBJECTS { hwFEifIndex,hwVpuSubBIndex,hwVpuDspFailReason }
 	STATUS current
 	DESCRIPTION
 		"
 		This notification indicates that the vpu dsp sub board restore.  
 		"
 	::= { hwIASVoipAlarmTraps 8 }
 	
  
     hwH248ProfileSupportTable OBJECT-TYPE
     SYNTAX      SEQUENCE OF HwH248ProfileSupportEntry
     MAX-ACCESS  not-accessible
     STATUS      current
     DESCRIPTION
       "
       This table is used to set the H248 profile configuration.
       The index of this table is hwH248ProfileIndex.
       "
     ::= { hwIASVoipObjects 67 }
 
   hwH248ProfileSupportEntry OBJECT-TYPE
     SYNTAX      HwH248ProfileSupportEntry
     MAX-ACCESS  not-accessible
     STATUS      current
     DESCRIPTION
       "
       This table is used to set the H248 profile configuration.
       The index of this entry is hwH248ProfileIndex.
       "
     INDEX    {  
                hwH248ProfileIndex
              }
     ::= { hwH248ProfileSupportTable 1 }
 
   HwH248ProfileSupportEntry ::=
     SEQUENCE
     {
       hwH248ProfileIndex       Integer32,
       hwH248ProfileCfgName	OCTET STRING,
       hwH248ProfileRegName     OCTET STRING
     }
 
   hwH248ProfileIndex OBJECT-TYPE
     SYNTAX      Integer32(0..254)
     MAX-ACCESS  not-accessible
     STATUS      current
     DESCRIPTION
         "
         Indicates the profile index.
         "
     ::= { hwH248ProfileSupportEntry 1 }   
     
   hwH248ProfileCfgName OBJECT-TYPE
     SYNTAX      OCTET STRING
     MAX-ACCESS  read-only
     STATUS      current
     DESCRIPTION
         "
         Indicates the configuration name of the profile.
         "
     ::= { hwH248ProfileSupportEntry 2 } 
     
   hwH248ProfileRegName OBJECT-TYPE
     SYNTAX      OCTET STRING
     MAX-ACCESS  read-only
     STATUS      current
     DESCRIPTION
         "
         Indicates the registration name (that is, the negotiation name) of the profile.
         "
     ::= { hwH248ProfileSupportEntry 3 }          
        

     hwH248MedGwyCurTableTable OBJECT-TYPE
     SYNTAX      SEQUENCE OF HwH248MedGwyCurTableEntry
     MAX-ACCESS  not-accessible
     STATUS      current
     DESCRIPTION
       "
       This table is used to query the current parameter configuration status of the MG interface.
       The index of this table is hwH248MgId.
       "
     ::= { hwIASVoipObjects 68 }
 
   hwH248MedGwyCurTableEntry OBJECT-TYPE
     SYNTAX      HwH248MedGwyCurTableEntry
     MAX-ACCESS  not-accessible
     STATUS      current
     DESCRIPTION
       "
       This table is used to query the current parameter configuration status of the MG interface.
       The index of this entry is hwH248MgId.
       "
     INDEX    {  
                hwH248MgId
              }
     ::= { hwH248MedGwyCurTableTable 1 }
 
     HwH248MedGwyCurTableEntry ::=
     SEQUENCE
     {
       hwH248MgId       Integer32,
       hwH248MedGwyProfileIndexCur  Integer32,
       hwH248MedGwyH248VersionCur     INTEGER,
       hwH248MedGwyHeartBeatTimerCur  Integer32,
       hwH248MedGwyMIDTypeCur         INTEGER,
       hwH248MedGwyDeviceNameCur      OCTET STRING,
       hwH248ProfileNegoParaCur        INTEGER,
       hwH248ProfileCfgNameCur         OCTET STRING,
       hwH248ProfileNegoNameCur        OCTET STRING,
       hwH248MedGwySigIPAddrNameCur    OCTET STRING,
       hwH248MedGwyMediaIPAddrNameCur  OCTET STRING,
       hwH248MedGwySigIPAddress1Cur    IpAddress,
       hwH248MedGwyMediaIPAddress1Cur  IpAddress
     }
 
     hwH248MgId OBJECT-TYPE
     SYNTAX      Integer32(0..16777215)
     MAX-ACCESS  not-accessible
     STATUS      current
     DESCRIPTION
         "
         Indicates the MG ID.
         "
     ::= { hwH248MedGwyCurTableEntry 1 }   
     
     hwH248MedGwyProfileIndexCur OBJECT-TYPE
     SYNTAX      Integer32(0..254)
     MAX-ACCESS  read-only
     STATUS      current
     DESCRIPTION
         "
         Indicates the profile index that is currently used by the MG.
         "
     ::= { hwH248MedGwyCurTableEntry 2 } 
     
     
     hwH248MedGwyH248VersionCur   OBJECT-TYPE
     SYNTAX      INTEGER{v1(1), -- version 1
                         v2(2), -- version 2
                         v3(3)  -- version 3
                         }
     MAX-ACCESS  read-only
     STATUS      current
     DESCRIPTION
         "
         Indicates the current H.248 version of the MG.
         Options:
         1. v1(1) -version 1
         2. v2(2) -version 2
         3. v3(3) -version 3
         "
     ::= { hwH248MedGwyCurTableEntry 3 }          
        
     hwH248MedGwyHeartBeatTimerCur  OBJECT-TYPE
     SYNTAX      Integer32(0..65535)
     MAX-ACCESS  read-only
     STATUS      current
     DESCRIPTION
         "
         Indicates the current length of the initial heartbeat timer.
         The valid value range is 1..65535, if the value is 0, the heartbeat is not started.
         Unit: second
         "
     ::= { hwH248MedGwyCurTableEntry 4 } 
     
     hwH248MedGwyMIDTypeCur OBJECT-TYPE
     SYNTAX      INTEGER{ip4Address(1), -- IP address
                         domainName(2), -- domain name
                         deviceName(3)  -- device name
                         }
     MAX-ACCESS  read-only
     STATUS      current
     DESCRIPTION
         "
         Indicates the current message MID type of the MG.
         Options:
         1. ip4Address(1) -IP address
         2. domainName(2) -domain name
         3. deviceName(3) -device name
         "
     ::= { hwH248MedGwyCurTableEntry 5 }
     
     hwH248MedGwyDeviceNameCur OBJECT-TYPE
     SYNTAX      OCTET STRING(SIZE (0..64))
     MAX-ACCESS  read-only
     STATUS      current
     DESCRIPTION
         "
         Indicates the current device name of the MG.
         "
     ::= { hwH248MedGwyCurTableEntry 6 }
     
     hwH248ProfileNegoParaCur  OBJECT-TYPE
     SYNTAX      INTEGER{ disable(1),enable(2) }
     MAX-ACCESS  read-only
     STATUS      current
     DESCRIPTION
         "
         Indicates whether the profile currently used by the MG supports the profile parameter negotiation.
         Options:
         1. disable(1)  -disable
         2. enable(2)   -enable
         "
     ::= { hwH248MedGwyCurTableEntry 7 }
     
     hwH248ProfileCfgNameCur OBJECT-TYPE
     SYNTAX      OCTET STRING(SIZE (1..67))
     MAX-ACCESS  read-only
     STATUS      current
     DESCRIPTION
         "
         Indicates the configuration name of the H.248 profile currently used by the MG.
         "
     ::= { hwH248MedGwyCurTableEntry 8 }
     
     hwH248ProfileNegoNameCur OBJECT-TYPE
     SYNTAX      OCTET STRING(SIZE (0..67))
     MAX-ACCESS  read-only
     STATUS      current
     DESCRIPTION
         "
         Indicates the negotiation name of the H.248 profile currently used by the MG.
         "
     ::= { hwH248MedGwyCurTableEntry 9 } 
     
     hwH248MedGwySigIPAddrNameCur OBJECT-TYPE
     SYNTAX      OCTET STRING(SIZE (0..64))
     MAX-ACCESS  read-only
     STATUS      current
     DESCRIPTION
         "
         Indicates the current working dynamic signal IP name.
         "
     ::= { hwH248MedGwyCurTableEntry 10 }   
     
     hwH248MedGwyMediaIPAddrNameCur OBJECT-TYPE
     SYNTAX      OCTET STRING(SIZE (0..64))
     MAX-ACCESS  read-only
     STATUS      current
     DESCRIPTION
         "
         Indicates the current working dynamic media IP name.
         "
     ::= { hwH248MedGwyCurTableEntry 11 }   
     
     
    
     hwH248MedGwySigIPAddress1Cur OBJECT-TYPE
     SYNTAX      IpAddress
     MAX-ACCESS  read-only
     STATUS      current
     DESCRIPTION
         "
         Indicates the signaling IP address of currently used by the MG.
         "
     ::= { hwH248MedGwyCurTableEntry 12 } 
     
     hwH248MedGwyMediaIPAddress1Cur OBJECT-TYPE
     SYNTAX      IpAddress
     MAX-ACCESS  read-only
     STATUS      current
     DESCRIPTION
         "
         Indicates the media IP address of currently used by the MG.
         "
     ::= { hwH248MedGwyCurTableEntry 13 }     
  
   hwH248ExtMgcTable OBJECT-TYPE
     SYNTAX      SEQUENCE OF HwH248ExtMgcEntry
     MAX-ACCESS  not-accessible
     STATUS      current
     DESCRIPTION
       "
       This table is used to config Extended MGC.
       The indexes of this table are hwH248ExtMgcMedGwyId and hwH248ExtMgcNo.
       "
     ::= { hwIASVoipObjects 204 }
     
   hwH248ExtMgcEntry OBJECT-TYPE
     SYNTAX      HwH248ExtMgcEntry
     MAX-ACCESS  not-accessible
     STATUS      current
     DESCRIPTION
       "
       This table is used to config Extended MGC.
       The index of this entry is hwH248ExtMgcMedGwyId and hwH248ExtMgcNo.
       "
     INDEX    { 
               hwH248ExtMgcMedGwyId, 
               hwH248ExtMgcNo
              }
     ::= { hwH248ExtMgcTable 1 }
 
   HwH248ExtMgcEntry ::=
     SEQUENCE
     {
       hwH248ExtMgcMedGwyId     Integer32,
       hwH248ExtMgcNo           Integer32,
       hwH248ExtMgcType	        INTEGER,
       hwH248ExtMgcIp            IpAddress,
       hwH248ExtMgcPort         Integer32,
       hwH248ExtMgcRowStatus    RowStatus
     }
     
   hwH248ExtMgcMedGwyId OBJECT-TYPE
     SYNTAX      Integer32(0..16777215)
     MAX-ACCESS  not-accessible
     STATUS      current
     DESCRIPTION
         "
         Media Gateway ID.
         "
     ::= { hwH248ExtMgcEntry 1 }
 
   hwH248ExtMgcNo OBJECT-TYPE
     SYNTAX      Integer32(0..7)
     MAX-ACCESS  not-accessible
     STATUS      current
     DESCRIPTION
         "
         Extended MGC number.
         "
     ::= { hwH248ExtMgcEntry 2 }
 
   hwH248ExtMgcType OBJECT-TYPE
     SYNTAX      INTEGER{primary(1), -- primary
                         secondary(2) -- secondary
                         }
     MAX-ACCESS  read-write
     STATUS      current
     DESCRIPTION
         "
         Extended MGC for primary MGC or secondary MGC.
         Options:
         1. primary(1) -primary
         2. secondary(2) -secondary
         "   
     ::= { hwH248ExtMgcEntry 3 }
 
   hwH248ExtMgcIp OBJECT-TYPE
     SYNTAX      IpAddress
     MAX-ACCESS  read-write
     STATUS      current
     DESCRIPTION
         "
         Indicates the signaling IP address of the Extended MGC.
         "   
     ::= { hwH248ExtMgcEntry 4 }  
     
   hwH248ExtMgcPort OBJECT-TYPE
     SYNTAX      Integer32(2900..2999)
     MAX-ACCESS  read-write
     STATUS      current
     DESCRIPTION
         "
         Signalling UDP port that the Extended MGC will use to communicate with the Media Gateway.
         Default:2944.
         "   
     ::= { hwH248ExtMgcEntry 5 } 
     
   hwH248ExtMgcRowStatus OBJECT-TYPE
     SYNTAX      RowStatus
     MAX-ACCESS  read-write
     STATUS      current
     DESCRIPTION
         "
         This is used to create new rows in this table, modify existing rows, and to delete existing rows.
         "
     ::= { hwH248ExtMgcEntry 6 }        
--  /* Start hwIASH248TrapsVbOids */
    
     hwH248TrapRequestID OBJECT-TYPE
     SYNTAX Unsigned32(0..4294967295)
     MAX-ACCESS accessible-for-notify
     STATUS current
     DESCRIPTION
         "
         The h248 trap request ID.
         "
     ::= { hwIASH248TrapsVbOids 1 }

     hwH248MgStatus OBJECT-TYPE
     SYNTAX INTEGER
        {
            up(1),
    	    close(2),
    	    gracefulClose(3),
    	    waitAck(4),
    	    fault(5)
        }
     MAX-ACCESS accessible-for-notify
     STATUS current
     DESCRIPTION
         "
	     The status of the h248 media gateway.
	     Options:
	     1. up(1) -normal
	     2. close(2) -closed
	     3. gracefulClose(3) -graceful closing
	     4. waitAck(4) -waiting for ACK
	     5. fault(5) -fault
         "
     ::= { hwIASH248TrapsVbOids 2 }
     
     hwH248TrapLastChangeTime OBJECT-TYPE
     SYNTAX TimeTicks
     MAX-ACCESS accessible-for-notify
     STATUS current
     DESCRIPTION
         "
	 The value of sysUpTime at the time the media gateway or the media gateway control entered its current status or media gateway control switched.
         "
     ::= { hwIASH248TrapsVbOids 3 }
     
     hwH248MgcIpAddress OBJECT-TYPE
     SYNTAX IpAddress
     MAX-ACCESS accessible-for-notify
     STATUS current
     DESCRIPTION
         "
	     The mgc ip address.
         "
     ::= { hwIASH248TrapsVbOids 4 }
     
     hwH248MgcIndex OBJECT-TYPE
     SYNTAX Unsigned32(0..1)
     MAX-ACCESS accessible-for-notify
     STATUS current
     DESCRIPTION
         "
	     The current mgc index.
         "
     ::= { hwIASH248TrapsVbOids 5 } 

     hwH248MgcStatus OBJECT-TYPE
     SYNTAX INTEGER{ up(1), down(2), standby(3) }
     MAX-ACCESS accessible-for-notify
     STATUS current
     DESCRIPTION
         "
	     The media gateway control status.
	     Options:
	     1. up(1)     -active
	     2. down(2)   -shut down
	     3. standby(3) -standby
         "
     ::= { hwIASH248TrapsVbOids 6 } 

     hwH248Frame OBJECT-TYPE
     SYNTAX Unsigned32(0..255)
     MAX-ACCESS accessible-for-notify
     STATUS current
     DESCRIPTION
         "
	     The frame where mg user is configed.
         "
     ::= { hwIASH248TrapsVbOids 7 } 
    
     hwH248Slot OBJECT-TYPE
     SYNTAX Unsigned32(0..255)
     MAX-ACCESS accessible-for-notify
     STATUS current
     DESCRIPTION
         "
	     The slot where mg user is configed.
         "
     ::= { hwIASH248TrapsVbOids 8 } 
     
     hwH248Port OBJECT-TYPE
     SYNTAX Unsigned32(0..255)
     MAX-ACCESS accessible-for-notify
     STATUS current
     DESCRIPTION
         "
	     The port where mg user is configed.
         "
     ::= { hwIASH248TrapsVbOids 9 }  
     
     hwH248LongConnectDuration OBJECT-TYPE
     SYNTAX Unsigned32(0..4294967295)
     MAX-ACCESS accessible-for-notify
     STATUS current
     DESCRIPTION
         "
	     The duration of a long connect.
         "
     ::= { hwIASH248TrapsVbOids 10 }     
     
     hwH248UserTelNo OBJECT-TYPE
     SYNTAX      OCTET STRING(SIZE (1..16))
     MAX-ACCESS accessible-for-notify
     STATUS current
     DESCRIPTION
         "
	     The user telphone number.
         "
     ::= { hwIASH248TrapsVbOids 11 }
     
     hwH248MgcPort OBJECT-TYPE
     SYNTAX Unsigned32(0..65535)
     MAX-ACCESS accessible-for-notify
     STATUS current
     DESCRIPTION
         "
	     The UDP port of MGC connected.
         "
     ::= { hwIASH248TrapsVbOids 12 }
     
     hwH248OnlineUser OBJECT-TYPE
     SYNTAX Unsigned32(0..4294967295)
     MAX-ACCESS accessible-for-notify
     STATUS current
     DESCRIPTION
         "
	     The number of online user.
         "
     ::= { hwIASH248TrapsVbOids 13 }
     
     hwH248InnerCall OBJECT-TYPE
     SYNTAX Unsigned32(0..4294967295)
     MAX-ACCESS accessible-for-notify
     STATUS current
     DESCRIPTION
         "
	     The number of inner-call.
         "
     ::= { hwIASH248TrapsVbOids 14 }     
     
     hwH248RejectCall OBJECT-TYPE
     SYNTAX Unsigned32(0..4294967295)
     MAX-ACCESS accessible-for-notify
     STATUS current
     DESCRIPTION
         "
	     The number of calls rejected.
         "
     ::= { hwIASH248TrapsVbOids 15 } 
     
     hwH248IsConfigTid OBJECT-TYPE
     SYNTAX Unsigned32(0..4294967295)
     MAX-ACCESS accessible-for-notify
     STATUS current
     DESCRIPTION
     	"
     	Indicates whether the terminal ID needs to be configured for the subscriber. Bit0 (low) to bit31 (high) respectively represent PSTN, BRA, PRA, DPNSS, DASS2, and R2. The remaining bits are reserved.
     	"
     ::= { hwIASH248TrapsVbOids 16 }
     
     hwH248IsUpdateTid OBJECT-TYPE
     SYNTAX Unsigned32(0..4294967295)
     MAX-ACCESS accessible-for-notify
     STATUS current
     DESCRIPTION
     	"
     	Indicates whether the terminal ID needs to be updated for the subscriber. Bit0 (low) to bit31 (high) respectively represent PSTN, BRA, PRA, DPNSS, DASS2, and R2. The remaining bits are reserved.
     	"
     ::= { hwIASH248TrapsVbOids 17 }
               
--  /*  End  hwIASH248TrapsVbOids */    
     
--  /* Start hwIASH248CommonTraps */
	
     hwIASH248ResetTrap NOTIFICATION-TYPE
     OBJECTS { hwH248TrapRequestID, hwH248MedGwyId, hwH248MgStatus, hwH248TrapLastChangeTime }
     STATUS current
     DESCRIPTION
         "
         This notification indicates that the result of h248 media gateway reset operation.
         "
     ::= { hwIASH248CommonTraps 0 1 }
     
     hwIASH248ShutdownTrap NOTIFICATION-TYPE
     OBJECTS { hwH248TrapRequestID, hwH248MedGwyId, hwH248MgStatus, hwH248TrapLastChangeTime }
     STATUS current
     DESCRIPTION
         "
         This notification indicates that the h248 media gateway shutdown result.
         "
     ::= { hwIASH248CommonTraps 0 2 }
     
     hwIASH248MgStateTrap NOTIFICATION-TYPE
     OBJECTS { hwH248TrapRequestID, hwH248MedGwyId, hwH248MgStatus, hwH248TrapLastChangeTime }
     STATUS current
     DESCRIPTION
         "
         This notification indicates that the h248 media gateway status changes.
         "
     ::= { hwIASH248CommonTraps 0 3 }

     hwIASH248MgcSwitchTrap NOTIFICATION-TYPE
     OBJECTS { hwH248TrapRequestID, hwH248MedGwyId, hwH248MgcIndex, hwH248MgcStatus, hwH248TrapLastChangeTime }
     STATUS current
     DESCRIPTION
         "
         This notification indicates that the h248 media gateway control switchs.
         "
     ::= { hwIASH248CommonTraps 0 4 }
     
     hwIASH248MgcStateTrap NOTIFICATION-TYPE
     OBJECTS { hwH248TrapRequestID, hwH248MedGwyId, hwH248MgcIndex, hwH248MgcStatus, hwH248TrapLastChangeTime }
     STATUS current
     DESCRIPTION
         "
         This notification indicates that the h248 media gateway status changed.
         "
     ::= { hwIASH248CommonTraps 0 5 }

     hwIASH248MgLableTrap NOTIFICATION-TYPE
     OBJECTS { hwH248MedGwyId, hwH248MedGwyDesc }
     STATUS current
     DESCRIPTION
         "
         This notification indicates that the userlabel of the H248 interface changed.
         "
     ::= { hwIASH248CommonTraps 0 6 }

     hwIASH248TidUpdateTrap NOTIFICATION-TYPE
     OBJECTS { hwH248MedGwyId, hwH248IsConfigTid, hwH248IsUpdateTid }
     STATUS current
     DESCRIPTION
         "
         This notification indicates that the H248 terminal ID updated.
         "
     ::= { hwIASH248CommonTraps 0 7 }     
--  /*  End  hwIASH248CommonTraps */
     
--  /* Start hwIASH248AlarmTraps */

    hwIASH248MgFaultTrap NOTIFICATION-TYPE
    OBJECTS  { hwH248MedGwyId, hwH248MgcIpAddress, hwH248MgcPort, hwH248OnlineUser }
    STATUS      current
    DESCRIPTION    
        "
        This notification indicates that the h248 media gateway is closed.
        "
    ::= { hwIASH248AlarmTraps 0 1 }
    
    hwIASH248MgRestoreTrap NOTIFICATION-TYPE
    OBJECTS  { hwH248MedGwyId, hwH248MgcIpAddress, hwH248MgcPort, hwH248InnerCall, hwH248RejectCall }
    STATUS      current
    DESCRIPTION    
        "
        This notification indicates that the h248 media gateway is normal.
        "
    ::= { hwIASH248AlarmTraps 0 2 }
    
    hwIASH248AbsentBandwidthTrap NOTIFICATION-TYPE
    STATUS      current
    DESCRIPTION    
        "
        This notification indicates that bandwidth occupied by VoIP calls exceeds the threshold.
        "
    ::= { hwIASH248AlarmTraps 0 3 }
    
    hwIASH248LongConnectTrap NOTIFICATION-TYPE
    OBJECTS  { hwH248Frame, hwH248Slot, hwH248Port, hwH248LongConnectDuration, hwH248UserTelNo }
    STATUS      current
    DESCRIPTION    
        "
        This notification indicates that the H248 user has calls for a long time.
        "
    ::= { hwIASH248AlarmTraps 0 4 }
    
--  /*  End  hwIASH248AlarmTraps */

 
END
