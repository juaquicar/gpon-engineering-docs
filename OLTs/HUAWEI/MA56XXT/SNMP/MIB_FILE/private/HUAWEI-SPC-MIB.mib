-- ============================================================================
-- Copyright (C) 2015 by HUAWEI TECHNOLOGIES. All rights reserved.
-- Description: The MIB module defines Huawei's SPC management MIB objects.
-- Reference:
-- Version: V3.17
-- ============================================================================     
	    HUAWEI-SPC-MIB DEFINITIONS ::= BEGIN
		IMPORTS
			huaweiUtility
				FROM HUAWEI-MIB
			Integer32, IpAddress, OBJECT-TYPE, NOTIFICATION-TYPE, MODULE-IDENTITY, Unsigned32
				FROM SNMPv2-SMI
			RowStatus
				FROM SNMPv2-TC;
		


		hwSPC MODULE-IDENTITY
			LAST-UPDATED "201507200000Z"
			ORGANIZATION "Huawei Technologies Co.,Ltd."
			CONTACT-INFO                                        
			             "Huawei Industrial Base                
                                      Bantian, Longgang                     
                                      Shenzhen 518129                       
                                      People's Republic of China            
                                      Website: http://www.huawei.com        
                                      Email: support@huawei.com                          
                                     "                                      
			DESCRIPTION
				"The MIB module defines Huawei's SPC management MIB objects.
				"

	    -- Revision history      
	    REVISION     "201507200000Z"
            DESCRIPTION  "V3.17, added hw2833IPSpcServiceState to hwSpcMngtTable.
                                 modify the value range of hwSpcSignalType,hwSpcInitialRingType,hwSpcCadenceRingType."

	    REVISION     "201407110000Z"
            DESCRIPTION  "V3.16, modify the node name of hwSignalType to hwSpcSignalType."

	    REVISION     "201406280000Z"
            DESCRIPTION  "V3.15, Modify the following not normative nodes to satisfy for the new OMSYS tool.     
                       hwSpcMibObjects     
                       hwSpcNo      
                       hwApptype       
                       hwSpcMibTrap      
                       hwSpcMibCompance      
                       hwIASSpcTrapsVbOids
                       hwIASSpcTraps"
            
	    REVISION     "201312160000Z"
            DESCRIPTION  "V3.14, added hwIASSpcCommonTrapsPrefix to hwIASSpcCommonTraps."
            
	    REVISION     "201312160000Z"
            DESCRIPTION  "V3.14, added hwIASSpcAlarmTrapsPrefix to hwIASSpcAlarmTraps."
	    
	    REVISION     "201303280000Z"
            DESCRIPTION  "V1.33, modify the value range of hwIpSpcAttributeVoiceCode,hwIpSpcAttributeVoiceCode,hwIpSpcAttributeEce,
                                                           hwIpSpcAttributeSce,hwIpSpcAttributeRtpInterval,hwIpSpcAttributePlc,
                                                           hwIpSpcAttributeRfc2198,hwIpSpcAttributeJbMode,hwIpSpcAttributeWorkMode,
                                                           hwIpSpcAttributeStreamMode,hwRemotePortStepNum in hwSpcMngtTable."
            REVISION     "201302170000Z"
            DESCRIPTION  "V3.13, added hwIpSpcMinUdp, hwIpSpcMaxUdp to hwSpcMibObjects."
			
            REVISION     "201009030000Z"
            DESCRIPTION  "V3.12, corrected  error descriptions." 
            
            REVISION     "201007030000Z"
            DESCRIPTION  "V3.11, corrected  errors." 
            
            REVISION     "201005280000Z"            
            DESCRIPTION  "V3.10, corrected the update date."             
           
            REVISION     "201004100000Z"
            DESCRIPTION  "V3.09, corrected the enumerate name." 
            
            REVISION     "201003220000Z"
            DESCRIPTION  "V3.08, corrected test errors."
  	    
	     	REVISION     "201001260000Z"        
            DESCRIPTION  "V3.06, added trap notification and corrected compile errors."
                
            REVISION     "200907030000Z"        
            DESCRIPTION  "V3.05, added value range of hwIpSpcAttributeVoiceCode to support G.722 and G.726 codec."
                                  
			::=	{ huaweiUtility	15 }


		hwSpcMibObjects	OBJECT IDENTIFIER ::= {	hwSPC 1	}

		hwSpcMngtTable OBJECT-TYPE
			SYNTAX	   SEQUENCE OF HwSpcMngtEntry
			MAX-ACCESS not-accessible
			STATUS current
			DESCRIPTION	
			    "You can add, delete, modify or query SPC using hwSpcMngtTable.
			    The index of this table is hwSpcNo.
			    "
			::=	{ hwSpcMibObjects 1	}

		hwSpcMngtEntry OBJECT-TYPE
			SYNTAX	   HwSpcMngtEntry
			MAX-ACCESS not-accessible
			STATUS current
			DESCRIPTION	
			    "You can add, delete, modify or query SPC using hwSpcMngtTable.
			    The index of this entry is hwSpcNo.
			    "
			INDEX {	hwSpcNo	}
			::=	{ hwSpcMngtTable 1 }

		HwSpcMngtEntry ::=
			SEQUENCE {
				hwSpcNo
					Integer32,
				hwStartFrameID
					Integer32,
				hwStartSlotID
					Integer32,
				hwStartPort
					Integer32,
				hwStartBsn
					Integer32,
				hwEndFrameID
					Integer32,
				hwEndSlotID
					Integer32,
				hwEndPort
					Integer32,
				hwEndBsn
					Integer32,
				hwChannelNum
					Integer32,
				hwApptype
					INTEGER,
				hwSpctype
					INTEGER,
				hwStartPortSubType
					INTEGER,
				hwEndPortSubType
					INTEGER,
				hwPathProtect
					INTEGER,
				hwSPCName
					OCTET STRING,
				hwSpcState
					INTEGER,
				hwFailCause
					INTEGER,
				hwOprType
					INTEGER,
				hwRowStatus
					RowStatus,
				hwStartCESFrame
					Integer32,
				hwStartCESSlot
					Integer32,
				hwStartCESPort
					Integer32,
				hwStartUpPv8Frame
					Integer32,
				hwStartUpPv8Slot
					Integer32,
				hwStartUpPv8Port
					Integer32,
				hwStartDownPv8Frame
					Integer32,
				hwStartDownPv8Slot
					Integer32,
				hwStartDownPv8Port
					Integer32,
				hwStartRspFrame
					Integer32,
				hwStartRspSlot
					Integer32,
				hwStartRspPort
					Integer32,
				hwEndtCESFrame
					Integer32,
				hwEndCESSlot
					Integer32,
				hwEndCESPort
					Integer32,
				hwEndUpPv8Frame
					Integer32,
				hwEndUpPv8Slot
					Integer32,
				hwEndUpPv8Port
					Integer32,
				hwEndDownPv8Frame
					Integer32,
				hwEndDownPv8Slot
					Integer32,
				hwEndDownPv8Port
					Integer32,
				hwEndRspFrame
					Integer32,
				hwEndRspSlot
					Integer32,
				hwEndRspPort
					Integer32,
                hwIpSpcAttributeLocalIPAddr	
                    IpAddress,
	  	        hwIpSpcAttributeLocalPort	
	  	  	        Integer32,
				hwIpSpcAttributeRemoteIPAddr	
					IpAddress,
				hwIpSpcAttributeRemotePort	
					Integer32,
				hwIpSpcAttributeVoiceCode	
					INTEGER,
				hwIpSpcAttributeEce			
					INTEGER,
				hwIpSpcAttributeSce			
					INTEGER,
				hwIpSpcAttributeRtpInterval	
					INTEGER,
				hwIpSpcAttributePlc        
					INTEGER,
				hwIpSpcAttributeRfc2198    
					INTEGER,
				hwIpSpcAttributeJbMode    
					INTEGER,
				hwIpSpcAttributeWorkMode   
					INTEGER,
				hwIpSpcAttributeStreamMode 
					INTEGER,
				hwRemotePortStepNum
				    Integer32,
				hwLinksetNo
				    Integer32,
				hwInterfaceID
				    Integer32,
				hwConfGroup
				    Integer32,
				hwB1DspInfo
				    OCTET STRING,
				hwB2DspInfo
				    OCTET STRING,
				hwSpcSignalType
			      Integer32,
			  hwSpcInitialRingType
			      Integer32,
			  hwSpcCadenceRingType
			      Integer32,
			  hwSpc2833Payload
			      Integer32,
			hw2833IPSpcServiceState
			       INTEGER
			 }

		hwSpcNo	OBJECT-TYPE
			SYNTAX		Integer32(0..2099)
			MAX-ACCESS accessible-for-notify
			STATUS current
			DESCRIPTION
				"
				Index of the SPC
				Range: 0-2047 for MD products and 0-511 for MA products
				"
			::=	{ hwSpcMngtEntry 1 }

		hwStartFrameID OBJECT-TYPE
			SYNTAX Integer32 (0..97)
			MAX-ACCESS read-create
			STATUS current
			DESCRIPTION
				"
				Frame ID of SPC's start point. It must have been described in HUAWEI-DIVICE-MIB.
				"
			::=	{ hwSpcMngtEntry 2 }

		hwStartSlotID OBJECT-TYPE
			SYNTAX Integer32 (0..35)
			MAX-ACCESS read-create
			STATUS current
			DESCRIPTION
				"
				Slot ID of SPC's start point. It must have been described in HUAWEI-DIVICE-MIB.
				"
			::=	{ hwSpcMngtEntry 3 }

		hwStartPort	OBJECT-TYPE
			SYNTAX Integer32 (0..63)
			MAX-ACCESS read-create
			STATUS current
			DESCRIPTION
				"
				Port ID of SPC's start point. It must have been described in HUAWEI-DIVICE-MIB.
				"
			::=	{ hwSpcMngtEntry 4 }

		hwStartBsn OBJECT-TYPE
			SYNTAX Integer32 (0..31)
			MAX-ACCESS read-create
			STATUS current
			DESCRIPTION
				"
				Channel index of SPC's start point
				"
			::=	{ hwSpcMngtEntry 5 }

		hwEndFrameID OBJECT-TYPE
			SYNTAX Integer32 (0..97|255)
			MAX-ACCESS read-create
			STATUS current
			DESCRIPTION
				"
				Shelf ID of ANSPC's end point. It must have been described in HUAWEI-DIVICE-MIB.
				The value 255 indicates that this parameter is not used.
				"
			::=	{ hwSpcMngtEntry 6 }

		hwEndSlotID	OBJECT-TYPE
			SYNTAX Integer32 (0..35|255)
			MAX-ACCESS read-create
			STATUS current
			DESCRIPTION
				" 
				Slot ID of ANSPC's end point. It must have been described in HUAWEI-DIVICE-MIB.
				The value 255 indicates that this parameter is not used.
				"
			::=	{ hwSpcMngtEntry 7 }

		hwEndPort OBJECT-TYPE
			SYNTAX Integer32 (0..63|255)
			MAX-ACCESS read-create
			STATUS current
			DESCRIPTION
				"
				Port ID of ANSPC's end point. It must have been described in HUAWEI-DIVICE-MIB.
				The value 255 indicates that this parameter is not used.
				"
			::=	{ hwSpcMngtEntry 8 }

		hwEndBsn OBJECT-TYPE
			SYNTAX Integer32 (0..31|255)
			MAX-ACCESS read-create
			STATUS current
			DESCRIPTION
				"
				Channel index of SPC's end point.
				The value 255 indicates that this parameter is not used.
				"
			::=	{ hwSpcMngtEntry 9 }

		hwChannelNum OBJECT-TYPE
			SYNTAX Integer32 (1..32)
			MAX-ACCESS read-create
			STATUS current
			DESCRIPTION
				" 
				Total channels occupied by the SPC.
				"
			::=	{ hwSpcMngtEntry 10	}


			hwApptype OBJECT-TYPE
			SYNTAX INTEGER
				{
						normal(1),              -- normal SPC
						hotline(2),             -- hotline SPC
						mChannelTransparent(3), -- M-Channel Transparent SPC
						pbxExtention(4),       -- PBX extent SPC
						pbxBothway(5),         -- Bothway SPC
						e1DDI(6),              -- E1-DDI SPC
						t1DDI(7),              -- T1-DDI SPC
						emSignal(8)            -- EM-Signal SPC
				}
			MAX-ACCESS read-create
			STATUS current
			DESCRIPTION
				"
				Applied type of SPC.
				Options:
				1. normal(1) -normal application
				2. hotline(2) -hotline application
				3. mChannelTransparent(3) -M channel transparent
				4. pbxExtention(4) -Z interface extension
				5. pbxBothway(5) -PBX bothway application
				6. e1DDI(6) -E1 direct dial in
				7. t1DDI(7) -T1 direct dial in
				8. emSignal(8) -EM signal application
				"
			::=	{ hwSpcMngtEntry 11	}
			
			hwSpctype OBJECT-TYPE
			SYNTAX INTEGER
				{
				    anSpc(1),        -- Inner SPC
				    v5Spc(2),        -- V5 SPC
				    v5Preconnect(3), -- V5 pre-connection SPC
				    private(4),      -- Leased line SPC
				    ipspc(5),        -- IP SPC
				    confspc(6)       -- conference SPC
				}
			MAX-ACCESS read-create
			STATUS current
			DESCRIPTION
				"Configuration type of SPC.
				Options:
				1. anSpc(1) -Internal SPC
				2. v5Spc(2) -V5 SPC
				3. v5Preconnect(3) -V5 pre-connection SPC
				4. private(4) -leased line SPC
				5. ipspc(5) -IP SPC
				6. confspc(6) -conference SPC
				"
			::=	{ hwSpcMngtEntry 12	}

		hwStartPortSubType OBJECT-TYPE
			SYNTAX INTEGER
				{
				    noSubType(255), 
				    mnt(1),         
				    mlt(2)
				}
			MAX-ACCESS read-create
			STATUS current
			DESCRIPTION
				"Sub type of SPC's start port. If the SPC is used for PHS, the type must be set to mnt or mlt.
				Options:
				1. noSubType(255) -no sub type
				2. mnt(1) -mnt
				3. mlt(2) -mlt	
				"
			::=	{ hwSpcMngtEntry 13	}

		hwEndPortSubType OBJECT-TYPE
			SYNTAX INTEGER
				{
				    noSubType(255),
			        mnt(1),
				    mlt(2)
				}
			MAX-ACCESS read-create
			STATUS current
			DESCRIPTION
				"Sub type of SPC's end port.
				This node is not used on the OLT.
				Options:
				1. noSubType(255) -no sub type
				2. mnt(1) -mnt
				3. mlt(2) -mlt	
				"
			::=	{ hwSpcMngtEntry 14	}

		hwPathProtect OBJECT-TYPE
			SYNTAX INTEGER
				{
				    yes(1),
				    no(2)
				}
			MAX-ACCESS read-create
			STATUS current
			DESCRIPTION
				"Enable path protection. This leaf is not used on the OLT. 
				Options:
				1. yes(1) -YES
				2. no(2) -NO
				"
			::=	{ hwSpcMngtEntry 15	}

		hwSPCName OBJECT-TYPE
			SYNTAX OCTET STRING	(SIZE (1..31))
			MAX-ACCESS read-write
			STATUS current
			DESCRIPTION
				" 
				Name of SPC. It contains 31 characters.
				- means it is not configured.
				"
			::=	{ hwSpcMngtEntry 16	}

		hwSpcState OBJECT-TYPE
			SYNTAX INTEGER
				{
				idle(1),
				normal(2),
				error(3),
				errorChecking(4),
				occupying(5),
				checking(6),
				released(7),
				errReleasing(8),
				refreshReleasing(9),
				disconnecting(10)
				}
			MAX-ACCESS read-only
			STATUS current
			DESCRIPTION
				"SPC state.
				Options:
				1. idle(1) -idle
				2. normal(2) -normal
				3. error(3) -error
				4. errorChecking(4) -error checking
				5. occupying(5) -occupying
				6. checking(6) -checking
				7. released(7) -released
				8. errReleasing(8) -error releasing
				9. refreshReleasing(9) -refresh releasing
				10. disconnecting(10) -disconnecting
				"
			::=	{ hwSpcMngtEntry 17	}

		hwFailCause	OBJECT-TYPE
			SYNTAX INTEGER
				{
				startBusy(1),
				endBusy(2),
				startFault(3),
				endFault(4),
				startLoop(5),
				endLoop(6),
				startLock(7),
				endLock(8),
				resNotEnough(9),
				waitingTimeout(10),
				startTest(11),
				endTest(12),
				noAlarm(13),
				noTS(14),
				noLicense(15),
				linksetFault(16),
				portUnactive(17)
				}
			MAX-ACCESS read-only
			STATUS current
			DESCRIPTION
				"Fault reason of SPC.
				Options:
				1. startBusy(1) -the start port is busy
				2. endBusy(2) - the end port is busy
				3. startFault(3) - the start	port is	fault
				4. endFault(4) - the end port is fault
				5. startLoop(5) - the start port is looped
				6. endLoop(6) - the end port is looped                                 
				7. startLock(7) - the start	port is	locked
				8. endLock(8) - the end port is locked
				9. resNotEnough(9) -the system resource is not enough
				10. waitingTimeout(10) -the waiting timer times out
			        11. startTest(11) -the start port is testing
		                12. endTest(12) -the end port is testing
				13. noAlarm(13) -no alarm
				14. noTS(14) -no TS
				15. noLicense(15) -no license
				16. linksetFault(16) -link set fault
				17. portUnactive(17) -port unactive
                "
			::=	{ hwSpcMngtEntry 18	}

		hwOprType OBJECT-TYPE
			SYNTAX INTEGER
				{
				noOperation(1), -- No operation
				connect(2),     -- Connect
				disconnect(3)   -- Disconnect
				}
			MAX-ACCESS read-write
			STATUS current
			DESCRIPTION
				"Operate type of SPC. It can be set to disconnect or connect.
				Options:
				1. noOperation(1) -no operation
				2. connect(2) -connect
				3. disconnect(3) -disconnect
				"
			::=	{ hwSpcMngtEntry 19	}

		hwRowStatus OBJECT-TYPE
			SYNTAX RowStatus
			MAX-ACCESS read-write
			STATUS current
			DESCRIPTION
				" 
				Row status. It supports only CreateAndGo(4) and Destroy(6).
                "
			::=	{ hwSpcMngtEntry 20 }
			
		hwStartCESFrame	OBJECT-TYPE
			SYNTAX Integer32 (0..255)
			MAX-ACCESS read-only
			STATUS current
			DESCRIPTION
				"Start CES shelf.
				If the value is 255, it indicates that the SPC does not use this path.
				This leaf is not used on the OLT. 
				"
			::=	{ hwSpcMngtEntry 21	}

		hwStartCESSlot OBJECT-TYPE
			SYNTAX Integer32 (0..255)
			MAX-ACCESS read-only
			STATUS current
			DESCRIPTION
				"CES slot.
				If the value is 255, it indicates that the SPC does not use this path.
				This leaf is not used on the OLT. 
				"
		        ::=	{ hwSpcMngtEntry 22	}

		hwStartCESPort OBJECT-TYPE
			SYNTAX Integer32 (0..255)
			MAX-ACCESS read-only
			STATUS current
			DESCRIPTION
				"Start CES port.
				If the value is 255, it indicates that the SPC does not use this path.
				This leaf is not used on the OLT. 
				"
			::=	{ hwSpcMngtEntry 23	}

		hwStartUpPv8Frame OBJECT-TYPE
			SYNTAX Integer32 (0..255)
			MAX-ACCESS read-only
			STATUS current
			DESCRIPTION
				"Start upstream PV8 shelf.
				If the value is 255, it indicates that the SPC does not use this path.
				This leaf is not used on the OLT. 
				"
			::=	{ hwSpcMngtEntry 24	}

		hwStartUpPv8Slot OBJECT-TYPE
			SYNTAX Integer32 (0..255)
			MAX-ACCESS read-only
			STATUS current
			DESCRIPTION
				"Start upstream PV8 slot.
				If the value is 255, it indicates that the SPC does not use this path.
				This leaf is not used on the OLT. 
				"
			::=	{ hwSpcMngtEntry 25	}

		hwStartUpPv8Port OBJECT-TYPE
			SYNTAX Integer32 (0..255)
			MAX-ACCESS read-only
			STATUS current
			DESCRIPTION
				"Start upstream PV8 port.
				If the value is 255, it indicates that the SPC does not use this path.
				This leaf is not used on the OLT. 
				"
			::=	{ hwSpcMngtEntry 26	}

		hwStartDownPv8Frame	OBJECT-TYPE
			SYNTAX Integer32 (0..255)
			MAX-ACCESS read-only
			STATUS current
			DESCRIPTION
				"Start downstream PV8 shelf.
				If the value is 255, it indicates that the SPC does not use this path.
				This leaf is not used on the OLT. 
				"
			::=	{ hwSpcMngtEntry 27	}

		hwStartDownPv8Slot OBJECT-TYPE
			SYNTAX Integer32 (0..255)
			MAX-ACCESS read-only
			STATUS current
			DESCRIPTION
				"Start downstream PV8 slot.
				If the value is 255, it indicates that the SPC does not use this path.
				This leaf is not used on the OLT. 
				"
			::=	{ hwSpcMngtEntry 28	}

		hwStartDownPv8Port OBJECT-TYPE
			SYNTAX Integer32 (0..255)
			MAX-ACCESS read-only
			STATUS current
			DESCRIPTION
				"Start downstream PV8 port.
				If the value is 255, it indicates that the SPC does not use this path.
				This leaf is not used on the OLT. 
				"
			::=	{ hwSpcMngtEntry 29	}

		hwStartRspFrame	OBJECT-TYPE
			SYNTAX Integer32 (0..255)
			MAX-ACCESS read-only
			STATUS current
			DESCRIPTION
				"Start downstream RSP shelf.
				If the value is 255, it indicates that the SPC does not use this path.
				This leaf is not used on the OLT. 
				"
			::=	{ hwSpcMngtEntry 30	}

		hwStartRspSlot OBJECT-TYPE
			SYNTAX Integer32 (0..255)
			MAX-ACCESS read-only
			STATUS current
			DESCRIPTION
				"Start downstream RSP slot.
				If the value is 255, it indicates that the SPC does not use this path.
				This leaf is not used on the OLT. 
				"
			::=	{ hwSpcMngtEntry 31	}

		hwStartRspPort OBJECT-TYPE
			SYNTAX Integer32 (0..255)
			MAX-ACCESS read-only
			STATUS current
			DESCRIPTION
				"Start downstream RSP port.
				If the value is 255, it indicates that the SPC does not use this path.
				This leaf is not used on the OLT. 
				"
			::=	{ hwSpcMngtEntry 32	}

		hwEndtCESFrame OBJECT-TYPE
			SYNTAX Integer32 (0..255)
			MAX-ACCESS read-only
			STATUS current
			DESCRIPTION
				"End downstream CES shelf.
				If the value is 255, it indicates that the SPC does not use this path.
				This leaf is not used on the OLT. 
				"
			::=	{ hwSpcMngtEntry 33	}

		hwEndCESSlot OBJECT-TYPE
			SYNTAX Integer32 (0..255)
			MAX-ACCESS read-only
			STATUS current
			DESCRIPTION
				"End downstream CES slot.
				If the value is 255, it indicates that the SPC does not use this path.
				This leaf is not used on the OLT. 
				"
			::=	{ hwSpcMngtEntry 34	}

		hwEndCESPort OBJECT-TYPE
			SYNTAX Integer32 (0..255)
			MAX-ACCESS read-only
			STATUS current
			DESCRIPTION
				"End CES port.
				If the value is 255, it indicates that the SPC does not use this path.
				This leaf is not used on the OLT. 
				"
			::=	{ hwSpcMngtEntry 35	}

		hwEndUpPv8Frame	OBJECT-TYPE
			SYNTAX Integer32 (0..255)
			MAX-ACCESS read-only
			STATUS current
			DESCRIPTION
				"End upstream PV8 shelf.
				If the value is 255, it indicates that the SPC does not use this path.
				This leaf is not used on the OLT. 
				"
			::=	{ hwSpcMngtEntry 36	}

		hwEndUpPv8Slot OBJECT-TYPE
			SYNTAX Integer32 (0..255)
			MAX-ACCESS read-only
			STATUS current
			DESCRIPTION
				"End upstream PV8 slot.
				If the value is 255, it indicates that the SPC does not use this path.
				This leaf is not used on the OLT. 
				"
			::=	{ hwSpcMngtEntry 37	}

		hwEndUpPv8Port OBJECT-TYPE
			SYNTAX Integer32 (0..255)
			MAX-ACCESS read-only
			STATUS current
			DESCRIPTION
				"End upstream PV8 port.
				If the value is 255, it indicates that the SPC does not use this path.
				This leaf is not used on the OLT. 
				"
			::=	{ hwSpcMngtEntry 38	}

		hwEndDownPv8Frame OBJECT-TYPE
			SYNTAX Integer32 (0..255)
			MAX-ACCESS read-only
			STATUS current
			DESCRIPTION
				"End downstream PV8 shelf.
				If the value is 255, it indicates that the SPC does not use this path.
				This leaf is not used on the OLT. 
				"
			::=	{ hwSpcMngtEntry 39	}

		hwEndDownPv8Slot OBJECT-TYPE
			SYNTAX Integer32 (0..255)
			MAX-ACCESS read-only
			STATUS current
			DESCRIPTION
				"End downstream PV8 slot.
				If the value is 255, it indicates that the SPC does not use this path.
				This leaf is not used on the OLT. 
				"
			::=	{ hwSpcMngtEntry 40	}

		hwEndDownPv8Port OBJECT-TYPE
			SYNTAX Integer32 (0..255)
			MAX-ACCESS read-only
			STATUS current
			DESCRIPTION
				"End downstream PV8 port.
				If the value is 255, it indicates that the SPC does not use this path.
				This leaf is not used on the OLT. 
				"
			::=	{ hwSpcMngtEntry 41	}

		hwEndRspFrame OBJECT-TYPE
			SYNTAX Integer32 (0..255)
			MAX-ACCESS read-only
			STATUS current
			DESCRIPTION
				"End RSP shelf.
				If the value is 255, it indicates that the SPC does not use this path.
				This leaf is not used on the OLT. 
				"
			::=	{ hwSpcMngtEntry 42	}

		hwEndRspSlot OBJECT-TYPE
			SYNTAX Integer32 (0..255)
			MAX-ACCESS read-only
			STATUS current
			DESCRIPTION
				"End RSP slot.
				If the value is 255, it indicates that the SPC does not use this path.
				This leaf is not used on the OLT. 
				"
			::=	{ hwSpcMngtEntry 43	}

		hwEndRspPort OBJECT-TYPE
			SYNTAX Integer32 (0..255)
			MAX-ACCESS read-only
			STATUS current
			DESCRIPTION
				"End RSP port.
				If the value is 255, it indicates that the SPC does not use this path.
				This leaf is not used on the OLT. 
				"
			::=	{ hwSpcMngtEntry 44	}

		hwIpSpcAttributeLocalIPAddr	OBJECT-TYPE
			SYNTAX		IpAddress
			MAX-ACCESS	read-write
			STATUS	current
			DESCRIPTION
				"Local IP address of the SPC. If the SPC's type is IPSPC, the local IP address must be configured.
				"
			::=	{ hwSpcMngtEntry	45 }

		hwIpSpcAttributeLocalPort OBJECT-TYPE
			SYNTAX		Integer32(0..65535)
			MAX-ACCESS	read-write
			STATUS		current
			DESCRIPTION
			"Local UDP port of the SPC. If the SPC's type is IPSPC, the local UDP port must be configured.
				"
			::=	{ hwSpcMngtEntry	46 }

		hwIpSpcAttributeRemoteIPAddr OBJECT-TYPE
			SYNTAX		IpAddress
			MAX-ACCESS	read-write
			STATUS		current
			DESCRIPTION
				"Remote IP address of the SPC. If the SPC's type is IPSPC, the remote IP address mustd be configured.
				"
			::=	{ hwSpcMngtEntry	47 }

		hwIpSpcAttributeRemotePort OBJECT-TYPE
			SYNTAX		Integer32(0..65535)
			MAX-ACCESS	read-write
			STATUS		current
			DESCRIPTION
				"Remote UDP port of the SPC. If the SPC's type is IPSPC, the remote UDP port must be configured.
				"
			::=	{ hwSpcMngtEntry	48 }

		hwIpSpcAttributeVoiceCode OBJECT-TYPE
			SYNTAX		INTEGER
			{
			    acG711Malaw(1),  -- G.711A
                acG711Mulaw(2),  -- G.711U
                acG723Low(3),    -- G.723low
                acG723High(4),   -- G.723high
                acG729(5),       -- G.729
                clearMode(6),    -- clear mode
                g72616k(7),     -- G.726_16K
                g72624k(8),     -- G.726_24K
                g72632k(9),     -- G.726_32K
                g72640k(10),    -- G.726_40K
                g722(11),        -- G.722
                invalid(-1)	-- invalid value
			}
			MAX-ACCESS	read-write
			STATUS		current
			DESCRIPTION
				"Voice codec type of the SPC.
				Options:
				1. acG711Malaw(1) -G.711A
				2. acG711Mulaw(2) -G.711U    
				3. acG723Low(3) -G.723low  
				4. acG723High(4) -G.723high 
				5. acG729(5) -G.729     
				6. clearMode(6) -clear mode
				7. g72616k(7) -G.726_16K   
				8. g72624k(8) -G.726_24K   
				9. g72632k(9) -G.726_32K   
				10. g72640k(10) -G.726_40K   
				11. g722(11) -G.722     
				12. invalid(-1) -invalid value
				"
			::=	{ hwSpcMngtEntry	49 }

		hwIpSpcAttributeEce	OBJECT-TYPE
			SYNTAX		INTEGER
			{
			    disable(1),
			    enable(2),
			    invalid(-1)
			}
			MAX-ACCESS	read-write
			STATUS		current
			DESCRIPTION
				"
				The switch of EC.
				Options:
				1. disable(1) -disable EC
				2. enable(2) -enable EC
				3. invalid(-1) -invalid value
				"
			::=	{ hwSpcMngtEntry	50 }

		hwIpSpcAttributeSce	OBJECT-TYPE
			SYNTAX		INTEGER
			{
			    disable(1),
			    enable(2),
			    invalid(-1)
			}
			MAX-ACCESS	read-write
			STATUS		current
			DESCRIPTION
				"
				The switch of SC.
				Options:
				1. disable(1) -disable SC
				2. enable(2) -enable SC
				3. invalid(-1) -invalid value
				"
			::=	{ hwSpcMngtEntry	51 }

		hwIpSpcAttributeRtpInterval	OBJECT-TYPE
			SYNTAX		INTEGER
			{ 
			    five(1),
			    ten(2),
			    twenty(3),
			    thirty(4),
			    invalid(255)
			}
			MAX-ACCESS	read-write
			STATUS		current
			DESCRIPTION
				"RTP sampling time.
				Options:
				1. five(1) -5 ms
				2. ten(2) -10 ms
				3. twenty(3) -20 ms
				4. thirty(4) -30 ms
				5. invalid(255) -invalid value
				Unit: millisecond				
				"
			::=	{ hwSpcMngtEntry	52}
					
		hwIpSpcAttributePlc	OBJECT-TYPE
			SYNTAX		INTEGER{ enable(1),disable(2),invalid(255)}
			MAX-ACCESS	read-write
			STATUS		current
			DESCRIPTION
				"The switch of PLC.
				Options:
				1. enable(1) -enable PLC
				2. disable(2) -disable PLC
				3. invalid(255) -invalid value
				"
			::=	{ hwSpcMngtEntry	53}
					
		hwIpSpcAttributeRfc2198	OBJECT-TYPE
			SYNTAX		INTEGER{ enable(1),disable(2),invalid(255)}
			MAX-ACCESS	read-write
			STATUS		current
			DESCRIPTION
				"
				The switch of 2198.
				Options:
				1. enable(1) -enable RFC2198 redundancy
				2. disable(2) -disable RFC2198 redundancy
				3. invalid(255) -invalid value
				"
			::=	{ hwSpcMngtEntry	54}
					
		hwIpSpcAttributeJbMode	OBJECT-TYPE
			SYNTAX		INTEGER{ adapt(1),fixed(2),invalid(255)}
			MAX-ACCESS	read-write
			STATUS		current
			DESCRIPTION
				"Jitterbuffer mode.
				Options:
				1. adapt(1) -adapt
				2. fixed(2) -fixed
				3. invalid(255) -invalid value
				"
			::=	{ hwSpcMngtEntry	55}
					
		hwIpSpcAttributeWorkMode	OBJECT-TYPE
			SYNTAX		INTEGER{ voice(1),fax(2),modem(3),invalid(255) }
			MAX-ACCESS	read-write
			STATUS		current
			DESCRIPTION
				"
				DSP work mode.
				Options:
				1. voice(1) -voice
				2. fax(2) -fax
				3. modem(3) -modem
				4. invalid(255) -invalid value
				"
			::=	{ hwSpcMngtEntry	56}
					
		hwIpSpcAttributeStreamMode	OBJECT-TYPE
			SYNTAX		INTEGER{ sendReceive(1),sendOnly(2),receiveOnly(3),invalid(255) }
			MAX-ACCESS	read-write
			STATUS		current
			DESCRIPTION
				"
				Connect mode.
				Options:
				1. sendReceive(1) -send and receive
				2. sendOnly(2) -send only
				3. receiveOnly(3) -receive only
				4. invalid(255) -invalid value
				"
			::=	{ hwSpcMngtEntry	57}
					
		hwRemotePortStepNum OBJECT-TYPE
			SYNTAX Integer32 (1..65534|65535)
			MAX-ACCESS read-create
			STATUS current
			DESCRIPTION
			  "
			  The remote-port step. If the value is 65535, the ANSPC does not use the remote port step number attribute.
			  "
			::=	{ hwSpcMngtEntry 58	}
			        
        hwLinksetNo OBJECT-TYPE
			SYNTAX Integer32 (-1|0..31)
			MAX-ACCESS read-create
			STATUS current
			DESCRIPTION
			  " 
			  IUA link set number.
			  In the case of the U interface transparent, this parameter must be configured.
		      If the value is -1, it indicates that the SPC does not use the IUA link set number.
			  "
			::=	{ hwSpcMngtEntry 59	}
			        
        hwInterfaceID OBJECT-TYPE
			SYNTAX Integer32 (-1|0..65535)
			MAX-ACCESS read-create
			STATUS current
			DESCRIPTION
			  " 
			  IUA interface ID.
			  In the case of the U interface transparent, this parameter must be configured.
		      If the value is -1, it indicates that the SPC does not use the IUA interface ID.
			  "
			::=	{ hwSpcMngtEntry 60	}	
			                      	
        hwConfGroup OBJECT-TYPE
            SYNTAX Integer32 (0..15)
			MAX-ACCESS read-create
			STATUS current
			DESCRIPTION
			  "
			  Conference Group ID.
			  This leaf is not used on the OLT. 
			  "
            ::=     { hwSpcMngtEntry 61	}												
                           
        hwB1DspInfo OBJECT-TYPE
			SYNTAX OCTET STRING	(SIZE (9..32))
			MAX-ACCESS read-only
			STATUS current
			DESCRIPTION
				"
				Information of B1 DSP in conference service or BRA IP service.
				It contains 32 characters and it is in the format of FrameID/SlotID/CardID/ChipID/CHNID.
				This leaf is not used on the OLT. 
				"
			::=	{ hwSpcMngtEntry 62	}												
                        
		hwB2DspInfo OBJECT-TYPE
			SYNTAX OCTET STRING	(SIZE (9..32))
			MAX-ACCESS read-only
			STATUS current
			DESCRIPTION
				"
				Information of B2 DSP in BRA ip service.
				It contains 32 characters and it is in the format of FrameID/SlotID/CardID/ChipID/CHNID
				This leaf is not used on OLT. 
                "
			::=	{ hwSpcMngtEntry 63	}
			
		hwSpcSignalType	OBJECT-TYPE
			SYNTAX Integer32 (-1|1..2)
			MAX-ACCESS	read-write
			STATUS		current
			DESCRIPTION
				"
				Signal type of IP SPC.
				Options:
				1. 1 - normal
				2. 2 - 2833 
				3. -1 - invalid value 
				For the MA5600T, the default value of the IPSPC is normal, and the ANSPC does not support this node. 
				This leaf is only used on the UA5000 and MA5600T.
				"
			::=	{ hwSpcMngtEntry	64}
			
		hwSpcInitialRingType OBJECT-TYPE
			SYNTAX Integer32 (-1|1..28)
			MAX-ACCESS read-write
			STATUS current
			DESCRIPTION
				"IP SPC initial ring type.
         Enumeration type: 
         1-Null, 2-Normal ring (FSK) 1:4, 3-Special ring (FSK) 1:2, 4-Special ring (FSK) 0.4:0.2:0.4:4, 5-Special ring (FSK) 1.2:2, 6-HK ring (FSK) 1:3, 7-HK CNTRX (FSK) 0.4:0.2:0.4:0.2:0.4:3.0,
         8-HK DN-A (FSK) 0.4:0.2:0.4:3.0, 9-HK DN-B (FSK) 1.2:3, 10-CNTRX-IN (FSK) 0.4:0.2:0.4:0.2:0.4:2.6, 11-Egypt long-distance ring (FSK) 2:1, 12-user defined FSK ring mode 0,
         13-user defined FSK ring mode 1, 14-user defined FSK ring mode 2, 15-user defined FSK ring mode 3, 16-user defined FSK ring mode 4, 17-user defined FSK ring mode 5,
         18-user defined FSK ring mode 6, 19-user defined FSK ring mode 7, 20-user defined FSK ring mode 8, 21-user defined FSK ring mode 9, 22-user defined FSK ring mode 10,
         23-user defined FSK ring mode 11, 24-user defined FSK ring mode 12, 25-user defined FSK ring mode 13, 26-user defined FSK ring mode 14, 27-user defined FSK ring mode 15, 
         28-ETSI RP-AS (FSK) 0.25, -1-invalid value
         For the MA5600T, the default value of the IPSPC is 2, and the ANSPC does not support this node.
				This leaf is only used on the UA5000 and MA5600T.
				"
			::=	{ hwSpcMngtEntry 65	}
			
		hwSpcCadenceRingType OBJECT-TYPE
			SYNTAX Integer32 (-1|1..31)
			MAX-ACCESS read-write
			STATUS current
			DESCRIPTION
				"IP SPC cadence ring type.
         Enumerated types: 
         1-Null, 2-Normal ring 1:4, 3-Special ring 1:2, 4-Special ring 0.4:0.2:0.4:4, 5-Long ring, 6-Special ring 1.2:2, 7-HK ring 1:3, 8-HK CNTRX 0.4:0.2:0.4:0.2:0.4:3.0,
         9-HK DN-A 0.4:0.2:0.4:3.0, 10-HK ACB 0.4:0.2, 11-HK reminder ring (one tone every 0.4 second; one tone), 12-HK DN-B 1.2:3, 13-CNTRX-IN 0.4:0.2:0.4:0.2:0.4:2.6,
         14-Egypt long-distance ring 2:1, 15-user defined ring mode 0, 16-user defined ring mode 1, 17-user defined ring mode 2, 18-user defined ring mode 3,
         19-user defined ring mode 4, 20-user defined ring mode 5, 21-user defined ring mode 6, 22-user defined ring mode 7, 23-user defined ring mode 8, 24-user defined ring mode 9,
         25-user defined ring mode 10, 26-user defined ring mode 11, 27-user defined ring mode 12, 28-user defined ring mode 13, 29-user defined ring mode 14,
         30-user defined ring mode 15, 31-ETSI RP-AS 0.25, -1-invalid value 
         For the MA5600T, the default value of the IPSPC is 2, and the ANSPC does not support this node.
				This leaf is only used on the UA5000 and MA5600T.
				"
			::=	{ hwSpcMngtEntry 66	}
			
		hwSpc2833Payload OBJECT-TYPE
			SYNTAX Integer32 (96..127)
			MAX-ACCESS read-write
			STATUS current
			DESCRIPTION
				"IP SPC 2833 payload type.
				This leaf is only used on the UA5000.
				"
			::=	{ hwSpcMngtEntry 67	} 
			
       hw2833IPSpcServiceState	OBJECT-TYPE
			SYNTAX  INTEGER  
			{
			   fault(1),
			   idle(2),
			   offhook(3),
			   ring(4),
			   invalid(-1)
			}
			MAX-ACCESS	read-only
			STATUS		current
			DESCRIPTION
				"
				Service State of IP SPC.
				Options:
				1. fault(1) - fault
				2. idle(2) - idle    
				3. offhook(3) - offhook  
				4. ring(4)  - ring    
				5. invalid(-1) - invalid
				Default: invalid(-1)  
				This leaf is only used on the MA5600T.
				"
			::=	{ hwSpcMngtEntry	68}
	
		hwNextAllocSpcNo	OBJECT-TYPE
			SYNTAX		Integer32(0..2099)
			MAX-ACCESS	read-only
			STATUS		current
			DESCRIPTION
				"
				Next valid allocation of SPC index
				Range: 0-2047 for MD products and 0-511 for MA products.
				"
			::=	{ hwSpcMibObjects 3	}

		hwSpcProtectGroupTable OBJECT-TYPE
			SYNTAX	   SEQUENCE OF HwSpcProtectGroupEntry
			MAX-ACCESS not-accessible
			STATUS current
			DESCRIPTION	
			    "You can add, delete, modify or query SPC protect group using hwSpcProtectGroupTable.
			    The index of this table is hwSpcProtectGroupID.
			    "
			::=	{ hwSpcMibObjects 4	}

		hwSpcProtectGroupEntry OBJECT-TYPE
			SYNTAX	   HwSpcProtectGroupEntry
			MAX-ACCESS not-accessible
			STATUS current
			DESCRIPTION	
			    "You can add, delete, modify or query SPC protect group using hwSpcProtectGroupTable.
			    The index of this entry is hwSpcProtectGroupID.
			    "
			INDEX {	hwSpcProtectGroupID	}
			::=	{ hwSpcProtectGroupTable 1 }
			
		HwSpcProtectGroupEntry ::=
			SEQUENCE {
				hwSpcProtectGroupID
					Integer32,
				hwSpcMainPortFrameID
				  Integer32,
				hwSpcMainPortSlotID
				  Integer32,
				hwSpcMainPortPortID
				  Integer32,
				hwProtectGroupRowStatus
					RowStatus
			 }
			 
		hwSpcProtectGroupID	OBJECT-TYPE
			SYNTAX		Integer32(0..2)
			MAX-ACCESS not-accessible
			STATUS current
			DESCRIPTION
				"
				Index of the SPC E1 protect group.
				Range: 0-2 for UA products.
				"
			::=	{ hwSpcProtectGroupEntry 1 }

		hwSpcMainPortFrameID OBJECT-TYPE
			SYNTAX Integer32 (0..97)
			MAX-ACCESS read-write
			STATUS current
			DESCRIPTION
				"
				Frame ID of SPC E1 protect service link. It must have been described in HUAWEI-DIVICE-MIB.
				"
			::=	{ hwSpcProtectGroupEntry 2 }
			
		hwSpcMainPortSlotID OBJECT-TYPE
			SYNTAX Integer32 (0..35)
			MAX-ACCESS read-write
			STATUS current
			DESCRIPTION
				"
				Slot ID of SPC E1 protect service link. It must have been described in HUAWEI-DIVICE-MIB.
				"
			::=	{ hwSpcProtectGroupEntry 3 }
			
		hwSpcMainPortPortID OBJECT-TYPE
			SYNTAX Integer32 (0..63)
			MAX-ACCESS read-write
			STATUS current
			DESCRIPTION
				"
				Port ID of SPC E1 protect service link. It must have been described in HUAWEI-DIVICE-MIB.
				"
			::=	{ hwSpcProtectGroupEntry 4 }
					
		  hwProtectGroupRowStatus OBJECT-TYPE
			SYNTAX RowStatus
			MAX-ACCESS read-write
			STATUS current
			DESCRIPTION
				" 
				Row status. It supports only CreateAndGo(4) and Destroy(6).
        "
			::=	{ hwSpcProtectGroupEntry 5 }

		hwSpcProtectTable OBJECT-TYPE
			SYNTAX	   SEQUENCE OF HwSpcProtectEntry
			MAX-ACCESS not-accessible
			STATUS current
			DESCRIPTION	
			    "You can add, delete, modify or query SPC protect link using hwSpcProtectTable.
			    The index of this table is hwSpcProtectID.
			    "
			::=	{ hwSpcMibObjects 5	}

		hwSpcProtectEntry OBJECT-TYPE
			SYNTAX	   HwSpcProtectEntry
			MAX-ACCESS not-accessible
			STATUS current
			DESCRIPTION	
			    "You can add, delete, modify or query SPC protect link using hwSpcProtectTable.
			    The index of this entry is hwSpcProtectID.
			    "
			INDEX {	hwSpcProtectID	}
			::=	{ hwSpcProtectTable 1 }
			
		HwSpcProtectEntry ::=
			SEQUENCE {
				hwSpcProtectID
					Integer32,
				hwSpcProtectGroupId
				  Integer32,
				hwSpcProtectPortFrameID
				  Integer32,
				hwSpcProtectPortSlotID
				  Integer32,
				hwSpcProtectPortPortID
				  Integer32,
				hwSpcProtectPriority
				  Integer32,
				hwSpcProtectUsedFlag
				  Integer32,
				hwProtectLinkRowStatus
					RowStatus
			 }
			 
		hwSpcProtectID	OBJECT-TYPE
			SYNTAX		Integer32(0..8)
			MAX-ACCESS not-accessible
			STATUS current
			DESCRIPTION
				"
				Index of the SPC E1 protect link.
				Range: 0-8 for UA products.
				"
			::=	{ hwSpcProtectEntry 1 }
			
		hwSpcProtectGroupId	OBJECT-TYPE
			SYNTAX		Integer32(0..2)
			MAX-ACCESS not-accessible
			STATUS current
			DESCRIPTION
				"
				Index of the SPC E1 protect group.
				"
			::=	{ hwSpcProtectEntry 2 }
			
		hwSpcProtectPortFrameID OBJECT-TYPE
			SYNTAX Integer32 (0..97)
			MAX-ACCESS read-write
			STATUS current
			DESCRIPTION
				"
				Frame ID of SPC E1 protect link. It must have been described in HUAWEI-DIVICE-MIB.
				"
			::=	{ hwSpcProtectEntry 3 }
			
		hwSpcProtectPortSlotID OBJECT-TYPE
			SYNTAX Integer32 (0..35)
			MAX-ACCESS read-write
			STATUS current
			DESCRIPTION
				"
				Slot ID of SPC E1 protect link. It must have been described in HUAWEI-DIVICE-MIB.
				"
			::=	{ hwSpcProtectEntry 4 }
			
		hwSpcProtectPortPortID OBJECT-TYPE
			SYNTAX Integer32 (0..63)
			MAX-ACCESS read-write
			STATUS current
			DESCRIPTION
				"
				Port ID of SPC E1 protect link. It must have been described in HUAWEI-DIVICE-MIB.
				"
			::=	{ hwSpcProtectEntry 5 }
			
		hwSpcProtectPriority OBJECT-TYPE
			SYNTAX Integer32 (1..3)
			MAX-ACCESS read-write
			STATUS current
			DESCRIPTION
				"
				Priority of SPC E1 protect link. 1: cat1(1), 2: cat1(2), 3: cat1(3).
				"
			::=	{ hwSpcProtectEntry 6 }
			
		hwSpcProtectUsedFlag	OBJECT-TYPE
			SYNTAX		Integer32(1..2)
			MAX-ACCESS read-only
			STATUS current
			DESCRIPTION
				"
				State of the SPC E1 protect link.
				"
			::=	{ hwSpcProtectEntry 7 }
			
			hwProtectLinkRowStatus OBJECT-TYPE
			SYNTAX RowStatus
			MAX-ACCESS read-write
			STATUS current
			DESCRIPTION
				" 
				Row status. It supports only CreateAndGo(4) and Destroy(6).
        "
			::=	{ hwSpcProtectEntry 8 }
			
    --start: add for scs
    hwSubRateSwitchTable OBJECT-TYPE
			SYNTAX	   SEQUENCE OF HwSubRateSwitchEntry
			MAX-ACCESS not-accessible
			STATUS current
			DESCRIPTION	
			    "You can add, delete, modify or query sub-rate switch using hwSubRateSwitchTable.
			    The index of this table is hwSubRateSwitchID.
			    "
			::=	{ hwSpcMibObjects 6	}

		hwSubRateSwitchEntry OBJECT-TYPE
			SYNTAX	   HwSubRateSwitchEntry
			MAX-ACCESS not-accessible
			STATUS current
			DESCRIPTION	
			    "You can add, delete, modify or query sub-rate switch using hwSubRateSwitchTable.
			    The index of this entry is hwSubRateSwitchID.
			    "
			INDEX {	hwSubRateSwitchID	}
			::=	{ hwSubRateSwitchTable 1 }

		HwSubRateSwitchEntry ::=
			SEQUENCE {
				hwSubRateSwitchID
					Integer32,
				hwSubRateSwitchStartFrameID
					Integer32,
				hwSubRateSwitchStartSlotID
					Integer32,
				hwSubRateSwitchStartPortID
					Integer32,
				hwSubRateSwitchStartChannelID
					Integer32,
				hwSubRateSwitchStartSubChannelID
					Integer32,
				hwSubRateSwitchEndFrameID
					Integer32,
				hwSubRateSwitchEndSlotID
					Integer32,
				hwSubRateSwitchEndPortID
					Integer32,
				hwSubRateSwitchEndChannelID
					Integer32,
				hwSubRateSwitchEndSubChannelID
					Integer32,
				hwSubRateSwitchState
					INTEGER,
				hwSubRateSwitchRowStatus
					RowStatus
				 }

		hwSubRateSwitchID	OBJECT-TYPE
			SYNTAX		Integer32(0..1023)
			MAX-ACCESS not-accessible
			STATUS current
			DESCRIPTION
				"
				Index of the sub-rate switch
				"
			::=	{ hwSubRateSwitchEntry 1 }

		hwSubRateSwitchStartFrameID OBJECT-TYPE
			SYNTAX Integer32 (0..97)
			MAX-ACCESS read-create
			STATUS current
			DESCRIPTION
				"
				Frame ID of sub-rate switch start point. It must have been described in HUAWEI-DIVICE-MIB.
				"
			::=	{ hwSubRateSwitchEntry 2 }

		hwSubRateSwitchStartSlotID OBJECT-TYPE
			SYNTAX Integer32 (0..35)    
			MAX-ACCESS read-create
			STATUS current
			DESCRIPTION
				"
				Slot ID of sub-rate switch start point. It must have been described in HUAWEI-DIVICE-MIB.
				"
			::=	{ hwSubRateSwitchEntry 3 }

		hwSubRateSwitchStartPortID	OBJECT-TYPE
			SYNTAX Integer32 (0..31)
			MAX-ACCESS read-create
			STATUS current
			DESCRIPTION
				"
				Port ID of sub-rate switch start point. It must have been described in HUAWEI-DIVICE-MIB.
				"
			::=	{ hwSubRateSwitchEntry 4 }

		hwSubRateSwitchStartChannelID OBJECT-TYPE
			SYNTAX Integer32 (0..31)
			MAX-ACCESS read-create
			STATUS current
			DESCRIPTION
				"
				Channel index of sub-rate switch start point
				"
			::=	{ hwSubRateSwitchEntry 5 }
			
    hwSubRateSwitchStartSubChannelID OBJECT-TYPE
			SYNTAX Integer32 (0..19)
			MAX-ACCESS read-create
			STATUS current
			DESCRIPTION
				"
				sub-rate channel index of sub-rate switch start point
				"
			::=	{ hwSubRateSwitchEntry 6 }
			
		hwSubRateSwitchEndFrameID OBJECT-TYPE
			SYNTAX Integer32 (0..97)
			MAX-ACCESS read-create
			STATUS current
			DESCRIPTION
				"
				Frame ID of sub-rate switch end point. It must have been described in HUAWEI-DIVICE-MIB.
				"
			::=	{ hwSubRateSwitchEntry 7 }

		hwSubRateSwitchEndSlotID	OBJECT-TYPE
			SYNTAX Integer32 (0..35)
			MAX-ACCESS read-create
			STATUS current
			DESCRIPTION
				" 
				Slot ID of sub-rate switch end point. It must have been described in HUAWEI-DIVICE-MIB.
				"
			::=	{ hwSubRateSwitchEntry 8 }

		hwSubRateSwitchEndPortID OBJECT-TYPE
			SYNTAX Integer32 (0..31)
			MAX-ACCESS read-create
			STATUS current
			DESCRIPTION
				"
				Port ID of sub-rate switch end point. It must have been described in HUAWEI-DIVICE-MIB.
				"
			::=	{ hwSubRateSwitchEntry 9 }

		hwSubRateSwitchEndChannelID OBJECT-TYPE
			SYNTAX Integer32 (0..31)
			MAX-ACCESS read-create
			STATUS current
			DESCRIPTION
				"
				Channel index of sub-rate switch end point.
				"
			::=	{ hwSubRateSwitchEntry 10 }

		hwSubRateSwitchEndSubChannelID OBJECT-TYPE
			SYNTAX Integer32 (0..19)
			MAX-ACCESS read-create
			STATUS current
			DESCRIPTION
				" 
				sub-rate channel index of sub-rate switch end point.
				"
			::=	{ hwSubRateSwitchEntry 11	}
			
		hwSubRateSwitchState OBJECT-TYPE
			SYNTAX INTEGER
				{
				fault(1),
				normal(2)
				}
			MAX-ACCESS read-only
			STATUS current
			DESCRIPTION
				"sub-rate switch state.
				Options:
				1. fault(1) -fault
				2. normal(2) -normal
				"
			::=	{ hwSubRateSwitchEntry 12	}
			
		hwSubRateSwitchRowStatus OBJECT-TYPE
			SYNTAX RowStatus
			MAX-ACCESS read-write
			STATUS current
			DESCRIPTION
				" 
				Row status. It supports only CreateAndGo(4) and Destroy(6).
        "
			::=	{ hwSubRateSwitchEntry 13 }
						
		hwNextAllocSubRateSwitchID	OBJECT-TYPE
			SYNTAX		Integer32(0..1023)
			MAX-ACCESS	read-only
			STATUS		current
			DESCRIPTION
				"
				Next valid allocation of SubRateSwitch index
				Range: 0-1023.
				"
			::=	{ hwSpcMibObjects 7	}
						
		hwIpSpcMinUdp	OBJECT-TYPE
			SYNTAX		Integer32(0..65535)
			MAX-ACCESS	read-only
			STATUS		current
			DESCRIPTION
				"
				Start UDP port of IPSPC.
				Range: 0-65535.
				"
			::=	{ hwSpcMibObjects 8	}
						
		hwIpSpcMaxUdp	OBJECT-TYPE
			SYNTAX		Integer32(0..65535)
			MAX-ACCESS	read-only
			STATUS		current
			DESCRIPTION
				"
				End UDP port of IPSPC.
				Range: 0-65535.
				"
			::=	{ hwSpcMibObjects 9	}
    --end: add for scs
    
		hwSpcMibTrap OBJECT	IDENTIFIER ::= { hwSPC 2 }

		hwSpcTrapOid OBJECT	IDENTIFIER ::= { hwSpcMibTrap 1	}

		hwSpcTrapsDefine OBJECT	IDENTIFIER ::= { hwSpcMibTrap 2	}

		hwSpcTraps OBJECT IDENTIFIER ::= { hwSpcTrapsDefine	0 }

		hwSpcMibCompance OBJECT	IDENTIFIER ::= { hwSPC 3 }
		
		hwIASSpcTrapsVbOids OBJECT IDENTIFIER ::= { hwSPC 4 }

		hwIASSpcTraps OBJECT IDENTIFIER ::= { hwSPC 5 }
		
		hwIASSpcCommonTraps OBJECT IDENTIFIER ::= { hwIASSpcTraps 1 }
		hwIASSpcCommonTrapsPrefix OBJECT IDENTIFIER ::= { hwIASSpcCommonTraps 0 }
		
		hwIASSpcAlarmTraps OBJECT IDENTIFIER ::= { hwIASSpcTraps 2 }
		hwIASSpcAlarmTrapsPrefix OBJECT IDENTIFIER ::= { hwIASSpcAlarmTraps 0 }
		
 --  /* Start hwIASSpcTrapsVbOids */

    hwIASSpcBChn OBJECT-TYPE
    SYNTAX     Unsigned32(0..32)
    MAX-ACCESS accessible-for-notify
    STATUS current
    DESCRIPTION
        "
        Indicates the B-channel.
        "
    ::= { hwIASSpcTrapsVbOids 1 }  
    
    hwIASSpcDspFrame OBJECT-TYPE
    SYNTAX     Unsigned32(0..255)
    MAX-ACCESS accessible-for-notify
    STATUS current
    DESCRIPTION
        "
        Indicate the shelf ID of a DSP resource board.
        "
    ::= { hwIASSpcTrapsVbOids 2 }  
    
    hwIASSpcDspSlot OBJECT-TYPE
    SYNTAX     Unsigned32(0..255)
    MAX-ACCESS accessible-for-notify
    STATUS current
    DESCRIPTION
        "
        Indicate the slot ID of a DSP resource board.
        "
    ::= { hwIASSpcTrapsVbOids 3 }  
    
    hwIASSpcDspSub OBJECT-TYPE
    SYNTAX     Unsigned32(0..255)
    MAX-ACCESS accessible-for-notify
    STATUS current
    DESCRIPTION
        "
       Indicate the DSP sub-board ID of a resource board.
        "
    ::= { hwIASSpcTrapsVbOids 4 }
    
    hwIASSpcDspChannel OBJECT-TYPE
    SYNTAX     Unsigned32(0..65535)
    MAX-ACCESS accessible-for-notify
    STATUS current
    DESCRIPTION
        "
        Indicate the DSP inner channel ID of a subboard.
        "
    ::= { hwIASSpcTrapsVbOids 5 }
    
    hwIASSpcDspLoopdelay OBJECT-TYPE
    SYNTAX     Unsigned32(0..4294967295)
    MAX-ACCESS accessible-for-notify
    STATUS current
    DESCRIPTION
        "
        Indicate the DSP loop delay.
        "
    ::= { hwIASSpcTrapsVbOids 6 }
    
    hwIASSpcDspFractionLost OBJECT-TYPE
    SYNTAX     Unsigned32(0..4294967295)
    MAX-ACCESS accessible-for-notify
    STATUS current
    DESCRIPTION
        "
        Indicate the DSP fractionLost.
        "
    ::= { hwIASSpcTrapsVbOids 7 }
    
    hwIASSpcDspJitter OBJECT-TYPE
    SYNTAX     Unsigned32(0..4294967295)
    MAX-ACCESS accessible-for-notify
    STATUS current
    DESCRIPTION
        "
        The DSP jitter.
        "
    ::= { hwIASSpcTrapsVbOids 8 }
    
    hwIASSpcOperateType OBJECT-TYPE
    SYNTAX     INTEGER{ add(0), delete(1), modify(2), release(3), undorelease(4), dspconfig(5) }
    MAX-ACCESS accessible-for-notify
    STATUS current
    DESCRIPTION
        "
        Indicate the operate type on a SPC.
        Options:
				1. add(0) -add spc link
				2. delete(1) -delete spc link
				3. modify(2) -modify spc link
				4. release(3) -spc link end service 
				5. undorelease(4) -spc link start service
				6. dspconfig(5) -config spc link dsp parameters
        "
    ::= { hwIASSpcTrapsVbOids 9 }
    
 --  /*  End  hwIASSpcTrapsVbOids */  
       		
 --  /* Start hwIASSpcCommonTraps */	
    hwIASSpcOperateTrap NOTIFICATION-TYPE
    OBJECTS  { hwSpcNo,hwIASSpcOperateType }
    STATUS      current
    DESCRIPTION    
        "
        This notification indicates that the operation on the SPC.
        "
    ::= { hwIASSpcCommonTraps 0 1 }
 --  /* End hwIASSpcCommonTraps */
   
 --  /* Start hwIASSpcAlarmTraps */

    hwIASSpcFaultTrap NOTIFICATION-TYPE
    OBJECTS  { hwSpcNo }
    STATUS      current
    DESCRIPTION    
        "
        This notification indicates that the SPC is faulty.
        "
    ::= { hwIASSpcAlarmTraps 0 1 }

    hwIASSpcRestoreTrap NOTIFICATION-TYPE
    OBJECTS  { hwSpcNo }
    STATUS      current
    DESCRIPTION    
        "
        This notification indicates that the SPC recovers from a fault.
        "
    ::= { hwIASSpcAlarmTraps 0 2 }
    
    hwIASSpcReleaseTrap NOTIFICATION-TYPE
    OBJECTS  { hwSpcNo }
    STATUS      current
    DESCRIPTION    
        "
        This notification indicates that the SPC is released.
        "
    ::= { hwIASSpcAlarmTraps 0 3 }
    
    hwIASSpcConnectTrap NOTIFICATION-TYPE
    OBJECTS  { hwSpcNo }
    STATUS      current
    DESCRIPTION    
        "
        This notification indicates that the SPC is connected again.
        "
    ::= { hwIASSpcAlarmTraps 0 4 }
    
    hwIASSpcQosExceedTrap NOTIFICATION-TYPE
    OBJECTS  { hwSpcNo, hwIASSpcBChn, hwIASSpcDspFrame, hwIASSpcDspSlot, hwIASSpcDspSub, hwIASSpcDspChannel,
               hwIpSpcAttributeRemoteIPAddr, hwIASSpcDspLoopdelay, hwIASSpcDspFractionLost, hwIASSpcDspJitter }
    STATUS      current
    DESCRIPTION    
        "
        This notification indicates that the value of DSP QoS used by the SPC exceeds the threshold.
        "
    ::= { hwIASSpcAlarmTraps 0 5 }  
    
    hwIASSpcQosRestoreTrap NOTIFICATION-TYPE
    OBJECTS  { hwSpcNo, hwIASSpcBChn, hwIASSpcDspFrame, hwIASSpcDspSlot, hwIASSpcDspSub, hwIASSpcDspChannel,
               hwIpSpcAttributeRemoteIPAddr, hwIASSpcDspLoopdelay, hwIASSpcDspFractionLost, hwIASSpcDspJitter }
    STATUS      current
    DESCRIPTION    
        "
        This notification indicates that the value of DSP QoS used by the SPC is normal.
        "
    ::= { hwIASSpcAlarmTraps 0 6 }
      
 --  /*  End  hwIASSpcAlarmTraps */  		

	END
