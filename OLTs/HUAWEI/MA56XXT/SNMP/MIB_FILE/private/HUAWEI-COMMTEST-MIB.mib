-- ============================================================================
-- Copyright (C) 2015 by  HUAWEI TECHNOLOGIES. All rights reserved.
-- Description:   This MIB is used for Metallic line test(MELT).Melt test is a
--                common line status test method,used to test whether the copper
--                twisted pair from the service board to the phone set is normal.
--                Common MELT operations include starting a MELT test, querying 
--                the test result, querying the calibration data, and starting 
--                and stopping a searching tone test.  
-- Reference:  
-- Version: V3.46
-- ============================================================================
  HUAWEI-COMMTEST-MIB DEFINITIONS ::= BEGIN
 
    IMPORTS
      huaweiUtility     
        FROM HUAWEI-MIB     
      ifIndex     
        FROM IF-MIB     
      Unsigned32, Gauge32, BITS, Counter64, Integer32, OBJECT-TYPE, MODULE-IDENTITY, NOTIFICATION-TYPE          
        FROM SNMPv2-SMI     
      RowStatus, DateAndTime, TruthValue      
        FROM SNMPv2-TC
      TimeTicks         
        FROM SNMPv2-SMI 
      hwFrameIndex,hwSlotIndex
        FROM HUAWEI-DEVICE-MIB
            hwTrapSN
        FROM HUAWEI-SNMP-NOTIFICATION-MIB;
    
    hwTestCommon MODULE-IDENTITY 
        LAST-UPDATED "201507081000Z"
        ORGANIZATION "Huawei Technologies Co.,Ltd."
        CONTACT-INFO                                 
                     "Huawei Industrial Base         
                      Bantian, Longgang              
                      Shenzhen 518129                
                      People's Republic of China     
                      Website: http://www.huawei.com 
                      Email: support@huawei.com      
                     "
        DESCRIPTION                                        
          "This MIB is used for Metallic line test(MELT).Melt test is a 
           common line status test method,used to test whether the copper
           twisted pair from the service board to the phone set is normal.
           Common MELT operations include starting a MELT test, querying 
           the test result, querying the calibration data, and starting 
           and stopping a searching tone test.
          "

--  Revision history
      REVISION    "201507081000Z" 
      DESCRIPTION "V3.46,
                  1.Added enum(prohibit(3) and allow(4)) into hwLoopLineTestOprType
		  2.Added enum(prohibitmelt(13)) into hwLoopLineTestStatus"

      REVISION    "201503251500Z" 
      DESCRIPTION "V3.45, Modified the description of the leaf hwONTPotsTestItem"
      
      REVISION    "201501201200Z" 
      DESCRIPTION "V3.44, Modified the values of the following leaves:
                   hwBoardMeltChipStateCheckDCVolUpperLimit 
                   hwBoardMeltChipStateCheckDCVolLowerLimit"
      
      REVISION    "201412121200Z" 
      DESCRIPTION "V3.43, Modified the description of the leaf hwLoopLineTestConclusion"
      
      REVISION    "201411041435Z" 
      DESCRIPTION "V3.42,
                   1. Added enum(meltChipFaulty (11) and meltChipCheckInProcess(12)) into hwLoopLineTestStatus
                   2. Added hwLoopLineTestMeltChipStateTable. 
                      Added the following leaves into hwLoopLineTestMeltChipStateTable:
                      hwBoardMeltChipStateCheckConfig
                      hwBoardMeltChipStateCheckResult
                      hwPortMeltChipStateList
                      hwBoardMeltChipStateCheckDCVolUpperLimit
                      hwBoardMeltChipStateCheckDCVolLowerLimit
                   3. Added hwMeltChipStateCheck table.
                      Added the following leaves into  hwMeltChipStateCheck table:
                      hwMeltChipStateCheckConfig
                      hwMeltChipStateCheckTime
                      hwMeltChipStateCheckDCVolUpperLimit
                      hwMeltChipStateCheckDCVolLowerLimit
                   4. Added hwTestMeltChipID into hwTestCommonTrapVbOids:
                   5. Added the following leaves into hwTestCommonAlarmTrapsOIDs:
                      hwTestMeltChipFaultAlarmTrap
                      hwTestMeltChipRecoveryAlarmTrap
                   6. Added hwTestMeltChipStateCheckResultTrap into hwTestCommonGeneralTrapsOIDs"
                   
      REVISION    "201406041040Z" 
      DESCRIPTION "V3.41, Modified the syntax for OMSYS"

      REVISION    "201404091000Z" 
      DESCRIPTION "V3.40, Cleared tab"
      
      REVISION    "201403161600Z" 
      DESCRIPTION "V3.39, Modified the default value of the leaf hwLoopLineTestBusyProcFlag"
      
      REVISION    "201309161600Z" 
      DESCRIPTION "V3.38, Added the following leaves into hwONTPotsTestOprTable:
                   hwONTPotsTestLoopDCAGVoltCompensativeValue
                   hwONTPotsTestLoopDCBGVoltCompensativeValue
                   hwONTPotsTestLoopDCABVoltCompensativeValue
                   hwONTPotsTestLoopACAGVoltCompensativeValue
                   hwONTPotsTestLoopACBGVoltCompensativeValue
                   hwONTPotsTestLoopACABVoltCompensativeValue
                   hwONTPotsTestLoopResistanceAGCompensativeValue
                   hwONTPotsTestLoopResistanceBGCompensativeValue
                   hwONTPotsTestLoopResistanceABCompensativeValue
                  "
      
      REVISION    "201204150900Z" 
      DESCRIPTION "V3.37, Added an enum into hwLoopLineTestStatus    
                   Delete unnecessary en dashes
                  "
                  
      REVISION    "201203220900Z" 
      DESCRIPTION "V3.36, Added the following leaves into hwLoopLineTestSysConfigPara:
                   hwLoopLineTestSysConfigSigCapUpperLimit
                   hwLoopLineTestSysConfigSigCapLowerLimit
                   hwLoopLineTestSysConfigSigResistance
                  "

      REVISION    "201203210900Z" 
      DESCRIPTION "V3.35, Modified the string length and description of 
                   hwLoopLineTestMeltChip.
                   
                   Added the following leaves into hwLoopLineTestOprTable:
                   hwLoopLineTestCapterminal
                   hwLoopLineTestCapterminalFlag.
                   
                   Added the following leaves into hwLoopLineTestSysConfigPara:
                   hwLoopLineTestSysConfigCableFactor
                  "

      REVISION    "201105051900Z" 
      DESCRIPTION "V3.34, Modified the definitions of hwLoopLineTestOprTable and hwTestCommonMeltTestResultTrap.
                   Added following leaves into hwLoopLineTestOprTable:
                   hwLoopLineTestCtrLV
                   hwLoopLineTestCtrLVFlag
                   hwLoopLineTestCtrHV
                   hwLoopLineTestCtrHVFlag
                   hwLoopLineTestCtrAc
                   hwLoopLineTestCtrAcFlag
                   hwLoopLineTestRtgSer
                   hwLoopLineTestRtgSerFlag
                   hwLoopLineTestRrgSer
                   hwLoopLineTestRrgSerFlag
                   hwLoopLineTestRtrSer
                   hwLoopLineTestRtrSerFlag
                   hwLoopLineTestUtgAcAdmit
                   hwLoopLineTestUtgAcAdmitFlag
                   hwLoopLineTestUrgAcAdmit
                   hwLoopLineTestUrgAcAdmitFlag
                   hwLoopLineTestUtrAcAdmit
                   hwLoopLineTestUtrAcAdmitFlag

                   Add enums into leaf hwLoopLineTestMoreDataFlag in hwTestCommonMeltTestResultTrap.
                  "

--  Revision history
      REVISION    "201104300900Z" 
      DESCRIPTION "V3.33, Added following leaves into hwLoopLineTestOprTable:
                   hwONTPotsTestLoopDCABVoltValue
                   hwONTPotsTestLoopACABVoltValue
                   hwONTPotsTestLoopAGCapacitanceValue
                   hwONTPotsTestLoopBGCapacitanceValue
                   hwONTPotsTestLoopABCapacitanceValue
                   
                   Added the following trap nodes into hwTestOntPotsTestResultTrap:
                   hwONTPotsTestLoopDCABVoltValue
                   hwONTPotsTestLoopACABVoltValue
                   hwONTPotsTestLoopAGCapacitanceValue
                   hwONTPotsTestLoopBGCapacitanceValue
                   hwONTPotsTestLoopABCapacitanceValue
                   
                   Modified the leaves's description of hwONTPotsTestOprTable:
                   hwONTPotsTestLoopDCAGVoltValue
                   hwONTPotsTestLoopDCBGVoltValue
                   hwONTPotsTestLoopACAGVoltValue
                   hwONTPotsTestLoopACBGVoltValue 
                   hwONTPotsTestLoopResistanceAGValue   
                   hwONTPotsTestLoopResistanceBGValue 
                   hwONTPotsTestLoopResistanceABValue
                   "

--  Revision history                     
      REVISION    "201103060900Z" 
      DESCRIPTION "V3.32, Modified the definition of the table hwLoopLineTestOprTable.
                   Added following leaves into hwLoopLineTestOprTable: 
                   hwLoopLineTestLRFlag
                   hwLoopLineTestDcCurrent              
                   hwLoopLineTestAcCurrent              
                   hwLoopLineTestConductance            
                   hwLoopLineTestSusceptance            
                   hwLoopLineTestAcfrequencyA           
                   hwLoopLineTestAcfrequencyB           
                   hwLoopLineTestRABH                   
                   hwLoopLineTestRABHFlag               
                   hwLoopLineTestCapABH                 
                   hwLoopLineTestCapABHFlag             
                   hwLoopLineTestGtrH                   
                   hwLoopLineTestGtrHFlag               
                   hwLoopLineTestBtrH                   
                   hwLoopLineTestBtrHFlag               
                   hwLoopLineTestABDcCurrent            
                   hwLoopLineTestABDcCurrentFlag        
                   hwLoopLineTestBADcCurrent            
                   hwLoopLineTestBADcCurrentFlag        
                   hwLoopLineTestABAcCurrent            
                   hwLoopLineTestABAcCurrentFlag        
                   hwLoopLineTestBAAcCurrent            
                   hwLoopLineTestBAAcCurrentFlag        
                   hwLoopLineTestCSfrequencyForTest     
                   hwLoopLineTestCSfrequencyForTestFlag 
                   hwLoopLineTestImpedanceForTest       
                   hwLoopLineTestImpedanceForTestFlag   
                   hwLoopLineTestMaxVForSignature       
                   hwLoopLineTestMaxVForSignatureFlag   
                   hwLoopLineTestAGMaxVForTest          
                   hwLoopLineTestAGMaxVForTestFlag      
                   hwLoopLineTestAGMinVForTest          
                   hwLoopLineTestAGMinVForTestFlag      
                   hwLoopLineBGMaxVForTest              
                   hwLoopLineTestBGMaxVForTestFlag      
                   hwLoopLineTestBGMinVForTest          
                   hwLoopLineTestBGMinVForTestFlag      
                   hwLoopLineTestABMaxVForTest          
                   hwLoopLineTestABMaxVForTestFlag      
                   hwLoopLineTestABMinVForTest          
                   hwLoopLineTestABMinVForTestFlag      
                   hwLoopLineTestAGMaxCForTest          
                   hwLoopLineTestAGMaxCForTestFlag      
                   hwLoopLineTestAGMinCForTest          
                   hwLoopLineTestAGMinCForTestFlag      
                   hwLoopLineTestBGMaxCForTest          
                   hwLoopLineTestBGMaxCForTestFlag      
                   hwLoopLineTestBGMinCForTest          
                   hwLoopLineTestBGMinCForTestFlag      
                   hwLoopLineTestABMaxCForTest          
                   hwLoopLineTestABMaxCForTestFlag      
                   hwLoopLineTestABMaxNegCForTest       
                   hwLoopLineTestMaxNegCForTestFlag     
                   hwLoopLineTestMaxNegCForTestFlag 
                   hwLoopLineTestLineALength 
                   hwLoopLineTestLineBLength   
                   hwLoopLineTestTermimalConcusion
                   hwLoopLineTestMoreDataFlag  
                   
                   Add an enum notsupport(3) into following leaves:      
                   hwLoopLineTestACAGFlag                                  
                   hwLoopLineTestACBGFlag                                  
                   hwLoopLineTestACABFlag                                  
                   hwLoopLineTestDCAGFlag                                  
                   hwLoopLineTestDCBGFlag                                  
                   hwLoopLineTestDCABFlag                                  
                   hwLoopLineTestRAGFlag                                   
                   hwLoopLineTestRBGFlag                                   
                   hwLoopLineTestRABFlag                                   
                   hwLoopLineTestRABPoleFlag                               
                   hwLoopLineTestRABResPoleFlag                            
                   hwLoopLineTestCapAGFlag                                 
                   hwLoopLineTestCapBGFlag                                 
                   hwLoopLineTestCapABFlag                                 
                   hwLoopLineTestRbattipFlag                               
                   hwLoopLineTestRbatringFlag                              
                   hwLoopLineTestRringFlag                                 
                   hwLoopLineTestCsigFlag                                  
                   hwLoopLineTestUtgAcFreqFlag                             
                   hwLoopLineTestUrgAcFreqFlag                             
                   hwLoopLineTestUtrAcFreqFlag                             
                   hwLoopLineTestItipAcFlag                                
                   hwLoopLineTestIringAcFlag                               
                   hwLoopLineTestItipDcFlag                                
                   hwLoopLineTestIringDcFlag                               
                   hwLoopLineTestGtgFlag                                   
                   hwLoopLineTestBtgFlag                                   
                   hwLoopLineTestGrgFlag                                   
                   hwLoopLineTestBrgFlag                                   
                   hwLoopLineTestGtrFlag                                   
                   hwLoopLineTestBtrFlag  
                   
                   Add enums into leave hwLoopLineTestConclusion in hwLoopLineTestOprTable: 
                   abRFaultId(91)
                   aRFaultId(92)
                   bRFaultId(93)
                   abLeakId(94)
                   aLeakId(95)
                   bLeakId(96)
                   abFvacLevelH(97)
                   aFvacLevelH(98)
                   bFvacLevelH(99)
                   abFvacLevelI(100)
                   aFvacLevelI(101)
                   bFvacLevelI(102)
                   abFvacLevelO(103)
                   aFvacLevelO(104)
                   bFvacLevelO(105)
                   abFvDcLevelH(106)
                   aFvDcLevelH(107)
                   bFvDcLevelH(108)
                   abFvDcLevelI(109)
                   aFvDcLevelI(110)
                   bFvDcLevelI(111)
                   abFvDcLevelO(112)
                   aFvDcLevelO(113)
                   bFvDcLevelO(114)
                   fesIdPPA(115)
                   fesIdPPAInv(116)
                   fesId2PPA(117)
                   fesId2PPAInv(118)
                   etsiXdslSignature(119)
                   fetIdEr(120) 
                   abreak(121)
                   bbreak(122)
                   abreakInMDF(123) 
                   bbreakInMDF(124)
                   abreakOutMDF(125)
                   bbreakOutMDF(126)
                   
                   Added the following trap nodes into hwLoopLineTestTrap: 
                   hwLoopLineTestMSocket     
                   hwLoopLineTestPPAResult   
                   hwLoopLineTestMoreDataFlag 
                   
                   Added following leaves into hwSearchingToneOprTable: 
                   hwSearchingToneBusyProcFlag
                  "
        
--  Revision history 
      REVISION    "201012240900Z" 
      DESCRIPTION "V3.31, Modify the value of 
                   hwONTPotsTestSubscriberLineTestResult.
                  "

      REVISION    "201012220900Z" 
      DESCRIPTION "V3.30, Modified the description of MIB.
                  "
                  
      REVISION    "201011230900Z" 
      DESCRIPTION "V3.29, Added hwONTPotsTestSubscriberLineTestResult into 
                   hwONTPotsTestOprTable.         
                   Modified the definition of the trap node 
                   hwTestOntPotsTestResultTrap.
                  "

      REVISION    "201011090900Z" 
      DESCRIPTION "V3.28, Added hwWettingCurrentOprTable.         
                   Added following leaves into hwWettingCurrentOprTable:
                     hwWettingCurrentOprStatus   
                     hwWettingCurrentOprWorkingVoltage
                     hwWettingCurrentOprMaximumVoltage
                     hwWettingCurrentOprSlope.
                  Modified the description of MIB.
                  "
                  
      REVISION    "201010100900Z" 
      DESCRIPTION "V3.27, Modified the description of MIB.
                  "
                  
      REVISION    "201008110900Z" 
      DESCRIPTION "V3.26, Modified the definition of the trap node,include: hwLoopLineTestTrap.         
                   Added following leaves into hwLoopLineTestOprTable:
                     hwLoopLineTestIfIndex   
                     hwLoopLineTestRequestID.
                  "
                  
      REVISION    "201008100900Z"
      DESCRIPTION "V3.25, Delete hwONTPotsTestMLTResult note of the trap node: hwTestOntPotsTestResultTrap.
                   Modify the leaves's description of the table hwONTPotsTestOprTable.
                   Added an enum inverseexist(3) in leaf hwLoopLineTestPPAResult.
                  "
                  
      REVISION    "201007290900Z" 
      DESCRIPTION "V3.24, Added hwPortTestingListOprTable.
                   Modified the description of MIB.
                  "
                  
      REVISION    "201007070900Z" 
      DESCRIPTION "V3.23, Modified the name of hwTestCommonStartupMeltTestResultTrap to hwTestCommonMeltTestFaileTrap. 
                   Modified the description of MIB.
                   Added hwTestCommonRequestID, ifIndex, hwONTPotsTestONTIndex, hwONTPotsTestONTPstnPortIndex, and hwONTPotsTestItem to hwTestOntPotsTestResultTrap.                               
                   Added following leaves into hwLoopLineTestOprTable:  
                       hwLoopLineTestPPAResultFlag
                       hwLoopLineTestUtgAcFreqFlag
                       hwLoopLineTestUrgAcFreqFlag
                       hwLoopLineTestUtrAcFreqFlag
                       hwLoopLineTestItipAcFlag   
                       hwLoopLineTestIringAcFlag  
                       hwLoopLineTestItipDcFlag   
                       hwLoopLineTestIringDcFlag  
                       hwLoopLineTestGtgFlag      
                       hwLoopLineTestBtgFlag      
                       hwLoopLineTestGrgFlag      
                       hwLoopLineTestBrgFlag      
                       hwLoopLineTestGtrFlag      
                       hwLoopLineTestBtrFlag      
                       hwLoopLineTestSIGNFlag     
                       hwLoopLineTestACFEMFlag    
                       hwLoopLineTestDCFEMFlag    
                       hwLoopLineTestONHKFlag     
                       hwLoopLineTestOPENFlag     
                       hwLoopLineTestSHORTFlag    
                       hwLoopLineTestROHFlag      
                       hwLoopLineTestUtgDcUpFlag  
                       hwLoopLineTestUtgDcDownFlag
                       hwLoopLineTestUrgDcUpFlag  
                       hwLoopLineTestUrgDcDownFlag
                       hwLoopLineTestUtrPosFlag   
                       hwLoopLineTestUtrNegFlag   
                       hwLoopLineTestItgDcUpFlag  
                       hwLoopLineTestItgDcDownFlag
                       hwLoopLineTestIrgDcUpFlag  
                       hwLoopLineTestIrgDcDownFlag
                       hwLoopLineTestItrPosFlag   
                       hwLoopLineTestItrNegFlag   
                       hwLoopLineTestRingerFlag.  
                   Modified the name of hwSearchingToneTimeout to hwSearchingToneDurationTime.
                   Modified the range of hwSearchingToneDurationTime to 1-54000.
                   Modified the default value of hwSearchingToneDurationTime to 9000.  
                   Modified the unit of hwSearchingToneDurationTime to 0.1s.
                   Added hwSearchingToneRemainingTime to hwSearchingToneOprTable.
                 "          
    
      REVISION    "201006220900Z" 
      DESCRIPTION "V3.22, Modified the description of hwLoopLineTestRinger.
                  " 
      
      REVISION    "201004200900Z" 
      DESCRIPTION "V3.21, Modified the size list of hwLoopLineTestMeltFactory.
                  "          

      REVISION    "201004150900Z" 
      DESCRIPTION "V3.20, Added following leaves into hwLoopLineTestOprTable:
                     hwLoopLineTestSNMPRab
                     hwLoopLineTestSNMPRabFlag
                     hwLoopLineTestSNMPRba
                     hwLoopLineTestSNMPRbaFlag.
                 "    
    
      REVISION    "201004010900Z" 
      DESCRIPTION "V3.19, Modified the syntax error." 
                      
      REVISION    "201003090900Z" 
      DESCRIPTION "V3.18, Added following leaves into hwLoopLineTestOprTable:
                     hwLoopLineTestRABPole
                     hwLoopLineTestACAGFlag
                     hwLoopLineTestACBGFlag
                     hwLoopLineTestACABFlag
                     hwLoopLineTestDCAGFlag
                     hwLoopLineTestDCBGFlag
                     hwLoopLineTestDCABFlag
                     hwLoopLineTestRAGFlag
                     hwLoopLineTestRBGFlag
                     hwLoopLineTestRABFlag
                     hwLoopLineTestItrPosFlag
                     hwLoopLineTestItrNegFlag
                     hwLoopLineTestCapAGFlag
                     hwLoopLineTestCapBGFlag
                     hwLoopLineTestCapABFlag
                     hwLoopLineTestRbattipFlag
                     hwLoopLineTestRbatringFlag
                     hwLoopLineTestRringFlag
                     hwLoopLineTestCsigFlag
                     hwLoopLineTestPPAResFlag
                     hwLoopLineTestVzenerFlag
                     hwLoopLineTestRzenerFlag.
                   " 
                  
      REVISION    "201002080900Z" 
      DESCRIPTION "V3.17, modified the definitions of hwTestCommonMeltTestResultTrap and hwTestCommonStartupMeltTestResultTrap."   
      
      REVISION    "201001210900Z" 
      DESCRIPTION "V3.16, Added hwONTPotsTestOprTable for ONT POTS test.
                   Added the definition of the trap node:hwTestOntPotsTestResultTrap,include:
                     hwONTPotsTestMLTResult,
                     hwONTPotsTestHazardousVoltResult,
                     hwONTPotsTestEMFResult,
                     hwONTPotsTestResistacneResult,
                     hwONTPotsTestOffHookResult,
                     hwONTPotsTestRingerResult,
                     hwONTPotsTestNT1DCSignalResult,
                     hwONTPotsTestSelfTestResult,
                     hwONTPotsTestDrawDialToneResult,
                     hwONTPotsTestBreakDialToneResult,
                     hwONTPotsTestQuietEnergyResult,
                     hwONTPotsTestDialToneEnergyResult,
                     hwONTPotsTestLoopDCAGVoltResult,
                     hwONTPotsTestLoopDCBGVoltResult,
                     hwONTPotsTestLoopACAGVoltResult,       
                     hwONTPotsTestLoopACBGVoltResult,       
                     hwONTPotsTestLoopResistanceAGResult,   
                     hwONTPotsTestLoopResistanceBGResult,   
                     hwONTPotsTestLoopResistanceABResult,   
                     hwONTPotsTestLoopRingerLoadTestResult, 
                     hwONTPotsTestDrawDialToneTimeValue,    
                     hwONTPotsTestBreakDialToneTimeValue,   
                     hwONTPotsTestQuietEnergyValue,         
                     hwONTPotsTestDialToneEnergyValue,      
                     hwONTPotsTestLoopDCAGVoltValue,        
                     hwONTPotsTestLoopDCBGVoltValue,        
                     hwONTPotsTestLoopACAGVoltValue,        
                     hwONTPotsTestLoopACBGVoltValue,        
                     hwONTPotsTestLoopResistanceAGValue,    
                     hwONTPotsTestLoopResistanceBGValue,    
                     hwONTPotsTestLoopResistanceABValue,    
                     hwONTPotsTestLoopRingerLoadTestValue.
                  "  
                    
      REVISION    "201001120900Z" 
      DESCRIPTION "V3.15, Added definitions of hwTestCommonMeltTestResultTrap and hwTestCommonStartupMeltTestResultTrap."
               
      REVISION     "200912130900Z"        
      DESCRIPTION  "V3.14, Added hwLoopLineTestMeltVerTable for getting MELT chipset information.
                    Added hwLoopLineTestCalibrationTable for getting calibraton of MELT.
                    Added hwLoopLineTestOprMeasuredFreq for setting MELT with aggregate frequency.
                    Added hwSearchingToneTimeOut for setting timeout value of searchingtone.
                    Added hwLoopLineTestSysConfigPara for reverse polarity of A wire and B wire.
                    Added hwLoopLineTestSysConfigConvertAB in hwLoopLineTestSysConfigPara for setting MELT parameters. "

      REVISION    "200912070900Z" 
      DESCRIPTION "V3.13, Added following leaves into hwLoopLineTestOprTable:
                      hwLoopLineTestBtssPowerProcFlag
                      hwLoopLineTestImpedance
                      hwLoopLineTestImpedanceAB
                      hwLoopLineTestImpedanceBA
                      hwLoopLineTestImpedanceAG
                      hwLoopLineTestImpedanceBG
                      hwLoopLineTestCurrent
                      hwLoopLineTestACCurrentAG
                      hwLoopLineTestACCurrentBG
                      hwLoopLineTestACCurrentAB
                      hwLoopLineTestDCCurrentAG
                      hwLoopLineTestDCCurrentBG
                      hwLoopLineTestDCCurrentAB
                      hwLoopLineTestLoopCurrent
                      hwLoopLineTestLC
                      hwLoopLineTestNoise
                      hwLoopLineTestN
                      hwLoopLineTestPPA
                      hwLoopLineTestPPAResult
                      hwLoopLineTestDeferredTime
                      hwLoopLineTestTimeoutProc
                      hwLoopLineTestReverse
                      hwLoopLineTestUtgAcFreq
                      hwLoopLineTestUrgAcFreq
                      hwLoopLineTestUtrAcFreq
                      hwLoopLineTestItipAc
                      hwLoopLineTestIringAc
                      hwLoopLineTestItipDc
                      hwLoopLineTestIringDc
                      hwLoopLineTestRbattip
                      hwLoopLineTestRbatring
                      hwLoopLineTestRring
                      hwLoopLineTestCsig
                      hwLoopLineTestVzener
                      hwLoopLineTestRzener
                      hwLoopLineTestGtg
                      hwLoopLineTestBtg
                      hwLoopLineTestGrg
                      hwLoopLineTestBrg
                      hwLoopLineTestGtr
                      hwLoopLineTestBtr
                      hwLoopLineTestSIGN
                      hwLoopLineTestACFEM
                      hwLoopLineTestDCFEM
                      hwLoopLineTestONHK
                      hwLoopLineTestOPEN
                      hwLoopLineTestSHORT
                      hwLoopLineTestROH
                      hwLoopLineTestUtgDcUp
                      hwLoopLineTestUtgDcDown
                      hwLoopLineTestUrgDcUp
                      hwLoopLineTestUrgDcDown
                      hwLoopLineTestUtrPos
                      hwLoopLineTestUtrNeg
                      hwLoopLineTestItgDcUp
                      hwLoopLineTestItgDcDown
                      hwLoopLineTestIrgDcUp
                      hwLoopLineTestIrgDcDown
                      hwLoopLineTestItrPos
                      hwLoopLineTestItrNeg
                      hwLoopLineTestRinger
                      hwLoopLineTestPPARes
                      hwLoopLineTestStartTime
                      hwLoopLineTestEndTime.
                   Added hwMeterTestBusyFlag to hwMeterTestOprTable.
                   Added hwMeterTestBusyFlag to hwMeterTestOprTable.
                   Added hwTestBoardDiagnoseTestCapacitance to hwTestBoardDiagnoseTestOprTable.
                   Added hwSearchingToneOprTable.
                  "
  
      REVISION    "200304280900Z" 
      DESCRIPTION "V3.00, Removed Chinese description.
                  "   
      
      REVISION    "200303080900Z" 
      DESCRIPTION "V2.00, Corrected the SYNTAX.
                  "

      REVISION    "200301280900Z" 
      DESCRIPTION "V1.00, initial version."   
      
      ::= { hwTest 1 }
     
    hwTest OBJECT IDENTIFIER ::= { huaweiUtility 21 }
    
    hwTestCommonMib OBJECT IDENTIFIER ::= { hwTestCommon 1 }
    
    hwTestCommonMIBObjects OBJECT IDENTIFIER ::= { hwTestCommonMib 1 }
    
    hwTestGroupOprTable OBJECT-TYPE
      SYNTAX SEQUENCE OF HwTestGroupOprEntry
      MAX-ACCESS not-accessible
      STATUS current
      DESCRIPTION
        "Table of the test group:
         It provides the number of the test group to which a shelf of the device corresponds.
         It is uniquely identified by the number of the test group. Multiple shelves can share
         a test board.
         A test group corresponds to a test board. The number of a test group is the same as
         the number of the shelf that houses the test board to which the test group corresponds.
         The index of this table is hwTestGroupNo.
        "
      ::= { hwTestCommonMIBObjects 1 }
    
    hwTestGroupOprEntry OBJECT-TYPE
      SYNTAX HwTestGroupOprEntry
      MAX-ACCESS not-accessible
      STATUS current
      DESCRIPTION      
        "Table of the test group:
         It provides the number of the test group to which a shelf of the device corresponds.
         It is uniquely identified by the number of the test group. Multiple shelves can share
         a test board.
         A test group corresponds to a test board. The number of a test group is the same as
         the number of the shelf that houses the test board to which the test group corresponds.
         The index of this entry is hwTestGroupNo.
        "
      INDEX { hwTestGroupNo }
      ::= { hwTestGroupOprTable 1 }
    
    HwTestGroupOprEntry ::=
      SEQUENCE { 
        hwTestGroupNo
          Integer32,
        hwTestBoardIfIndex
          Integer32,
        hwTestGroupAssistIfIndex
          Integer32,
        hwTestGroupAssistTelNo
          OCTET STRING,
        hwTestGroupRowStatus
          RowStatus
       }

    hwTestGroupNo OBJECT-TYPE
      SYNTAX Integer32 (0..240)
      MAX-ACCESS not-accessible
      STATUS current
      DESCRIPTION
        "Test group number. The MD5500 supports the number that ranges from 0 to 240. 
         The MA5100 supports the number that ranges from 0 to 4.
         The MA5300 supports the number that ranges from 0 to 63.
        "
      ::= { hwTestGroupOprEntry 1 }
    
    hwTestBoardIfIndex OBJECT-TYPE
      SYNTAX Integer32
      MAX-ACCESS read-create
      STATUS current
      DESCRIPTION
        "Test board IfIndex."
      ::= { hwTestGroupOprEntry 2 }
    
    hwTestGroupAssistIfIndex OBJECT-TYPE
      SYNTAX Integer32
      MAX-ACCESS read-create
      STATUS current
      DESCRIPTION
        "TestGroupAssist port IfIndex."
      ::= { hwTestGroupOprEntry 3 }
    
    hwTestGroupAssistTelNo OBJECT-TYPE
      SYNTAX OCTET STRING (SIZE (0..16))
      MAX-ACCESS read-create
      STATUS current
      DESCRIPTION
        "Assistant telephone number.
         The maximum length is 16 Octets."
      ::= { hwTestGroupOprEntry 4 }
    
    hwTestGroupRowStatus OBJECT-TYPE
      SYNTAX RowStatus
      MAX-ACCESS read-create
      STATUS current
      DESCRIPTION
        "Present operation status of a row.
         Options:
         1. active(1),        -the present operation status of the row is active 
         2. notInService(2),  -the present operation status of the row is notInService
         3. notReady(3),      -the present operation status of the row is notReady
         4. createAndGo(4),   -the present operation status of the row is createAndGo
         5. createAndWait(5), -the present operation status of the row is createAndWait
         6. destroy(6)        -the present operation status of the row is destroy
        "
      ::= { hwTestGroupOprEntry 5 }
    
    hwLoopLineTestOprTable OBJECT-TYPE
      SYNTAX SEQUENCE OF HwLoopLineTestOprEntry
      MAX-ACCESS not-accessible
      STATUS current
      DESCRIPTION
        "This table is used for enabling a subscriber line test and obtaining the test result
         after a test is complete. The subscriber line test function can be used for obtaining 
         the performance information about a subscriber line, such as capacity and resistance. 
         Users can learn about the conditions of the line by comparing such information with
         standard data.
         The index of this table is ifindex.
        "
      ::= { hwTestCommonMIBObjects 2 }
    
    -- 1.3.6.1.4.1.2011.6.21.1.1.1.2.1
    hwLoopLineTestOprEntry OBJECT-TYPE
      SYNTAX HwLoopLineTestOprEntry
      MAX-ACCESS not-accessible
      STATUS current
      DESCRIPTION      
        "This table is used for enabling a subscriber line test and obtaining the test result
         after a test is complete. The subscriber line test function can be used for obtaining 
         the performance information about a subscriber line, such as capacity and resistance. 
         Users can learn about the conditions of the line by comparing such information with
         standard data.
         The index of this entry is ifindex.
        "
      INDEX { ifIndex }
      ::= { hwLoopLineTestOprTable 1 }
    
    HwLoopLineTestOprEntry ::=
      SEQUENCE { 
        hwLoopLineTestOprType
          INTEGER,
        hwLoopLineTestVoltage
          INTEGER,
        hwLoopLineTestResistance
          INTEGER,
        hwLoopLineTestCapacitance
          INTEGER,
        hwLoopLineTestLoopResistance
          INTEGER,
        hwLoopLineTestPoleResistance
          INTEGER,
        hwLoopLineTestBusyProcFlag
          INTEGER,
        hwLoopLineTestStatus
          INTEGER,
        hwLoopLineTestConclusion
          INTEGER,
        hwLoopLineTestACAG
          Integer32,
        hwLoopLineTestACBG
          Integer32,
        hwLoopLineTestACAB
          Integer32,
        hwLoopLineTestDCAG
          Integer32,
        hwLoopLineTestDCBG
          Integer32,
        hwLoopLineTestDCAB
          Integer32,
        hwLoopLineTestRAG
          Integer32,
        hwLoopLineTestRBG
          Integer32,
        hwLoopLineTestRAB
          Integer32,
        hwLoopLineTestCapAG
          Integer32,
        hwLoopLineTestCapBG
          Integer32,
        hwLoopLineTestCapAB
          Integer32,
        hwLoopLineTestLR
          Integer32,
        hwLoopLineTestRABResPole
          Integer32,
        hwLoopLineTestMSocket
          INTEGER,
        hwLoopLineTestBtssPowerProcFlag
          INTEGER,
        hwLoopLineTestImpedance
          INTEGER,
        hwLoopLineTestImpedanceAB
          Integer32,
        hwLoopLineTestImpedanceBA
          Integer32,
        hwLoopLineTestImpedanceAG
          Integer32,
        hwLoopLineTestImpedanceBG
          Integer32,
        hwLoopLineTestCurrent
          INTEGER,
        hwLoopLineTestACCurrentAG
          Integer32,
        hwLoopLineTestACCurrentBG
          Integer32,
        hwLoopLineTestACCurrentAB
          Integer32,
        hwLoopLineTestDCCurrentAG
          Integer32,
        hwLoopLineTestDCCurrentBG
          Integer32,
        hwLoopLineTestDCCurrentAB
          Integer32,
        hwLoopLineTestLoopCurrent
          INTEGER,
        hwLoopLineTestLC
          Integer32,
        hwLoopLineTestNoise
          INTEGER,
        hwLoopLineTestN
          Integer32,
        hwLoopLineTestPPA
          INTEGER,
        hwLoopLineTestPPAResult
          INTEGER,
        hwLoopLineTestDeferredTime
          Integer32,
        hwLoopLineTestTimeoutProc
          INTEGER,
        hwLoopLineTestReverse
          Integer32,
        hwLoopLineTestUtgAcFreq
          Integer32,
        hwLoopLineTestUrgAcFreq
          Integer32,
        hwLoopLineTestUtrAcFreq
          Integer32,
        hwLoopLineTestItipAc
          Integer32,
        hwLoopLineTestIringAc
          Integer32,
        hwLoopLineTestItipDc
          Integer32,
        hwLoopLineTestIringDc
          Integer32,
        hwLoopLineTestRbattip
          Integer32,
        hwLoopLineTestRbatring
          Integer32,
        hwLoopLineTestRring
          Integer32,
        hwLoopLineTestCsig
          Integer32,
        hwLoopLineTestVzener
          Integer32,
        hwLoopLineTestRzener
          Integer32,
        hwLoopLineTestGtg
          Integer32,
        hwLoopLineTestBtg
          Integer32,
        hwLoopLineTestGrg
          Integer32,
        hwLoopLineTestBrg
          Integer32,
        hwLoopLineTestGtr
          Integer32,
        hwLoopLineTestBtr
          Integer32,
        hwLoopLineTestSIGN
          TruthValue,
        hwLoopLineTestACFEM
          TruthValue,
        hwLoopLineTestDCFEM
          TruthValue,
        hwLoopLineTestONHK
          TruthValue,
        hwLoopLineTestOPEN
          TruthValue,
        hwLoopLineTestSHORT
          TruthValue,
        hwLoopLineTestROH
          TruthValue,
        hwLoopLineTestUtgDcUp
          Integer32,
        hwLoopLineTestUtgDcDown
          Integer32,
        hwLoopLineTestUrgDcUp
          Integer32,
        hwLoopLineTestUrgDcDown
          Integer32,
        hwLoopLineTestUtrPos
          Integer32,
        hwLoopLineTestUtrNeg
          Integer32,
        hwLoopLineTestItgDcUp
          Integer32,
        hwLoopLineTestItgDcDown
          Integer32,
        hwLoopLineTestIrgDcUp
          Integer32,
        hwLoopLineTestIrgDcDown
          Integer32,
        hwLoopLineTestItrPos
          Integer32,
        hwLoopLineTestItrNeg
          Integer32,
        hwLoopLineTestRinger
          Integer32,
        hwLoopLineTestPPARes
          Integer32,
        hwLoopLineTestStartTime
          DateAndTime,
        hwLoopLineTestEndTime
          DateAndTime,
        hwLoopLineTestOprMeasuredFreq 
          INTEGER,
        hwLoopLineTestIfIndex
          Integer32,
        hwLoopLineTestRequestID
          Integer32,    
        hwLoopLineTestRABPole
          Integer32,
        hwLoopLineTestACAGFlag
          INTEGER,
        hwLoopLineTestACBGFlag
          INTEGER,
        hwLoopLineTestACABFlag
          INTEGER,
        hwLoopLineTestDCAGFlag
          INTEGER,
        hwLoopLineTestDCBGFlag
          INTEGER,
        hwLoopLineTestDCABFlag
          INTEGER,
        hwLoopLineTestRAGFlag
          INTEGER,
        hwLoopLineTestRBGFlag
          INTEGER,
        hwLoopLineTestRABFlag
          INTEGER,
        hwLoopLineTestRABPoleFlag
          INTEGER,
        hwLoopLineTestRABResPoleFlag
          INTEGER,
        hwLoopLineTestCapAGFlag
          INTEGER,
        hwLoopLineTestCapBGFlag
          INTEGER,
        hwLoopLineTestCapABFlag
          INTEGER,
        hwLoopLineTestRbattipFlag
          INTEGER,
        hwLoopLineTestRbatringFlag
          INTEGER,
        hwLoopLineTestRringFlag
          INTEGER,
        hwLoopLineTestCsigFlag
          INTEGER,
        hwLoopLineTestPPAResFlag
          INTEGER,
        hwLoopLineTestVzenerFlag
          INTEGER,
        hwLoopLineTestRzenerFlag
          INTEGER,
        hwLoopLineTestSNMPRab
          Integer32,
        hwLoopLineTestSNMPRabFlag
          INTEGER,
        hwLoopLineTestSNMPRba
          Integer32,
        hwLoopLineTestSNMPRbaFlag
          INTEGER,
        hwLoopLineTestPPAResultFlag 
          INTEGER,
        hwLoopLineTestUtgAcFreqFlag  
          INTEGER,
        hwLoopLineTestUrgAcFreqFlag
          INTEGER,
        hwLoopLineTestUtrAcFreqFlag  
          INTEGER, 
        hwLoopLineTestItipAcFlag 
          INTEGER,
        hwLoopLineTestIringAcFlag
          INTEGER,
        hwLoopLineTestItipDcFlag
          INTEGER,
        hwLoopLineTestIringDcFlag
          INTEGER,
        hwLoopLineTestGtgFlag
          INTEGER,
        hwLoopLineTestBtgFlag
          INTEGER,  
        hwLoopLineTestGrgFlag
          INTEGER,
        hwLoopLineTestBrgFlag      
          INTEGER,
        hwLoopLineTestGtrFlag      
          INTEGER,
        hwLoopLineTestBtrFlag      
          INTEGER,
        hwLoopLineTestSIGNFlag     
          INTEGER,
        hwLoopLineTestACFEMFlag    
          INTEGER,
        hwLoopLineTestDCFEMFlag    
          INTEGER,
        hwLoopLineTestONHKFlag     
          INTEGER,
        hwLoopLineTestOPENFlag     
          INTEGER,
        hwLoopLineTestSHORTFlag    
          INTEGER,
        hwLoopLineTestROHFlag      
          INTEGER,
        hwLoopLineTestUtgDcUpFlag  
          INTEGER,
        hwLoopLineTestUtgDcDownFlag
          INTEGER, 
        hwLoopLineTestUrgDcUpFlag  
          INTEGER,
        hwLoopLineTestUrgDcDownFlag
          INTEGER,
        hwLoopLineTestUtrPosFlag   
          INTEGER,
        hwLoopLineTestUtrNegFlag   
          INTEGER,
        hwLoopLineTestItgDcUpFlag  
          INTEGER,
        hwLoopLineTestItgDcDownFlag
          INTEGER,
        hwLoopLineTestIrgDcUpFlag  
          INTEGER,
        hwLoopLineTestIrgDcDownFlag
          INTEGER,
        hwLoopLineTestItrPosFlag   
          INTEGER,  
        hwLoopLineTestItrNegFlag   
          INTEGER,
        hwLoopLineTestRingerFlag   
          INTEGER,
        hwLoopLineTestLRFlag
          INTEGER,
        hwLoopLineTestDcCurrent
          INTEGER,
        hwLoopLineTestAcCurrent
          INTEGER,
        hwLoopLineTestConductance
          INTEGER,
        hwLoopLineTestSusceptance
          INTEGER,
        hwLoopLineTestAcfrequencyA
          INTEGER,
        hwLoopLineTestAcfrequencyB
          INTEGER,
        hwLoopLineTestCapABH
          Integer32,
        hwLoopLineTestCapABHFlag
          INTEGER,
        hwLoopLineTestGtrH
          Integer32,
        hwLoopLineTestGtrHFlag
          INTEGER,
        hwLoopLineTestBtrH
          Integer32,
        hwLoopLineTestBtrHFlag
          INTEGER,
        hwLoopLineTestABDcCurrent
          Integer32,
        hwLoopLineTestABDcCurrentFlag
          INTEGER,
        hwLoopLineTestBADcCurrent
          Integer32,
        hwLoopLineTestBADcCurrentFlag
          INTEGER,
        hwLoopLineTestABAcCurrent
          Integer32,
        hwLoopLineTestABAcCurrentFlag
          INTEGER,
        hwLoopLineTestBAAcCurrent
          Integer32,
        hwLoopLineTestBAAcCurrentFlag
          INTEGER,
        hwLoopLineTestCSfrequencyForTest       
          Integer32,
        hwLoopLineTestCSfrequencyForTestFlag    
          INTEGER,  
        hwLoopLineTestImpedanceForTest 
          Integer32,
        hwLoopLineTestImpedanceForTestFlag         
          INTEGER,  
        hwLoopLineTestMaxVForSignature    
          Integer32,
        hwLoopLineTestMaxVForSignatureFlag
          INTEGER,  
        hwLoopLineTestAGMaxVForTest     
          Integer32,
        hwLoopLineTestAGMaxVForTestFlag  
          INTEGER,  
        hwLoopLineTestAGMinVForTest         
          Integer32,
        hwLoopLineTestAGMinVForTestFlag     
          INTEGER,  
        hwLoopLineTestBGMaxVForTest         
          Integer32,
        hwLoopLineTestBGMaxVForTestFlag     
          INTEGER,  
        hwLoopLineTestBGMinVForTest         
          Integer32,
        hwLoopLineTestBGMinVForTestFlag     
          INTEGER,  
        hwLoopLineTestABMaxVForTest
          Integer32,
        hwLoopLineTestABMaxVForTestFlag
          INTEGER,  
        hwLoopLineTestABMinVForTest
          Integer32,
        hwLoopLineTestABMinVForTestFlag
          INTEGER,  
        hwLoopLineTestAGMaxCForTest
          Integer32,
        hwLoopLineTestAGMaxCForTestFlag
          INTEGER,  
        hwLoopLineTestAGMinCForTest
          Integer32,
        hwLoopLineTestAGMinCForTestFlag
          INTEGER,  
        hwLoopLineTestBGMaxCForTest
          Integer32,
        hwLoopLineTestBGMaxCForTestFlag
          INTEGER,  
        hwLoopLineTestBGMinCForTest
          Integer32,
        hwLoopLineTestBGMinCForTestFlag
          INTEGER,  
        hwLoopLineTestABMaxCForTest
          Integer32,
        hwLoopLineTestABMaxCForTestFlag
          INTEGER,  
        hwLoopLineTestABMaxNegCForTest
          Integer32,
        hwLoopLineTestABMaxNegCForTestFlag
          INTEGER ,
        hwLoopLineTestLineALength 
          Integer32,
        hwLoopLineTestLineBLength   
          Integer32,  
        hwLoopLineTestTermimalConcusion
          INTEGER ,
        hwLoopLineTestMoreDataFlag
          INTEGER,
        hwLoopLineTestCtrLV
          Integer32,
        hwLoopLineTestCtrLVFlag
          INTEGER,
        hwLoopLineTestCtrHV
          Integer32,
        hwLoopLineTestCtrHVFlag
          INTEGER,
        hwLoopLineTestCtrAc
          Integer32,
        hwLoopLineTestCtrAcFlag
          INTEGER,
        hwLoopLineTestRtgSer
          Integer32,
        hwLoopLineTestRtgSerFlag
          INTEGER,
        hwLoopLineTestRrgSer
          Integer32,
        hwLoopLineTestRrgSerFlag
          INTEGER,
        hwLoopLineTestRtrSer
          Integer32,
        hwLoopLineTestRtrSerFlag
          INTEGER,
        hwLoopLineTestUtgAcAdmit
          Integer32,
        hwLoopLineTestUtgAcAdmitFlag
          INTEGER,
        hwLoopLineTestUrgAcAdmit
          Integer32,
        hwLoopLineTestUrgAcAdmitFlag
          INTEGER,
        hwLoopLineTestUtrAcAdmit
          Integer32,
        hwLoopLineTestUtrAcAdmitFlag
          INTEGER,
        hwLoopLineTestCapterminal
          INTEGER,  
        hwLoopLineTestCapterminalFlag
          INTEGER
       }
  
    hwLoopLineTestOprType OBJECT-TYPE
      SYNTAX INTEGER
        {
        stop(1),
        start(2),        
        invalid(-1),
	prohibit(3),
        allow(4)
        }
      MAX-ACCESS read-create
      STATUS current
      DESCRIPTION
        "MELT operation type
         Options:
         1. stop(1)     -stop a MELT test
         2. start(2)    -start a MELT test        
         3. invalid(-1) -invalid value 
	 4. prohibit(3) -prohibit a MELT test
         5. allow(4)    -allow a MELT test
        "
      ::= { hwLoopLineTestOprEntry 1 }
    
    hwLoopLineTestVoltage OBJECT-TYPE
      SYNTAX INTEGER
        {
        notest(1),
        test(2),
        invalid(-1)
        }
      MAX-ACCESS read-create
      STATUS current
      DESCRIPTION
        "Indicates whether a voltage exists on the line under test. 
         Options:
         1. notest(1)   -the voltage does not exist on the line under test
         2. test(2)     -the voltage exists on the line under test
         3. invalid(-1) -invalid value
         Default: notest(1)
        "
      ::= { hwLoopLineTestOprEntry 2 }
    
    hwLoopLineTestResistance OBJECT-TYPE
      SYNTAX INTEGER
        {
        notest(1),
        test(2),
        invalid(-1)
        }
      MAX-ACCESS read-create
      STATUS current
      DESCRIPTION
        "Indicates whether resistance exists on the line under test. 
         Options:
         1. notest(1)   -resistance does not exist on the line under test
         2. test(2)     -resistance exists on the line under test
         3. invalid(-1) -invalid value
         Default: notest(1)
        "
      ::= { hwLoopLineTestOprEntry 3 }
    
    hwLoopLineTestCapacitance OBJECT-TYPE
      SYNTAX INTEGER
        {
        notest(1),
        test(2),
        invalid(-1)
        }
      MAX-ACCESS read-create
      STATUS current
      DESCRIPTION
        "Indicates whether capacitance exists on the line under test. 
         Options:
         1. notest(1)   -capacitance does not exist on the line under test
         2. test(2)     -capacitance exists on the line under test
         3. invalid(-1) -invalid value
         Default: notest(1)
        "
      ::= { hwLoopLineTestOprEntry 4 }
    
    hwLoopLineTestLoopResistance OBJECT-TYPE
      SYNTAX INTEGER
        {
        notest(1),
        test(2),
        invalid(-1)
        }
      MAX-ACCESS read-create
      STATUS current
      DESCRIPTION
        "Indicates whether loop resistance exists on the line under test. 
         Options:
         1. notest(1)   -loop resistance does not exist on the line under test
         2. test(2)     -loop resistance exists on the line under test
         3. invalid(-1) -invalid value
         Default: notest(1)
        "
      ::= { hwLoopLineTestOprEntry 5 }
    
    hwLoopLineTestPoleResistance OBJECT-TYPE
      SYNTAX INTEGER
        {
        notest(1),
        test(2),
        invalid(-1)
        }
      MAX-ACCESS read-create
      STATUS current
      DESCRIPTION
        "Indicates whether pole resistance exists on the line under test. 
         Options:
         1. notest(1)   -Pole resistance does not exist on the line under test
         2. test(2)     -Pole resistance exists on the line under test
         3. invalid(-1) -invalid value
         Default: notest(1)
        "
      ::= { hwLoopLineTestOprEntry 6 }
    
    hwLoopLineTestBusyProcFlag OBJECT-TYPE
      SYNTAX INTEGER
        {
        busyNoTest(1),
        busyTest(2),
        busystrenTest(3),
        deferredTest(4),
        invalid(-1)
        }
      MAX-ACCESS read-create
      STATUS current
      DESCRIPTION
        "Identify whether to start a test when the line is busy. The system will excecute a corresponding 
         operation according to the configuration that a user specifies, for example, to cancel the test or to force to test.
         Options:
         1. busyNoTest(1)    -perform no test when a port is busy
         2. busyTest(2)      -perform a remedy test when a port is busy
         3. busystrenTest(3) -force to test when a port is busy
         4. deferredTest(4)  -defer a test when a port is busy
         5. invalid(-1)      -invalid value
         Default: busyNoTest(1)
         If the value of this leaf is deferredTest(4), both hwLoopLineTestDeferredTime and 
         hwLoopLineTestTimeoutProc must be set.
        "
      ::= { hwLoopLineTestOprEntry 7 }
    
    hwLoopLineTestStatus OBJECT-TYPE
      SYNTAX INTEGER
        {
        normal(1),
        testFail(2),
        portBusy(3),
        testOutOfTime(4),
        testingAbnormal(5),
        broadbandtesting(6),
        capturefail(7),
        notratb(8),
        testcanceled(9),
        invalid(-1),
        testNotSupport(10),
        meltChipFaulty(11),
	meltChipCheckInProcess(12),
	prohibitmelt(13)
        }
      MAX-ACCESS read-only
      STATUS current
      DESCRIPTION
        "Indicates the result of MELT test. 
         Options:
         1. normal(1)            -the MELT test is successful
         2. testFail(2)          -the MELT test fails
         3. portBusy(3)          -the MELT test port is busy
         4. testOutOfTime(4)     -the MELT test times out
         5. testingAbnormal(5)   -the MELT test is abnormal
         6. broadbandtesting(6)  -the MELT test is broadbandtesting
         7. capturefail(7)       -the MELT test fails to capture
         8. notratb(8)           -the relay transfer board of the MELT test does not exist
         9. testcanceled(9)      -the MELT test is canceled
         10. invalid(-1)         -invalid value
         11. testNotSupport(10)  -the MELT test is not support
         12. meltChipFaulty(11)  -the MELT chip is faulty
	 13. meltChipCheckInProcess(12)-the MELT chip status check is in process
	 14. prohibitmelt(13)    -the MELT test is prohibited
        "
      ::= { hwLoopLineTestOprEntry 8 }
    
    hwLoopLineTestConclusion OBJECT-TYPE
      SYNTAX INTEGER
        {
        normal(1),
        meetLine(2),
        aLineMix(3),
        bLineMix(4),
        doubleMix(5),
        aLineEarth(6),
        bLineEarth(7),
        doublelineearth(8),
        selfMix(9),
        abLine(10),
        aLineFree(11),
        bLineEarthFree(12),
        doubleLineEarthFree(13),
        abLineFree(14),
        killLine(15),
        noPutDownTele(16),
        unknow(17),
        selfMixinMDF(18),
        selfMixoutMDF(19),
        cutLineinMDF(20),
        cutLineoutMDF(21),
        dCvoltagePowerFeed(30),
        aCvoltageRinging(31),
        dCvoltageOffhook(32),
        dCvoltage(33),
        aCvoltage(34),
        abImpedance(35),
        baImpedance(36),
        agImpedance(37),
        bgImpedance(38),
        agACCurrent(39),
        bgACCurrent(41),
        abACCurrent(42),
        agDCCurrent(43),
        bgDCCurrent(44),
        abDCCurrent(45),
        loopCurrent(46),
        noise(47),
        abRFaultId(91),
        aRFaultId(92),
        bRFaultId(93),
        abLeakId(94),
        aLeakId(95),
        bLeakId(96),
        abFvacLevelH(97),
        aFvacLevelH(98),
        bFvacLevelH(99),
        abFvacLevelI(100),
        aFvacLevelI(101),
        bFvacLevelI(102),
        abFvacLevelO(103),
        aFvacLevelO(104),
        bFvacLevelO(105),
        abFvDcLevelH(106),
        aFvDcLevelH(107),
        bFvDcLevelH(108),
        abFvDcLevelI(109),
        aFvDcLevelI(110),
        bFvDcLevelI(111),
        abFvDcLevelO(112),
        aFvDcLevelO(113),
        bFvDcLevelO(114),
        fesIdPPA(115),
        fesIdPPAInv(116),
        fesId2PPA(117),
        fesId2PPAInv(118),
        etsiXdslSignature(119),
        fetIdEr(120), 
        abreak(121),
        bbreak(122),
        abreakInMDF(123), 
        bbreakInMDF(124),
        abreakOutMDF(125),
        bbreakOutMDF(126),
        invalid(-1)         
        }                         
      MAX-ACCESS read-only
      STATUS current
      DESCRIPTION
        "MELT test conclusion, this object is for pots and combo board's port.
         Options: 
         1. normal(1)                   -the test conclusion is normal
         2. meetLine(2)                 -the test conclusion is meetLine
         3. aLineMix(3)                 -the test conclusion is aLineMix
         4. bLineMix(4)                 -the test conclusion is bLineMix
         5. doubleMix(5)                -the test conclusion is doubleMix
         6. aLineEarth(6)               -the test conclusion is aLineEarth
         7. bLineEarth(7)               -the test conclusion is bLineEarth
         8. doublelineearth(8)          -the test conclusion is doublelineearth
         9. selfMix(9)                  -the test conclusion is selfMix
         10. abLine(10)                 -the test conclusion is abLine
         11. aLineFree(11)              -the test conclusion is aLineFree
         12. bLineEarthFree(12)         -the test conclusion is bLineEarthFree
         13. doubleLineEarthFree(13)    -the test conclusion is doubleLineEarthFree
         14. abLineFree(14)             -the test conclusion is abLineFree
         15. killLine(15)               -the test conclusion is killLine
         16. noPutDownTele(16)          -the test conclusion is noPutDownTele
         17. unknow(17)                 -the test conclusion is unknow
         18. selfMixinMDF(18)           -the test conclusion is selfMixinMDF
         19. selfMixoutMDF(19)          -the test conclusion is selfMixoutMDF
         20. cutLineinMDF(20)           -the test conclusion is cutLineinMDF
         21. cutLineoutMDF(21)          -the test conclusion is cutLineoutMDF
         22. dCvoltagePowerFeed(30)     -the test conclusion is dCvoltagePowerFeed
         23. aCvoltageRinging(31)       -the test conclusion is aCvoltageRinging
         24. dCvoltageOffhook(32)       -the test conclusion is dCvoltageOffhook
         25. dCvoltage(33)              -the test conclusion is dCvoltage
         26. aCvoltage(34)              -the test conclusion is aCvoltage
         27. abImpedance(35)            -the test conclusion is abImpedance
         28. baImpedance(36)            -the test conclusion is baImpedance
         29. agImpedance(37)            -the test conclusion is agImpedance
         30. bgImpedance(38)            -the test conclusion is bgImpedance
         31. agACCurrent(39)            -the test conclusion is agACCurrent
         32. bgACCurrent(41)            -the test conclusion is bgACCurrent
         33. abACCurrent(42)            -the test conclusion is abACCurrent
         34. agDCCurrent(43)            -the test conclusion is agDCCurrent
         35. bgDCCurrent(44)            -the test conclusion is bgDCCurrent
         36. abDCCurrent(45)            -the test conclusion is abDCCurrent
         37. loopCurrent(46)            -the test conclusion is loopCurrent
         38. noise(47)                  -the test conclusion is noise
         39. abRFaultId(91)             -the test conslusion is ab Line all fault                                                                                                                                      
         40. aRFaultId(92)              -the test conslusion is a Line fault                                                                                                                                
         41. bRFaultId(93)              -the test conslusion is b Line fault                                                                                                                                         
         42. abLeakId(94)               -the test conslusion is ab Line all leak                                                                                                                                 
         43. aLeakId(95)                -the test conslusion is a Line leak                                                                                                                                     
         44. bLeakId(96)                -the test conslusion is b line leak                                                                                                                                     
         45. abFvacLevelH(97)           -the test conslusion is ab dangerous AC to ground                                                                                                                      
         46. aFvacLevelH(98)            -the test conslusion is a dangerous AC to ground                                                                                                                       
         47. bFvacLevelH(99)            -the test conslusion is b dangerous AC to ground                                                                                                                       
         48. abFvacLevelI(100)          -the test conslusion is ab EMF AC to ground                                                                                                                       
         49. aFvacLevelI(101)           -the test conslusion is a EMF AC to ground                                                                                                                        
         50. bFvacLevelI(102)           -the test conslusion is b EMF AC to ground                                                                                                                         
         51. abFvacLevelO(103)          -the test conslusion is ab other dangerous AC to ground                                                                                                                 
         52. aFvacLevelO(104)           -the test conslusion is a other dangerous AC to ground                                                                                                                     
         53. bFvacLevelO(105)           -the test conslusion is b other dangerous AC to ground                                                                                                                   
         54. abFvDcLevelH(106)          -the test conslusion is ab dangerous DC to ground                                                                                                                     
         55. aFvDcLevelH(107)           -the test conslusion is a dangerous DC to ground                                                                                                                        
         56. bFvDcLevelH(108)           -the test conslusion is b dangerous DC to ground                                                                                                                        
         57. abFvDcLevelI(109)          -the test conslusion is ab EMF DC to ground                                                                                                                      
         58. aFvDcLevelI(110)           -the test conslusion is a EMF DC to ground                                                                                                                       
         59. bFvDcLevelI(111)           -the test conslusion is b EMF DC to ground                                                                                                                      
         60. abFvDcLevelO(112)          -the test conslusion is ab other dangerous DC to ground                                                                                                                  
         61. aFvDcLevelO(113)           -the test conslusion is a other dangerous DC to ground                                                                                                                  
         62. bFvDcLevelO(114)           -the test conslusion is b other dangerous DC to ground                                                                                                                  
         63. fesIdPPA(115)              -the test conslusion is ab PPA                                                                                                                                   
         64. fesIdPPAInv(116)           -the test conslusion is ab reverse PPA                                                                                                                                  
         65. fesId2PPA(117)             -the test conslusion is ab two PPA                                                                                                                           
         66. fesId2PPAInv(118)          -the test conslusion is ab two reverse PPA                                                                                                                           
         67. etsiXdslSignature(119)     -the test conslusion is ETSI XDSL Signature                                           
         68. fetIdEr(120)               -the test conslusion is exist electronic ring terminal 
         69. abreak(121)                -the test conslusion is a line break
         70. bbreak(122)                -the test conslusion is b line break 
         71. abreakInMDF(123)           -the test conslusion is a line break InMDF 
         72. bbreakInMDF(124)           -the test conslusion is b line break InMDF
         73. abreakOutMDF(125)          -the test conslusion is a line break OutMDF
         74. bbreakOutMDF(126)          -the test conslusion is b line break OutMDF
         75. invalid(-1)                -the test conclusion is invalid
        "
        
      ::= { hwLoopLineTestOprEntry 9 }
    
    hwLoopLineTestACAG OBJECT-TYPE
      SYNTAX Integer32
      MAX-ACCESS read-only
      STATUS current
      DESCRIPTION
        "Indicates the A->ground AC voltage. 
         Unit: mV
        "
      ::= { hwLoopLineTestOprEntry 10 }
    
    hwLoopLineTestACBG OBJECT-TYPE
      SYNTAX Integer32
      MAX-ACCESS read-only
      STATUS current
      DESCRIPTION
        "Indicates the B->ground AC voltage. 
         Unit: mV
        "
      ::= { hwLoopLineTestOprEntry 11 }
    
    hwLoopLineTestACAB OBJECT-TYPE
      SYNTAX Integer32
      MAX-ACCESS read-only
      STATUS current
      DESCRIPTION
        "Indicates the A->B AC voltage. 
         Unit: mV
        " 
      ::= { hwLoopLineTestOprEntry 12 }
    
    hwLoopLineTestDCAG OBJECT-TYPE
      SYNTAX Integer32
      MAX-ACCESS read-only
      STATUS current
      DESCRIPTION
        "Indicates the A->ground DC voltage. 
         Unit: mV
        " 
      ::= { hwLoopLineTestOprEntry 13 }
    
    hwLoopLineTestDCBG OBJECT-TYPE
      SYNTAX Integer32
      MAX-ACCESS read-only
      STATUS current
      DESCRIPTION
        "Indicates the B->ground DC voltage. 
         Unit: mV
        " 
      ::= { hwLoopLineTestOprEntry 14 }
    
    hwLoopLineTestDCAB OBJECT-TYPE
      SYNTAX Integer32
      MAX-ACCESS read-only
      STATUS current
      DESCRIPTION
        "Indicates the A->B DC voltage. 
         Unit: mV
        " 
      ::= { hwLoopLineTestOprEntry 15 }
    
    hwLoopLineTestRAG OBJECT-TYPE
      SYNTAX Integer32
      MAX-ACCESS read-only
      STATUS current
      DESCRIPTION
        "Indicates the A->ground insulation resistance. 
         Unit: ohm
        " 
      ::= { hwLoopLineTestOprEntry 16 }
    
    hwLoopLineTestRBG OBJECT-TYPE
      SYNTAX Integer32
      MAX-ACCESS read-only
      STATUS current
      DESCRIPTION
        "Indicates the B->ground insulation resistance. 
         Unit: ohm
        " 
      ::= { hwLoopLineTestOprEntry 17 }
    
    hwLoopLineTestRAB OBJECT-TYPE
      SYNTAX Integer32
      MAX-ACCESS read-only
      STATUS current
      DESCRIPTION
        "Indicates the A->B insulation resistance. 
         Unit: ohm
        " 
      ::= { hwLoopLineTestOprEntry 18 }
    
    hwLoopLineTestCapAG OBJECT-TYPE
      SYNTAX Integer32
      MAX-ACCESS read-only
      STATUS current
      DESCRIPTION
        "Indicates the A->ground capacitance. 
         Unit: nF
        " 
      ::= { hwLoopLineTestOprEntry 19 }
    
    hwLoopLineTestCapBG OBJECT-TYPE
      SYNTAX Integer32
      MAX-ACCESS read-only
      STATUS current
      DESCRIPTION
        "Indicates the B->ground capacitance. 
         Unit: nF
        " 
      ::= { hwLoopLineTestOprEntry 20 }
    
    hwLoopLineTestCapAB OBJECT-TYPE
      SYNTAX Integer32
      MAX-ACCESS read-only
      STATUS current
      DESCRIPTION
        "Indicates the A->B capacitance. 
         Unit: nF
        " 
      ::= { hwLoopLineTestOprEntry 21 }
    
    hwLoopLineTestLR OBJECT-TYPE
      SYNTAX Integer32
      MAX-ACCESS read-only
      STATUS current
      DESCRIPTION
        "Indicates the loop resistance. 
         Unit: ohm
        " 
      ::= { hwLoopLineTestOprEntry 22 }
    
    hwLoopLineTestRABResPole OBJECT-TYPE
      SYNTAX Integer32
      MAX-ACCESS read-only
      STATUS current
      DESCRIPTION
        "Indicates the A->B polarity reversal resistance. 
         Unit: ohm
        " 
      ::= { hwLoopLineTestOprEntry 23 }
    
    hwLoopLineTestMSocket OBJECT-TYPE
      SYNTAX INTEGER
        {
        notconnected(1),
        connected(2),
        aBReversed(3)
        }
      MAX-ACCESS read-only
      STATUS current
      DESCRIPTION
        "Indicates the M-socket connection. 
         Options:
         1. notconnected(1) -the M-socket is not connected 
         2. connected(2)    -the M-socket is connected
         3. aBReversed(3)   -the wire A and wire B are reversed
        "
      ::= { hwLoopLineTestOprEntry 24 }
    
    hwLoopLineTestBtssPowerProcFlag OBJECT-TYPE
      SYNTAX INTEGER
        {
        noTest(1),
        test(2),
        invalid(-1)
        }
      MAX-ACCESS read-create
      STATUS current
      DESCRIPTION
        "Loop line test-BTSS line with power processing.
         Options:
         1. noTest(1)     -not test
         2. test(2)       -test
         3. invalid(-1)    -invalid value
        "

      ::= { hwLoopLineTestOprEntry 25 }
    
    
    hwLoopLineTestImpedance OBJECT-TYPE
      SYNTAX INTEGER
        {
        notest(1),
        test(2)
        }
      MAX-ACCESS read-create
      STATUS current
      DESCRIPTION
        "Loop line test-impedance.
         Options:
         1. notest(1)     -not test
         2. test(2)       -test
        "
      ::= { hwLoopLineTestOprEntry 26 }
    
    hwLoopLineTestImpedanceAB OBJECT-TYPE
      SYNTAX Integer32
      MAX-ACCESS read-only
      STATUS current
      DESCRIPTION
        "A->B impedance (unit: ohm)
        "
      ::= { hwLoopLineTestOprEntry 27 }
      
    hwLoopLineTestImpedanceBA OBJECT-TYPE
      SYNTAX Integer32
      MAX-ACCESS read-only
      STATUS current
      DESCRIPTION
        "B->A impedance (unit: ohm)
        "
      ::= { hwLoopLineTestOprEntry 28 }
      
    hwLoopLineTestImpedanceAG OBJECT-TYPE
      SYNTAX Integer32
      MAX-ACCESS read-only
      STATUS current
      DESCRIPTION
        "A->ground impedance (unit: ohm)
        "
      ::= { hwLoopLineTestOprEntry 29 }
  
    hwLoopLineTestImpedanceBG OBJECT-TYPE
      SYNTAX Integer32
      MAX-ACCESS read-only
      STATUS current
      DESCRIPTION
        "B->ground impedance (unit: ohm)
        "
      ::= { hwLoopLineTestOprEntry 30 }
  
  
    hwLoopLineTestCurrent OBJECT-TYPE
      SYNTAX INTEGER
        {
        notest(1),
        test(2)
        }
      MAX-ACCESS read-create
      STATUS current
      DESCRIPTION
        "Loop line test-current.
         Options:
         1. notest(1)     -not test
         2. test(2)       -test
        "
      ::= { hwLoopLineTestOprEntry 31 }
    
    hwLoopLineTestACCurrentAG OBJECT-TYPE
      SYNTAX Integer32
      MAX-ACCESS read-only
      STATUS current
      DESCRIPTION
        "A->ground AC current (unit: mA)
        "
      ::= { hwLoopLineTestOprEntry 32 }
      
    hwLoopLineTestACCurrentBG OBJECT-TYPE
      SYNTAX Integer32
      MAX-ACCESS read-only
      STATUS current
      DESCRIPTION
        "B->ground AC current (unit: mA)
        "
      ::= { hwLoopLineTestOprEntry 33 }
  
    hwLoopLineTestACCurrentAB OBJECT-TYPE
      SYNTAX Integer32
      MAX-ACCESS read-only
      STATUS current
      DESCRIPTION
        "AB AC current (unit: mA)
        "
      ::= { hwLoopLineTestOprEntry 34 }
  
    hwLoopLineTestDCCurrentAG OBJECT-TYPE
      SYNTAX Integer32
      MAX-ACCESS read-only
      STATUS current
      DESCRIPTION
        "A->ground DC current (unit: mA)
        "
      ::= { hwLoopLineTestOprEntry 35 }
      
    hwLoopLineTestDCCurrentBG OBJECT-TYPE
      SYNTAX Integer32
      MAX-ACCESS read-only
      STATUS current
      DESCRIPTION
        "B->ground DC current (unit: mA)
        "
      ::= { hwLoopLineTestOprEntry 36 }
  
    hwLoopLineTestDCCurrentAB OBJECT-TYPE
      SYNTAX Integer32
      MAX-ACCESS read-only
      STATUS current
      DESCRIPTION
        "AB DC current (unit: mA)
        "
      ::= { hwLoopLineTestOprEntry 37 }
      
    hwLoopLineTestLoopCurrent OBJECT-TYPE
      SYNTAX INTEGER
        {
        notest(1),
        test(2)
        }
      MAX-ACCESS read-create
      STATUS current
      DESCRIPTION
        "Loop line test-loop current.
         Options:
         1. notest(1)     -not test
         2. test(2)       -test
        "
      ::= { hwLoopLineTestOprEntry 38 }
    
    hwLoopLineTestLC OBJECT-TYPE
      SYNTAX Integer32
      MAX-ACCESS read-only
      STATUS current
      DESCRIPTION
        "Loop current (unit: uA)
        "
      ::= { hwLoopLineTestOprEntry 39 }
  
    hwLoopLineTestNoise OBJECT-TYPE
      SYNTAX INTEGER
        {
        notest(1),
        test(2)
        }
      MAX-ACCESS read-create
      STATUS current
      DESCRIPTION
        "Loop line test-noise.
         Options:
         1. notest(1)     -not test
         2. test(2)       -test
        "
      ::= { hwLoopLineTestOprEntry 40 }
    
    hwLoopLineTestN OBJECT-TYPE
      SYNTAX Integer32
      MAX-ACCESS read-only
      STATUS current
      DESCRIPTION
        "Noise (unit: dBm)
        "
      ::= { hwLoopLineTestOprEntry 41 }
      
    hwLoopLineTestPPA OBJECT-TYPE
      SYNTAX INTEGER
        {
        notest(1),
        test(2),
        invalid(-1)
        }
      MAX-ACCESS read-create
      STATUS current
      DESCRIPTION
        "Indicates whether PPA exists on the line under test. 
         Options:
         1. notest(1)   -PPA does not exist on the line under test
         2. test(2)     -PPA exists on the line under test
         3. invalid(-1) -invalid value
         Default: notest(1)
        "
      ::= { hwLoopLineTestOprEntry 42 }
      
    hwLoopLineTestPPAResult OBJECT-TYPE
      SYNTAX INTEGER
        {
        noexist(1),
        exist(2),
        inverseexist(3),
        invalid(-1)
        }
      MAX-ACCESS read-only
      STATUS current
      DESCRIPTION
        "Indicates whether the PPA exists. 
         Options:
         1. noexist(1)       -PPA does not exist 
         2. exist(2)         -PPA exists
         3. inverseexist(3)  -PPA inverse exists
         4. invalid(-1)      -invalid value
        "
      ::= { hwLoopLineTestOprEntry 43 }

    hwLoopLineTestDeferredTime OBJECT-TYPE
      SYNTAX      Integer32(-1 | 1..1440)
      MAX-ACCESS  read-create
      STATUS      current
      DESCRIPTION
        "Indicates the deferred time.
         Unit: minute
         This leaf is valid only when the value of hwLoopLineTestBusyProcFlag is DeferredTest(4).
         Default: 30
        "
      DEFVAL { 30 }
      ::= { hwLoopLineTestOprEntry 44 }
      
    hwLoopLineTestTimeoutProc OBJECT-TYPE
      SYNTAX INTEGER
        {
        notest(1),
        test(2),
        invalid(-1)
        }
      MAX-ACCESS read-create
      STATUS current
      DESCRIPTION
        "Indicates the timeout processing.
         Options:
         1. notest(1)    -if the deferred time times out and the port is still busy
                          the test will be canceled
         2. test(2)      -if the deferred time times out and the port is still busy
                          the test will be forcedly started                                       
         3. invalid(-1)  -invalid value
         This leaf is valid only when the value of hwLoopLineTestBusyProcFlag is DeferredTest(4).
        "
      DEFVAL { 1 }
      ::= { hwLoopLineTestOprEntry 45 }

    hwLoopLineTestReverse OBJECT-TYPE
      SYNTAX Integer32
      MAX-ACCESS read-create
      STATUS current
      DESCRIPTION
        "Reverse flag (0:normal test 1:reverse test)
        "
      ::= { hwLoopLineTestOprEntry 46 }     
      
    hwLoopLineTestUtgAcFreq OBJECT-TYPE
      SYNTAX Integer32
      MAX-ACCESS read-only
      STATUS current
      DESCRIPTION
        "Frequency of foreign AC voltage source coupled to tip via Zbat_tip impedance. 
         Unit: Hz
        "
      ::= { hwLoopLineTestOprEntry 47 }

    hwLoopLineTestUrgAcFreq OBJECT-TYPE
      SYNTAX Integer32
      MAX-ACCESS read-only
      STATUS current
      DESCRIPTION
        "Frequency of foreign AC voltage source coupled to ring via Zbat_ring impedance.
         Unit:Hz
        "
      ::= { hwLoopLineTestOprEntry 48 }

    hwLoopLineTestUtrAcFreq OBJECT-TYPE
      SYNTAX Integer32
      MAX-ACCESS read-only
      STATUS current
      DESCRIPTION
        "Frequency of foreign AC voltage source coupled to tip-ring via Zbat_tipring impedance.
         Unit:Hz
        "
      ::= { hwLoopLineTestOprEntry 49 }

    hwLoopLineTestItipAc OBJECT-TYPE
      SYNTAX Integer32
      MAX-ACCESS read-only
      STATUS current
      DESCRIPTION
        "AC foreign current on the tip wire.
         Unit:uA
        "
      ::= { hwLoopLineTestOprEntry 50 }

    hwLoopLineTestIringAc OBJECT-TYPE
      SYNTAX Integer32
      MAX-ACCESS read-only
      STATUS current
      DESCRIPTION
        "AC foreign current on the ring wire.
         Unit:uA
        "
      ::= { hwLoopLineTestOprEntry 51 }

    hwLoopLineTestItipDc OBJECT-TYPE
      SYNTAX Integer32
      MAX-ACCESS read-only
      STATUS current
      DESCRIPTION
        "DC foreign current on the tip wire.
         Unit:uA
        "
      ::= { hwLoopLineTestOprEntry 52 }
      
    hwLoopLineTestIringDc OBJECT-TYPE
      SYNTAX Integer32
      MAX-ACCESS read-only
      STATUS current
      DESCRIPTION
        "DC foreign current on the ring wire.
         Unit:uA
        "
      ::= { hwLoopLineTestOprEntry 53 }     

    hwLoopLineTestRbattip OBJECT-TYPE
      SYNTAX Integer32
      MAX-ACCESS read-only
      STATUS current
      DESCRIPTION
        "In presence of a foreign voltage, the equivalent coupling resistance of wire A.
         Unit:ohm 
        "
      ::= { hwLoopLineTestOprEntry 54 }   

    hwLoopLineTestRbatring OBJECT-TYPE
      SYNTAX Integer32
      MAX-ACCESS read-only
      STATUS current
      DESCRIPTION
        "In presence of a foreign voltage, the equivalent coupling resistance of wire B.
         Unit:ohm 
        "
      ::= { hwLoopLineTestOprEntry 55 }   
      
    hwLoopLineTestRring OBJECT-TYPE
      SYNTAX Integer32
      MAX-ACCESS read-only
      STATUS current
      DESCRIPTION
        "Resistance in series with the ring capacitance, for example
         when a ringer load or a passive R-C signature terminates the loop. 
         It also includes the cable resistance R line but it does not include 
         the 24 kohm feeding resistance.
         Unit: ohm
        "
      ::= { hwLoopLineTestOprEntry 56 }   

    hwLoopLineTestCsig OBJECT-TYPE
      SYNTAX Integer32
      MAX-ACCESS read-only
      STATUS current
      DESCRIPTION
        "Capacitance of an xDSL signal.
         Unit: nF
        "
      ::= { hwLoopLineTestOprEntry 57 }   

    hwLoopLineTestVzener OBJECT-TYPE
      SYNTAX Integer32
      MAX-ACCESS read-only
      STATUS current
      DESCRIPTION
        "Zener diode threshold in the case of an off-hook phone.
         Unit: mV
        "
      ::= { hwLoopLineTestOprEntry 58 }   

    hwLoopLineTestRzener OBJECT-TYPE
      SYNTAX Integer32
      MAX-ACCESS read-only
      STATUS current
      DESCRIPTION
        "DC tip-ring resistance measured in the case of an off-hook phone.
         Unit: ohm
        "
      ::= { hwLoopLineTestOprEntry 59 }   

    hwLoopLineTestGtg OBJECT-TYPE
      SYNTAX Integer32
      MAX-ACCESS read-only
      STATUS current
      DESCRIPTION
        "Aggregate a->ground conductance.
         Unit: nS
        "
      ::= { hwLoopLineTestOprEntry 60 }   

    hwLoopLineTestBtg OBJECT-TYPE
      SYNTAX Integer32
      MAX-ACCESS read-only
      STATUS current
      DESCRIPTION
        "Aggregate a->ground susceptance.
         Unit: nS
        "
      ::= { hwLoopLineTestOprEntry 61 }   

    hwLoopLineTestGrg OBJECT-TYPE
      SYNTAX Integer32
      MAX-ACCESS read-only
      STATUS current
      DESCRIPTION
        "Aggregate b->ground conductance.
         Unit: nS
        "
      ::= { hwLoopLineTestOprEntry 62 }   

    hwLoopLineTestBrg OBJECT-TYPE
      SYNTAX Integer32
      MAX-ACCESS read-only
      STATUS current
      DESCRIPTION
        "Aggregate b->ground susceptance.
         Unit: nS
        "
      ::= { hwLoopLineTestOprEntry 63 }   

    hwLoopLineTestGtr OBJECT-TYPE
      SYNTAX Integer32
      MAX-ACCESS read-only
      STATUS current
      DESCRIPTION
        "Aggregate a->b conductance.
         Unit: nS
        "
      ::= { hwLoopLineTestOprEntry 64 }   

    hwLoopLineTestBtr OBJECT-TYPE
      SYNTAX Integer32
      MAX-ACCESS read-only
      STATUS current
      DESCRIPTION
        "Aggregate a->b susceptance.
         Unit: nS
        "
      ::= { hwLoopLineTestOprEntry 65 }   

    hwLoopLineTestSIGN OBJECT-TYPE
      SYNTAX TruthValue
      MAX-ACCESS read-only
      STATUS current
      DESCRIPTION
        "Indicates the ETSI xDSL Signature is detected or not.
        "
      ::= { hwLoopLineTestOprEntry 66 }   

    hwLoopLineTestACFEM OBJECT-TYPE
      SYNTAX TruthValue
      MAX-ACCESS read-only
      STATUS current
      DESCRIPTION
        "Indicates the presence of an AC foreign voltage above the threshold defined by ACFEMmin. 
         By reading the results of the foreign voltage test, it is possible to determine 
         whether the foreign electromotive force source has been coupled to tip, ring or 
         differentially between tip-ring.
        "
      ::= { hwLoopLineTestOprEntry 67 }   

    hwLoopLineTestDCFEM OBJECT-TYPE
      SYNTAX TruthValue
      MAX-ACCESS read-only
      STATUS current
      DESCRIPTION
        "Indicates the presence of a DC foreign voltage above the threshold defined 
         by DCFEMmin. By reading the results of the foreign voltage test, 
         it is possible to determine whether the foreign electromotive
         force source has been coupled to tip, ring or differentially between tip-ring.
        "
      ::= { hwLoopLineTestOprEntry 68 }   

    hwLoopLineTestONHK OBJECT-TYPE
      SYNTAX TruthValue
      MAX-ACCESS read-only
      STATUS current
      DESCRIPTION
        "Indicates the presens of a phone in the on-hook state.
        "
      ::= { hwLoopLineTestOprEntry 69 }   

    hwLoopLineTestOPEN OBJECT-TYPE
      SYNTAX TruthValue
      MAX-ACCESS read-only
      STATUS current
      DESCRIPTION
        "Indicates a->b resistance exceeds the threshold.
        "
      ::= { hwLoopLineTestOprEntry 70 }   

    hwLoopLineTestSHORT OBJECT-TYPE
      SYNTAX TruthValue
      MAX-ACCESS read-only
      STATUS current
      DESCRIPTION
        "Indicates that the insulation resistance is small.
        "
      ::= { hwLoopLineTestOprEntry 71 }   

    hwLoopLineTestROH OBJECT-TYPE
      SYNTAX TruthValue
      MAX-ACCESS read-only
      STATUS current
      DESCRIPTION
        "Indicates a phone in the off-hook state. 
        "
      ::= { hwLoopLineTestOprEntry 72 }   

    hwLoopLineTestUtgDcUp OBJECT-TYPE
      SYNTAX Integer32
      MAX-ACCESS read-only
      STATUS current
      DESCRIPTION
        "Indicates the a->ground highest measurement DC voltage.
         Unit: mV
        "
      ::= { hwLoopLineTestOprEntry 73 }   

    hwLoopLineTestUtgDcDown OBJECT-TYPE
      SYNTAX Integer32
      MAX-ACCESS read-only
      STATUS current
      DESCRIPTION
        "Indicates the a->ground lowest measurement DC voltage.
         Unit: mV
        "
      ::= { hwLoopLineTestOprEntry 74 }   

    hwLoopLineTestUrgDcUp OBJECT-TYPE
      SYNTAX Integer32
      MAX-ACCESS read-only
      STATUS current
      DESCRIPTION
        "Indicates the b->ground highest measurement DC voltage.
         Unit: mV
        "
      ::= { hwLoopLineTestOprEntry 75 }   

    hwLoopLineTestUrgDcDown OBJECT-TYPE
      SYNTAX Integer32
      MAX-ACCESS read-only
      STATUS current
      DESCRIPTION
        "Indicates the b->ground lowest measurement DC voltage.
         Unit: mV
        "
      ::= { hwLoopLineTestOprEntry 76 }   

    hwLoopLineTestUtrPos OBJECT-TYPE
      SYNTAX Integer32
      MAX-ACCESS read-only
      STATUS current
      DESCRIPTION
        "Indicates the a->b positive measurement DC voltage.
         Unit: mV
        "
      ::= { hwLoopLineTestOprEntry 77 }   

    hwLoopLineTestUtrNeg OBJECT-TYPE
      SYNTAX Integer32
      MAX-ACCESS read-only
      STATUS current
      DESCRIPTION
        "Indicates the b->a measurement DC voltage.
         Unit: mV
        "
      ::= { hwLoopLineTestOprEntry 78 }   

    hwLoopLineTestItgDcUp OBJECT-TYPE
      SYNTAX Integer32
      MAX-ACCESS read-only
      STATUS current
      DESCRIPTION
        "Indicates the current mapping the A-wire highest voltage for test.
         Unit: uA
        "
      ::= { hwLoopLineTestOprEntry 79 }   

    hwLoopLineTestItgDcDown OBJECT-TYPE
      SYNTAX Integer32
      MAX-ACCESS read-only
      STATUS current
      DESCRIPTION
        "Indicates the current mapping the A-wire lowest voltage for test. 
         Unit: uA
        "
      ::= { hwLoopLineTestOprEntry 80 }   

    hwLoopLineTestIrgDcUp OBJECT-TYPE
      SYNTAX Integer32
      MAX-ACCESS read-only
      STATUS current
      DESCRIPTION
        "Indicates the current mapping the B-wire highest voltage for test. 
         Unit: uA
        "
      ::= { hwLoopLineTestOprEntry 81 }   

    hwLoopLineTestIrgDcDown OBJECT-TYPE
      SYNTAX Integer32
      MAX-ACCESS read-only
      STATUS current
      DESCRIPTION
        "Indicates the current mapping the B-wire lowest voltage for test. 
         Unit: uA
        "
      ::= { hwLoopLineTestOprEntry 82 }   

    hwLoopLineTestItrPos OBJECT-TYPE
      SYNTAX Integer32
      MAX-ACCESS read-only
      STATUS current
      DESCRIPTION
        "Indicates the current mapping the A->B positive voltage for test.
         Unit: uA
        "
      ::= { hwLoopLineTestOprEntry 83 }   

    hwLoopLineTestItrNeg OBJECT-TYPE
      SYNTAX Integer32
      MAX-ACCESS read-only
      STATUS current
      DESCRIPTION
        "Indicates the current mapping the A->B negative voltage for test.
         Unit: uA
        "
      ::= { hwLoopLineTestOprEntry 84 }   

    hwLoopLineTestRinger OBJECT-TYPE
      SYNTAX Integer32
      MAX-ACCESS read-only
      STATUS current
      DESCRIPTION
        "Indicates the detected ringer.
        "
      ::= { hwLoopLineTestOprEntry 85 } 

    hwLoopLineTestPPARes OBJECT-TYPE
      SYNTAX Integer32
      MAX-ACCESS read-only
      STATUS current
      DESCRIPTION
        "Indicates the resistance of PPA.
         Unit: ohm
        "
      ::= { hwLoopLineTestOprEntry 86 } 
            
    hwLoopLineTestStartTime OBJECT-TYPE
      SYNTAX DateAndTime
      MAX-ACCESS read-only
      STATUS current
      DESCRIPTION       
        "Indicates the start time and date of the MELT test.
        "
      ::= { hwLoopLineTestOprEntry 87 } 
      
    hwLoopLineTestEndTime OBJECT-TYPE
      SYNTAX DateAndTime
      MAX-ACCESS read-only
      STATUS current
      DESCRIPTION       
        "Indicates the end time and date of the MELT test.
        "
      ::= { hwLoopLineTestOprEntry 88 }   
    
    hwLoopLineTestOprMeasuredFreq OBJECT-TYPE
      SYNTAX INTEGER
      {
      frequency25Hz(0),
      frequency275Hz(1),
      invalid(-1)
      }
      MAX-ACCESS read-write
      STATUS current
      DESCRIPTION
        "Indicates the measured frequency for complex impedance.
         Options:
         1. frequency25Hz(0)  -25 Hz 
         2. frequency275Hz(1) -275 Hz 
         3. invalid(-1)       -invalid value
         Default: frequency25Hz(0)
        "
        ::= { hwLoopLineTestOprEntry 89 }
                   
    hwLoopLineTestIfIndex OBJECT-TYPE
      SYNTAX Integer32
      MAX-ACCESS read-only
      STATUS current
      DESCRIPTION
        "Port IfIndex."
      ::= { hwLoopLineTestOprEntry 90 }
        
    hwLoopLineTestRequestID OBJECT-TYPE
      SYNTAX Integer32
      MAX-ACCESS read-only
      STATUS current
      DESCRIPTION
        "Request ID.
         The value is the fourth parameter in the trap message.
        "
      ::= { hwLoopLineTestOprEntry 91 }       
                      
    hwLoopLineTestRABPole OBJECT-TYPE
      SYNTAX Integer32
      MAX-ACCESS read-only
      STATUS current
      DESCRIPTION
        "Indicates the A->B polarity resistance. 
         Unit: ohm"
      ::= { hwLoopLineTestOprEntry 92 } 
      
    hwLoopLineTestACAGFlag OBJECT-TYPE
      SYNTAX INTEGER
      {
      valid(1),
      invalid(2),
      notsupport(3)
      }
      MAX-ACCESS read-only
      STATUS current
      DESCRIPTION
        "Indicates whether the value of hwLoopLineTestACAG is valid.
         Options:
         1. valid(1)       -the value of hwLoopLineTestACAG is valid 
         2. invalid(2)     -the value of hwLoopLineTestACAG is invalid
         3. notsupport(3)  -the value of hwLoopLineTestACAG is not support
        "
      ::= { hwLoopLineTestOprEntry 93 } 
                                                                                
    hwLoopLineTestACBGFlag OBJECT-TYPE
      SYNTAX INTEGER
      {
      valid(1),
      invalid(2),
      notsupport(3)
      }
      MAX-ACCESS read-only
      STATUS current
      DESCRIPTION
        "Indicates whether the value of hwLoopLineTestACBG is valid.
         Options:
         1. valid(1)   -the value of hwLoopLineTestACBG is valid 
         2. invalid(2) -the value of hwLoopLineTestACBG is invalid
         3. notsupport(3)  -the value of hwLoopLineTestACBG is not support
        "
        ::= { hwLoopLineTestOprEntry 94 } 
                  
    hwLoopLineTestACABFlag OBJECT-TYPE
      SYNTAX INTEGER
      {
        valid(1),
        invalid(2),
        notsupport(3)
      }
      MAX-ACCESS read-only
      STATUS current
      DESCRIPTION
        "Indicates whether the value of hwLoopLineTestACAB is valid.
         Options:
         1. valid(1)       -the value of hwLoopLineTestACAB is valid 
         2. invalid(2)     -the value of hwLoopLineTestACAB is invalid
         3. notsupport(3)  -the value of hwLoopLineTestACAB is not support
        "
      ::= { hwLoopLineTestOprEntry 95 } 
                                                             
    hwLoopLineTestDCAGFlag OBJECT-TYPE
      SYNTAX INTEGER
      {
      valid(1),
      invalid(2),
      notsupport(3)
      }
      MAX-ACCESS read-only
      STATUS current
      DESCRIPTION
        "Indicates whether the value of hwLoopLineTestDCAG is valid.
         Options:
         1. valid(1)       -the value of hwLoopLineTestDCAG is valid
         2. invalid(2)     -the value of hwLoopLineTestDCAG is invalid
         3. notsupport(3)  -the value of hwLoopLineTestDCAG is not support
        "
      ::= { hwLoopLineTestOprEntry 96 } 
                                      
    hwLoopLineTestDCBGFlag OBJECT-TYPE
      SYNTAX INTEGER
      {
      valid(1),
      invalid(2),
      notsupport(3)
      }
      MAX-ACCESS read-only
      STATUS current
      DESCRIPTION
        "Indicates whether the value of hwLoopLineTestDCBG is valid.
         Options:
         1. valid(1)       -the value of hwLoopLineTestDCBG is valid 
         2. invalid(2)     -the value of hwLoopLineTestDCBG is invalid
         3. notsupport(3)  -the value of hwLoopLineTestDCBG is not support
        "
      ::= { hwLoopLineTestOprEntry 97 } 
                                                             
    hwLoopLineTestDCABFlag OBJECT-TYPE
      SYNTAX INTEGER
      {
      valid(1),
      invalid(2),
      notsupport(3)
      }
      MAX-ACCESS read-only
      STATUS current
      DESCRIPTION
        "Indicates whether the value of hwLoopLineTestDCAB is valid.
         Options:
         1. valid(1)       -the value of hwLoopLineTestDCAB is valid 
         2. invalid(2)     -the value of hwLoopLineTestDCAB is invalid
         3. notsupport(3)  -the value of hwLoopLineTestDCAB is not support
        "
      ::= { hwLoopLineTestOprEntry 98 } 
                  
    hwLoopLineTestRAGFlag OBJECT-TYPE
      SYNTAX INTEGER
      {
      valid(1),
      invalid(2),
      notsupport(3)
      }
      MAX-ACCESS read-only
      STATUS current
      DESCRIPTION
        "Indicates whether the value of hwLoopLineTestRAG is valid.
         Options:
         1. valid(1)       -the value of hwLoopLineTestRAG is valid 
         2. invalid(2)     -the value of hwLoopLineTestRAG is invalid
         3. notsupport(3)  -the value of hwLoopLineTestRAG is not support
        "
      ::= { hwLoopLineTestOprEntry 99 } 
                                                             
    hwLoopLineTestRBGFlag OBJECT-TYPE
      SYNTAX INTEGER
      {
      valid(1),
      invalid(2),
      notsupport(3)
      }
      MAX-ACCESS read-only
      STATUS current
        DESCRIPTION
        "Indicates whether the value of hwLoopLineTestRBG is valid.
         Options:
         1. valid(1)       -the value of hwLoopLineTestRBG is valid 
         2. invalid(2)     -the value of hwLoopLineTestRBG is invalid
         3. notsupport(3)  -the value of hwLoopLineTestRBG is not support
        "
      ::= { hwLoopLineTestOprEntry 100 } 
                                      
    hwLoopLineTestRABFlag OBJECT-TYPE
      SYNTAX INTEGER
      {
      valid(1),
      invalid(2),
      notsupport(3)
      }
      MAX-ACCESS read-only
      STATUS current
      DESCRIPTION
        "Indicates whether the value of hwLoopLineTestRAB is valid.
         Options:
         1. valid(1)       -the value of hwLoopLineTestRAB is valid
         2. invalid(2)     -the value of hwLoopLineTestRAB is invalid
         3. notsupport(3)  -the value of hwLoopLineTestRAB is not support
        "
      ::= { hwLoopLineTestOprEntry 101 } 
                                                             
    hwLoopLineTestRABPoleFlag OBJECT-TYPE
      SYNTAX INTEGER
      {
      valid(1),
      invalid(2),
      notsupport(3)
      }
      MAX-ACCESS read-only
      STATUS current
      DESCRIPTION
        "Indicates whether the value of hwLoopLineTestRABPole is valid.
         Options:
         1. valid(1)       -the value of hwLoopLineTestRABPole is valid
         2. invalid(2)     -the value of hwLoopLineTestRABPole is invalid
         3. notsupport(3)  -the value of hwLoopLineTestRABPole is not support
        "
      ::= { hwLoopLineTestOprEntry 102 } 
                  
    hwLoopLineTestRABResPoleFlag OBJECT-TYPE
      SYNTAX INTEGER
      {
      valid(1),
      invalid(2),
      notsupport(3)
      }
      MAX-ACCESS read-only
      STATUS current
      DESCRIPTION
        "Indicates whether the value of hwLoopLineTestRABResPole is valid.
         Options:
         1. valid(1)       -the value of hwLoopLineTestRABResPole is valid 
         2. invalid(2)     -the value of hwLoopLineTestRABResPole is invalid
         3. notsupport(3)  -the value of hwLoopLineTestRABResPole is not support
        "
      ::= { hwLoopLineTestOprEntry 103 } 
                                                    
    hwLoopLineTestCapAGFlag OBJECT-TYPE
      SYNTAX INTEGER
      {
      valid(1),
      invalid(2),
      notsupport(3)
      }
      MAX-ACCESS read-only
      STATUS current
      DESCRIPTION
        "Indicates whether the value of hwLoopLineTestCapAG is valid.
         Options:
         1. valid(1)       -the value of hwLoopLineTestCapAG is valid 
         2. invalid(2)     -the value of hwLoopLineTestCapAG is invalid
         3. notsupport(3)  -the value of hwLoopLineTestCapAG is not support
        "
      ::= { hwLoopLineTestOprEntry 104 } 
                                      
    hwLoopLineTestCapBGFlag OBJECT-TYPE
      SYNTAX INTEGER
      {
      valid(1),
      invalid(2),
      notsupport(3)
      }
      MAX-ACCESS read-only
      STATUS current
      DESCRIPTION
        "Indicates whether the value of hwLoopLineTestCapBG is valid.
         Options:
         1. valid(1)       -the value of hwLoopLineTestCapBG is valid 
         2. invalid(2)     -the value of hwLoopLineTestCapBG is invalid
         3. notsupport(3)  -the value of hwLoopLineTestCapBG is not support
        "
      ::= { hwLoopLineTestOprEntry 105 } 
                                                          
    hwLoopLineTestCapABFlag OBJECT-TYPE
      SYNTAX INTEGER
      {
      valid(1),
      invalid(2),
      notsupport(3)
      }
      MAX-ACCESS read-only
      STATUS current
      DESCRIPTION
        "Indicates whether the value of hwLoopLineTestCapAB is valid.
         Options:
         1. valid(1)       -the value of hwLoopLineTestCapAB is valid 
         2. invalid(2)     -the value of hwLoopLineTestCapAB is invalid
         3. notsupport(3)  -the value of hwLoopLineTestCapAB is not support
        "
      ::= { hwLoopLineTestOprEntry 106 }
                   
    hwLoopLineTestRbattipFlag OBJECT-TYPE
      SYNTAX INTEGER
      {
      valid(1),
      invalid(2)
      }
      MAX-ACCESS read-only
      STATUS current
      DESCRIPTION
        "Indicates whether the value of hwLoopLineTestRbattip is valid.
         Options:
         1. valid(1)   -the value of hwLoopLineTestRbattip is valid 
         2. invalid(2) -the value of hwLoopLineTestRbattip is invalid
        "
      ::= { hwLoopLineTestOprEntry 107 } 
                                                             
    hwLoopLineTestRbatringFlag OBJECT-TYPE
      SYNTAX INTEGER
      {
      valid(1),
      invalid(2)
      }
      MAX-ACCESS read-only
      STATUS current
      DESCRIPTION
        "Indicates whether the value of hwLoopLineTestRbatring is valid.
         Options:
         1. valid(1)   -the value of hwLoopLineTestRbatring is valid 
         2. invalid(2) -the value of hwLoopLineTestRbatring is invalid
        "
      ::= { hwLoopLineTestOprEntry 108 }
                                          
    hwLoopLineTestRringFlag OBJECT-TYPE
      SYNTAX INTEGER
      {
      valid(1),
      invalid(2)
      }
      MAX-ACCESS read-only
      STATUS current
      DESCRIPTION
        "Indicates whether the value of hwLoopLineTestRring is valid.
         Options:
         1. valid(1)   -the value of hwLoopLineTestRring is valid 
         2. invalid(2) -the value of hwLoopLineTestRring is invalid
        "
      ::= { hwLoopLineTestOprEntry 109 } 
                                                             
    hwLoopLineTestCsigFlag OBJECT-TYPE
      SYNTAX INTEGER
      {
      valid(1),
      invalid(2)
      }
      MAX-ACCESS read-only
      STATUS current
      DESCRIPTION
        "Indicates whether the value of hwLoopLineTestCsig is valid.
         Options:
         1. valid(1)   -the value of hwLoopLineTestCsig is valid 
         2. invalid(2) -the value of hwLoopLineTestCsig is invalid
        "
      ::= { hwLoopLineTestOprEntry 110 } 
         
    hwLoopLineTestPPAResFlag OBJECT-TYPE
      SYNTAX INTEGER
      {
      valid(1),
          invalid(2)
      }
        MAX-ACCESS read-only
        STATUS current
      DESCRIPTION
        "Indicates whether the value of hwLoopLineTestPPARes is valid.
         Options:
         1. valid(1)   -the value of hwLoopLineTestPPARes is valid 
         2. invalid(2) -the value of hwLoopLineTestPPARes is invalid
        "
      ::= { hwLoopLineTestOprEntry 111 } 
                                                             
    hwLoopLineTestVzenerFlag OBJECT-TYPE
      SYNTAX INTEGER
      {
      valid(1),
      invalid(2)
      }
      MAX-ACCESS read-only
        STATUS current
      DESCRIPTION
        "Indicates whether the value of hwLoopLineTestVzener is valid.
         Options:
         1. valid(1)   -the value of hwLoopLineTestVzener is valid 
         2. invalid(2) -the value of hwLoopLineTestVzener is invalid
        "
      ::= { hwLoopLineTestOprEntry 112 } 
                             
    hwLoopLineTestRzenerFlag OBJECT-TYPE
      SYNTAX INTEGER
      {
      valid(1),
      invalid(2)
      }
      MAX-ACCESS read-only
      STATUS current
      DESCRIPTION
        "Indicates whether the value of hwLoopLineTestRzener is valid.
         Options:
         1. valid(1)   -the value of hwLoopLineTestRzener is valid 
         2. invalid(2) -the value of hwLoopLineTestRzener is invalid
        "
      ::= { hwLoopLineTestOprEntry 113 }                         
                   
    hwLoopLineTestSNMPRab OBJECT-TYPE
      SYNTAX Integer32
      MAX-ACCESS read-only
      STATUS current
      DESCRIPTION
        "Indicates the A to B resistance (insulation resistance). 
         Unit: ohm
        "
      ::= { hwLoopLineTestOprEntry 114 }
    
    hwLoopLineTestSNMPRabFlag OBJECT-TYPE
      SYNTAX INTEGER
      {
      valid(1),
      invalid(2)
      }
      MAX-ACCESS read-only
      STATUS current
      DESCRIPTION
        "Indicates whether the value of hwLoopLineTestSNMPRab is valid.
         Options:
         1. valid(1)    -the value of hwLoopLineTestSNMPRab is valid
         2. invalid(2)  -the value of hwLoopLineTestSNMPRab is invalid
        "
      ::= { hwLoopLineTestOprEntry 115 }    
    
    hwLoopLineTestSNMPRba OBJECT-TYPE
      SYNTAX Integer32
      MAX-ACCESS read-only
      STATUS current
      DESCRIPTION
        "Indicates the B to A resistance (insulation resistance).
         Unit: ohm
        "
      ::= { hwLoopLineTestOprEntry 116 }
    
    hwLoopLineTestSNMPRbaFlag OBJECT-TYPE
      SYNTAX INTEGER
      {
      valid(1),
      invalid(2)
      }
      MAX-ACCESS read-only
      STATUS current
      DESCRIPTION
        "Indicates whether the value of hwLoopLineTestSNMPRba is valid.
         Options:
         1. valid(1)   -the value of hwLoopLineTestSNMPRba is valid 
         2. invalid(2) -the value of hwLoopLineTestSNMPRba is invalid
        "
      ::= { hwLoopLineTestOprEntry 117 }   
                  
    hwLoopLineTestPPAResultFlag OBJECT-TYPE
      SYNTAX INTEGER
      {
      valid(1),
      invalid(2)
      }
      MAX-ACCESS read-only
      STATUS current
      DESCRIPTION
        "Indicates whether the value of hwLoopLineTestPPA is valid.
         Options:
         1. valid(1)   -the value of hwLoopLineTestPPA is valid 
         2. invalid(2) -the value of hwLoopLineTestPPA is invalid
        "
      ::= { hwLoopLineTestOprEntry 118 }
                                        
    hwLoopLineTestUtgAcFreqFlag OBJECT-TYPE
      SYNTAX INTEGER
      {
      valid(1),
      invalid(2),
      notsupport(3)
      }
      MAX-ACCESS read-only
      STATUS current
      DESCRIPTION
        "Indicates whether the value of hwLoopLineTestUtgAcFreq is valid.
         Options:
         1. valid(1)       -the value of hwLoopLineTestUtgAcFreq is valid
         2. invalid(2)     -the value of hwLoopLineTestUtgAcFreq is invalid
         3. notsupport(3)  -the value of hwLoopLineTestUtgAcFreq is not support
         
        "
      ::= { hwLoopLineTestOprEntry 119 } 
                     
    hwLoopLineTestUrgAcFreqFlag OBJECT-TYPE
      SYNTAX INTEGER
      {
      valid(1),
      invalid(2),
      notsupport(3)
      }
      MAX-ACCESS read-only
      STATUS current
      DESCRIPTION
        "Indicates whether the value of hwLoopLineTestUrgAcFreq is valid.
         Options:
         1. valid(1)       -the value of hwLoopLineTestUrgAcFreq is valid
         2. invalid(2)     -the value of hwLoopLineTestUrgAcFreq is invalid
         3. notsupport(3)  -the value of hwLoopLineTestUrgAcFreq is not support
        "
      ::= { hwLoopLineTestOprEntry 120 }    
                 
    hwLoopLineTestUtrAcFreqFlag OBJECT-TYPE
      SYNTAX INTEGER
      {
      valid(1),
      invalid(2),
      notsupport(3)
      }
      MAX-ACCESS read-only
      STATUS current
      DESCRIPTION
        "Indicates whether the value of hwLoopLineTestUtrAcFreq is valid.
         Options:
         1. valid(1)       -the value of hwLoopLineTestUtrAcFreq is valid
         2. invalid(2)     -the value of hwLoopLineTestUtrAcFreq is invalid
         3. notsupport(3)  -the value of hwLoopLineTestUtrAcFreq is not support
        "
      ::= { hwLoopLineTestOprEntry 121 }  
                 
      hwLoopLineTestItipAcFlag OBJECT-TYPE
      SYNTAX INTEGER
      {
      valid(1),
      invalid(2),
      notsupport(3)
      }
      MAX-ACCESS read-only
      STATUS current
      DESCRIPTION
        "Indicates whether the value of hwLoopLineTestItipAc is valid.
         Options:
         1. valid(1)       -the value of hwLoopLineTestItipAc is valid 
         2. invalid(2)     -the value of hwLoopLineTestItipAc is invalid
         3. notsupport(3)  -the value of hwLoopLineTestItipAc is not support
        "
      ::= { hwLoopLineTestOprEntry 122 }
    
    hwLoopLineTestIringAcFlag OBJECT-TYPE
      SYNTAX INTEGER
      {
      valid(1),
      invalid(2),
      notsupport(3)
      }
      MAX-ACCESS read-only
      STATUS current
      DESCRIPTION
        "Indicates whether the value of hwLoopLineTestIringAc is valid.
         Options:
         1. valid(1)       -the value of hwLoopLineTestIringAc is valid 
         2. invalid(2)     -the value of hwLoopLineTestIringAc is invalid
         3. notsupport(3)  -the value of hwLoopLineTestIringAc is not support
        "
      ::= { hwLoopLineTestOprEntry 123 }
     
    hwLoopLineTestItipDcFlag OBJECT-TYPE
      SYNTAX INTEGER
      {
      valid(1),
      invalid(2),
      notsupport(3)
      }
      MAX-ACCESS read-only
      STATUS current
      DESCRIPTION
        "Indicates whether the value of hwLoopLineTestItipDc is valid.
         Options:
         1. valid(1)       -the value of hwLoopLineTestItipDc is valid 
         2. invalid(2)     -the value of hwLoopLineTestItipDc is invalid
         3. notsupport(3)  -the value of hwLoopLineTestItipDc is not support
        "
      ::= { hwLoopLineTestOprEntry 124 }    
                      
    hwLoopLineTestIringDcFlag OBJECT-TYPE
      SYNTAX INTEGER
      {
      valid(1),
      invalid(2),
      notsupport(3)
      }
      MAX-ACCESS read-only
      STATUS current
      DESCRIPTION
        "Indicates whether the value of hwLoopLineTestIringDc is valid.
         Options:
         1. valid(1)       -the value of hwLoopLineTestIringDc is valid 
         2. invalid(2)     -the value of hwLoopLineTestIringDc is invalid
         3. notsupport(3)  -the value of hwLoopLineTestIringDc is not support
        "
      ::= { hwLoopLineTestOprEntry 125 }
                      
    hwLoopLineTestGtgFlag OBJECT-TYPE
      SYNTAX INTEGER
      {
       valid(1),
      invalid(2),
      notsupport(3)
      }
      MAX-ACCESS read-only
      STATUS current
      DESCRIPTION
        "Indicates whether the value of hwLoopLineTestGtg is valid.
         Options:
         1. valid(1)       -the value of hwLoopLineTestGtg is valid
         2. invalid(2)     -the value of hwLoopLineTestGtg is invalid
         3. notsupport(3)  -the value of hwLoopLineTestGtg is not support
        "
      ::= { hwLoopLineTestOprEntry 126 }
                      
    hwLoopLineTestBtgFlag OBJECT-TYPE
      SYNTAX INTEGER
      {
      valid(1),
      invalid(2),
      notsupport(3)
      }
      MAX-ACCESS read-only
      STATUS current
      DESCRIPTION
        "Indicates whether the value of hwLoopLineTestBtg is valid.
         Options:
         1. valid(1)       -the value of hwLoopLineTestBtg is valid 
         2. invalid(2)     -the value of hwLoopLineTestBtg is invalid
         3. notsupport(3)  -the value of hwLoopLineTestBtg is not support
        "
        ::= { hwLoopLineTestOprEntry 127 }
                      
    hwLoopLineTestGrgFlag OBJECT-TYPE
      SYNTAX INTEGER
      {
      valid(1),
      invalid(2),
      notsupport(3)
      }
      MAX-ACCESS read-only
      STATUS current
      DESCRIPTION
        "Indicates whether the value of hwLoopLineTestGrg is valid.
         Options:
         1. valid(1)       -the value of hwLoopLineTestGrg is valid
         2. invalid(2)     -the value of hwLoopLineTestGrg is invalid
         3. notsupport(3)  -the value of hwLoopLineTestGrg is not support
        "
      ::= { hwLoopLineTestOprEntry 128 }
                   
    hwLoopLineTestBrgFlag OBJECT-TYPE
      SYNTAX INTEGER
      {
      valid(1),
      invalid(2),
      notsupport(3)
      }
      MAX-ACCESS read-only
      STATUS current
      DESCRIPTION
        "Indicates whether the value of hwLoopLineTestBrg is valid.
         Options:
         1. valid(1)       -the value of hwLoopLineTestBrg is valid 
         2. invalid(2)     -the value of hwLoopLineTestBrg is invalid
         3. notsupport(3)  -the value of hwLoopLineTestBrg is not support
        "
      ::= { hwLoopLineTestOprEntry 129 }     
                       
    hwLoopLineTestGtrFlag OBJECT-TYPE
      SYNTAX INTEGER
      {
      valid(1),
      invalid(2),
      notsupport(3)
      }
      MAX-ACCESS read-only
      STATUS current
      DESCRIPTION
        "Indicates whether the value of hwLoopLineTestGtr is valid.
         Options:
         1. valid(1)       -the value of hwLoopLineTestGtr is valid 
         2. invalid(2)     -the value of hwLoopLineTestGtr is invalid
         3. notsupport(3)  -the value of hwLoopLineTestGtr is not support
        "
      ::= { hwLoopLineTestOprEntry 130 } 
                      
    hwLoopLineTestBtrFlag OBJECT-TYPE
      SYNTAX INTEGER
      {
      valid(1),
      invalid(2)
      }
      MAX-ACCESS read-only
      STATUS current
      DESCRIPTION
        "Indicates whether the value of hwLoopLineTestBtr is valid.
         Options:
         1. valid(1)   -the value of hwLoopLineTestBtr is valid
         2. invalid(2) -the value of hwLoopLineTestBtr is invalid
        "
      ::= { hwLoopLineTestOprEntry 131 }
         
    hwLoopLineTestSIGNFlag OBJECT-TYPE
      SYNTAX INTEGER
      {
      valid(1),
      invalid(2)
      }
      MAX-ACCESS read-only
      STATUS current
      DESCRIPTION
        "Indicates whether the value of hwLoopLineTestSIGN is valid.
         Options:
         1. valid(1)   -the value of hwLoopLineTestSIGN is valid 
         2. invalid(2) -the value of hwLoopLineTestSIGN is invalid
        "
      ::= { hwLoopLineTestOprEntry 132 }
         
    hwLoopLineTestACFEMFlag OBJECT-TYPE
      SYNTAX INTEGER
      {
      valid(1),
      invalid(2)
      }
      MAX-ACCESS read-only
      STATUS current
      DESCRIPTION
        "Indicates whether the value of hwLoopLineTestACFEM is valid.
         Options:
         1. valid(1)   -the value of hwLoopLineTestACFEM is valid
         2. invalid(2) -the value of hwLoopLineTestACFEM is invalid
        "
      ::= { hwLoopLineTestOprEntry 133 }
                      
    hwLoopLineTestDCFEMFlag OBJECT-TYPE
      SYNTAX INTEGER
      {
      valid(1),
      invalid(2)
      }
      MAX-ACCESS read-only
      STATUS current
      DESCRIPTION
        "Indicates whether the value of hwLoopLineTestDCFEM is valid.
         Options:
         1. valid(1)   -the value of hwLoopLineTestDCFEM is valid
         2. invalid(2) -the value of hwLoopLineTestDCFEM is invalid
        "
      ::= { hwLoopLineTestOprEntry 134 }
    
    hwLoopLineTestONHKFlag OBJECT-TYPE
      SYNTAX INTEGER
      {
      valid(1),
      invalid(2)
      }
      MAX-ACCESS read-only
      STATUS current
      DESCRIPTION
        "Indicates whether the value of hwLoopLineTestONHK is valid.
         Options:
         1. valid(1)   -the value of hwLoopLineTestONHK is valid 
         2. invalid(2) -the value of hwLoopLineTestONHK is invalid
        "
      ::= { hwLoopLineTestOprEntry 135 }
                      
    hwLoopLineTestOPENFlag OBJECT-TYPE
      SYNTAX INTEGER
      {
      valid(1),
      invalid(2)
      }
      MAX-ACCESS read-only
      STATUS current
      DESCRIPTION
        "Indicates whether the value of hwLoopLineTestOPEN is valid.
         Options:
         1. valid(1)   -the value of hwLoopLineTestOPEN is valid 
         2. invalid(2) -the value of hwLoopLineTestOPEN is invalid
        "
      ::= { hwLoopLineTestOprEntry 136 }
                      
    hwLoopLineTestSHORTFlag OBJECT-TYPE
      SYNTAX INTEGER
      {
      valid(1),
      invalid(2)
      }
      MAX-ACCESS read-only
      STATUS current
      DESCRIPTION
        "Indicates whether the value of hwLoopLineTestSHORT is valid.
         Options:
         1. valid(1)   -the value of hwLoopLineTestSHORT is valid 
         2. invalid(2) -the value of hwLoopLineTestSHORT is invalid
        "
      ::= { hwLoopLineTestOprEntry 137 }
    
    hwLoopLineTestROHFlag OBJECT-TYPE
      SYNTAX INTEGER
      {
      valid(1),
      invalid(2)
      }
      MAX-ACCESS read-only
      STATUS current
      DESCRIPTION
        "Indicates whether the value of hwLoopLineTestROH is valid.
         Options:
         1. valid(1)   -the value of hwLoopLineTestROH is valid
         2. invalid(2) -the value of hwLoopLineTestROH is invalid
        "
      ::= { hwLoopLineTestOprEntry 138 }
    
    hwLoopLineTestUtgDcUpFlag OBJECT-TYPE
      SYNTAX INTEGER
      {
      valid(1),
      invalid(2)
      }
      MAX-ACCESS read-only
      STATUS current
      DESCRIPTION
        "Indicates whether the value of hwLoopLineTestUtgDcUp is valid.
         Options:
         1. valid(1)   -the value of hwLoopLineTestUtgDcUp is valid 
         2. invalid(2) -the value of hwLoopLineTestUtgDcUp is invalid
        "
      ::= { hwLoopLineTestOprEntry 139 }
                   
    hwLoopLineTestUtgDcDownFlag OBJECT-TYPE
      SYNTAX INTEGER
      {
      valid(1),
      invalid(2)
      }
      MAX-ACCESS read-only
      STATUS current
      DESCRIPTION
        "Indicates whether the value of hwLoopLineTestUtgDcDown is valid.
         Options:
         1. valid(1)   -the value of hwLoopLineTestUtgDcDown is valid 
         2. invalid(2) -the value of hwLoopLineTestUtgDcDown is invalid
        "
      ::= { hwLoopLineTestOprEntry 140 }
                      
    hwLoopLineTestUrgDcUpFlag OBJECT-TYPE
      SYNTAX INTEGER
      {
      valid(1),
      invalid(2)
      }
      MAX-ACCESS read-only
      STATUS current
      DESCRIPTION
        "Indicates whether the value of hwLoopLineTestUrgDcUp is valid.
         Options:
         1. valid(1)   -the value of hwLoopLineTestUrgDcUp is valid
         2. invalid(2) -the value of hwLoopLineTestUrgDcUp is invalid
        "
      ::= { hwLoopLineTestOprEntry 141 }
         
    hwLoopLineTestUrgDcDownFlag OBJECT-TYPE
      SYNTAX INTEGER
      {
      valid(1),
      invalid(2)
      }
      MAX-ACCESS read-only
      STATUS current
      DESCRIPTION
        "Indicates whether the value of hwLoopLineTestUrgDcDown is valid.
         Options:
         1. valid(1)   -the value of hwLoopLineTestUrgDcDown is valid
         2. invalid(2) -the value of hwLoopLineTestUrgDcDown is invalid
        "
      ::= { hwLoopLineTestOprEntry 142 }
                      
    hwLoopLineTestUtrPosFlag OBJECT-TYPE
      SYNTAX INTEGER
      {
      valid(1),
      invalid(2)
      }
      MAX-ACCESS read-only
      STATUS current
      DESCRIPTION
        "Indicates whether the value of hwLoopLineTestUtrPos is valid.
         Options:
         1. valid(1)   -the value of hwLoopLineTestUtrPos is valid 
         2. invalid(2) -the value of hwLoopLineTestUtrPos is invalid
        "
      ::= { hwLoopLineTestOprEntry 143 }
                      
    hwLoopLineTestUtrNegFlag OBJECT-TYPE
      SYNTAX INTEGER
      {
      valid(1),
      invalid(2)
      }
      MAX-ACCESS read-only
      STATUS current
      DESCRIPTION
        "Indicates whether the value of hwLoopLineTestUtrNeg is valid.
         Options:
         1. valid(1)   -the value of hwLoopLineTestUtrNeg is valid 
         2. invalid(2) -the value of hwLoopLineTestUtrNeg is invalid
        "
      ::= { hwLoopLineTestOprEntry 144 }     
                      
    hwLoopLineTestItgDcUpFlag OBJECT-TYPE
      SYNTAX INTEGER
      {
      valid(1),
      invalid(2)
      }
      MAX-ACCESS read-only
      STATUS current
      DESCRIPTION
        "Indicates whether the value of hwLoopLineTestItgDcUp is valid.
         Options:
         1. valid(1)   -the value of hwLoopLineTestItgDcUp is valid 
         2. invalid(2) -the value of hwLoopLineTestItgDcUp is invalid
        "
      ::= { hwLoopLineTestOprEntry 145 }
                      
    hwLoopLineTestItgDcDownFlag OBJECT-TYPE
      SYNTAX INTEGER
      {
      valid(1),
      invalid(2)
      }
      MAX-ACCESS read-only
      STATUS current
      DESCRIPTION
        "Indicates whether the value of hwLoopLineTestItgDcDown is valid.
         Options:
         1. valid(1)   -the value of hwLoopLineTestItgDcDown is valid 
         2. invalid(2) -the value of hwLoopLineTestItgDcDown is invalid
        "
      ::= { hwLoopLineTestOprEntry 146 }
                   
    hwLoopLineTestIrgDcUpFlag OBJECT-TYPE
      SYNTAX INTEGER
      {
      valid(1),
      invalid(2)
      }
      MAX-ACCESS read-only
      STATUS current
      DESCRIPTION
        "Indicates whether the value of hwLoopLineTestIrgDcUp is valid.
         Options:
         1. valid(1)   -the value of hwLoopLineTestIrgDcUp is valid 
         2. invalid(2) -the value of hwLoopLineTestIrgDcUp is invalid
        "
      ::= { hwLoopLineTestOprEntry 147 }
    
    hwLoopLineTestIrgDcDownFlag OBJECT-TYPE
      SYNTAX INTEGER
      {
      valid(1),
      invalid(2)
      }
      MAX-ACCESS read-only
      STATUS current
      DESCRIPTION
        "Indicates whether the value of hwLoopLineTestIrgDcDown is valid.
         Options:
         1. valid(1)   -the value of hwLoopLineTestIrgDcDown is valid
         2. invalid(2) -the value of hwLoopLineTestIrgDcDown is invalid
        "
      ::= { hwLoopLineTestOprEntry 148 }
                   
    hwLoopLineTestItrPosFlag OBJECT-TYPE
      SYNTAX INTEGER
      {
      valid(1),
      invalid(2)
      }
      MAX-ACCESS read-only
      STATUS current
      DESCRIPTION
        "Indicates whether the value of hwLoopLineTestItrPos is valid.
         Options:
         1. valid(1)   -the value of hwLoopLineTestItrPos is valid 
         2. invalid(2) -the value of hwLoopLineTestItrPos is invalid
        "
      ::= { hwLoopLineTestOprEntry 149 }
                      
    hwLoopLineTestItrNegFlag OBJECT-TYPE
      SYNTAX INTEGER
      {
      valid(1),
      invalid(2)
      }
      MAX-ACCESS read-only
      STATUS current
      DESCRIPTION
        "Indicates whether the value of hwLoopLineTestItrNeg is valid.
         Options:
         1. valid(1)   -the value of hwLoopLineTestItrNeg is valid
         2. invalid(2) -the value of hwLoopLineTestItrNeg is invalid
        "
      ::= { hwLoopLineTestOprEntry 150 }                                                                                                                                                                                                                                                                                                                                                                                                                                                                                                                                                                                                                                               
                        
    hwLoopLineTestRingerFlag OBJECT-TYPE
      SYNTAX INTEGER
      {
      valid(1),
      invalid(2)
      }
      MAX-ACCESS read-only
      STATUS current
      DESCRIPTION
        "Indicates whether the value of hwLoopLineTestRinger is valid.
         Options:
         1. valid(1)   -the value of hwLoopLineTestRinger is valid
         2. invalid(2) -the value of hwLoopLineTestRinger is invalid
        "
      ::= { hwLoopLineTestOprEntry 151 }    

    hwLoopLineTestLRFlag OBJECT-TYPE
      SYNTAX INTEGER
      {
      valid(1),
      invalid(2),
      notsupport(3)
      }
      MAX-ACCESS read-only
      STATUS current
      DESCRIPTION
        "Indicates whether the value of hwLoopLineTestLR is valid.
         Options:
         1. valid(1)       -the value of hwLoopLineTestLR is valid
         2. invalid(2)     -the value of hwLoopLineTestLR is invalid
         3. notsupport(3)  -the value of hwLoopLineTestLR is not support
        "
      ::= { hwLoopLineTestOprEntry 152 }

    hwLoopLineTestDcCurrent OBJECT-TYPE
      SYNTAX INTEGER
      {
      notest(1),
      test(2),
      invalid(-1)
      }
      MAX-ACCESS read-create
      STATUS current
      DESCRIPTION
      "Indicates whether DcCurrent exists on the line under test. 
         Options:
         1. notest(1)   -DcCurrent does not exist on the line under test
         2. test(2)     -DcCurrent exists on the line under test
         3. invalid(-1) -invalid value
         Default: notest(1)
      "
      ::= { hwLoopLineTestOprEntry 153 }

    hwLoopLineTestAcCurrent OBJECT-TYPE
      SYNTAX INTEGER
      {
      notest(1),
      test(2),
      invalid(-1)
      }
      MAX-ACCESS read-create
      STATUS current
      DESCRIPTION
      "Indicates whether AcCurrent exists on the line under test. 
         Options:
         1. notest(1)   -AcCurrent does not exist on the line under test
         2. test(2)     -AcCurrent exists on the line under test
         3. invalid(-1) -invalid value
         Default: notest(1)
      "
      ::= { hwLoopLineTestOprEntry 154 }

    hwLoopLineTestConductance OBJECT-TYPE
      SYNTAX INTEGER
      {
      notest(1),
      test(2),
      invalid(-1)
      }
      MAX-ACCESS read-create
      STATUS current
      DESCRIPTION
      "Indicates whether conductance exists on the line under test. 
         Options:
         1. notest(1)   -Conductance does not exist on the line under test
         2. test(2)     -Conductance exists on the line under test
         3. invalid(-1) -invalid value
         Default: notest(1)
      "
      ::= { hwLoopLineTestOprEntry 155 }

    hwLoopLineTestSusceptance OBJECT-TYPE
      SYNTAX INTEGER
      {
      notest(1),
      test(2),
      invalid(-1)
      }
      MAX-ACCESS read-create
      STATUS current
      DESCRIPTION
      "Indicates whether susceptance exists on the line under test. 
         Options:
         1. notest(1)   -Susceptance does not exist on the line under test
         2. test(2)     -Susceptance exists on the line under test
         3. invalid(-1) -invalid value
         Default: notest(1)
      "
      ::= { hwLoopLineTestOprEntry 156 }

    hwLoopLineTestAcfrequencyA OBJECT-TYPE
      SYNTAX INTEGER
      {
      sixteenDotSix(1),
      twentyFive(2),
      fifty(3),
      sixty(4),
      unknown(5),
      invalid(-1)
      }
      MAX-ACCESS read-only
      STATUS current
      DESCRIPTION
      "Indicates status of Acfrequency in line A. 
         Options:
         1. sixteenDotSix(1)  -line A has ACFrequency 16.6
         2. twentyFive(2)     -line A has ACFrequency 25
         3. fifty(3)          -line A has ACFrequency 50
         4. sixty(4)          -line A has ACFrequency 60
         5. unknown(5)        -line A has unknown ACFrequency 
         6. invalid(-1)       -invalid value
         Unit: Hz
      "
      ::= { hwLoopLineTestOprEntry 157 }

    hwLoopLineTestAcfrequencyB OBJECT-TYPE
      SYNTAX INTEGER
      {
      sixteenDotSix(1),
      twentyFive(2),
      fifty(3),
      sixty(4),
      unknown(5),
      invalid(-1)
      }
      MAX-ACCESS read-only
      STATUS current
      DESCRIPTION
      "Indicates status of Acfrequency in line A. 
         Options:
         1. sixteenDotSix(1)  -line A has ACFrequency 16.6
         2. twentyFive(2)     -line A has ACFrequency 25
         3. fifty(3)          -line A has ACFrequency 50
         4. sixty(4)          -line A has ACFrequency 60
         5. unknown(5)        -line A has unknown ACFrequency 
         6. invalid(-1)       -invalid value
         Unit: Hz
      "
      ::= { hwLoopLineTestOprEntry 158 }

    hwLoopLineTestCapABH OBJECT-TYPE
      SYNTAX Integer32
      MAX-ACCESS read-only
      STATUS current
      DESCRIPTION
        "Indicates the A->B capacitance. 
         Unit: nF
        " 
      ::= { hwLoopLineTestOprEntry 159 }

    hwLoopLineTestCapABHFlag OBJECT-TYPE
      SYNTAX INTEGER
      {
      valid(1),
      invalid(2),
      notsupport(3)
      }
      MAX-ACCESS read-only
      STATUS current
      DESCRIPTION
        "Indicates whether the value of hwLoopLineTestCapABH is valid.
         Options:
         1. valid(1)       -the value of hwLoopLineTestCapABH is valid
         2. invalid(2)     -the value of hwLoopLineTestCapABH is invalid
         3. notsupport(3)  -the value of hwLoopLineTestCapABH is not support
        "
      ::= { hwLoopLineTestOprEntry 160 }

     hwLoopLineTestGtrH OBJECT-TYPE
      SYNTAX Integer32
      MAX-ACCESS read-only
      STATUS current
      DESCRIPTION
        "Indicates the A->B conductance. 
         Unit: nS
        " 
      ::= { hwLoopLineTestOprEntry 161 }

    hwLoopLineTestGtrHFlag OBJECT-TYPE
      SYNTAX INTEGER
      {
      valid(1),
      invalid(2),
      notsupport(3)
      }
      MAX-ACCESS read-only
      STATUS current
      DESCRIPTION
        "Indicates whether the value of hwLoopLineTestGtrH is valid.
         Options:
         1. valid(1)       -the value of hwLoopLineTestGtrH is valid
         2. invalid(2)     -the value of hwLoopLineTestGtrH is invalid
         3. notsupport(3)  -the value of hwLoopLineTestGtrH is not support
        "
      ::= { hwLoopLineTestOprEntry 162 }

    hwLoopLineTestBtrH OBJECT-TYPE
      SYNTAX Integer32
      MAX-ACCESS read-only
      STATUS current
      DESCRIPTION
        "Indicates the A->B susceptance. 
         Unit: nS
        " 
      ::= { hwLoopLineTestOprEntry 163 }

    hwLoopLineTestBtrHFlag OBJECT-TYPE
      SYNTAX INTEGER
      {
      valid(1),
      invalid(2),
      notsupport(3)
      }
      MAX-ACCESS read-only
      STATUS current
      DESCRIPTION
        "Indicates whether the value of hwLoopLineTestBtrH is valid.
         Options:
         1. valid(1)       -the value of hwLoopLineTestBtrH is valid
         2. invalid(2)     -the value of hwLoopLineTestBtrH is invalid
         3. notsupport(3)  -the value of hwLoopLineTestBtrH is not support
        "
      ::= { hwLoopLineTestOprEntry 164 }

    hwLoopLineTestABDcCurrent OBJECT-TYPE
      SYNTAX Integer32
      MAX-ACCESS read-only
      STATUS current
      DESCRIPTION
        "Indicates the A->B Dc current. 
         Unit: uA
        " 
      ::= { hwLoopLineTestOprEntry 165 }

    hwLoopLineTestABDcCurrentFlag OBJECT-TYPE
      SYNTAX INTEGER
      {
      valid(1),
      invalid(2),
      notsupport(3)
      }
      MAX-ACCESS read-only
      STATUS current
      DESCRIPTION
        "Indicates whether the value of hwLoopLineTestABDcCurrent is valid.
         Options:
         1. valid(1)       -the value of hwLoopLineTestABDcCurrent is valid
         2. invalid(2)     -the value of hwLoopLineTestABDcCurrent is invalid
         3. notsupport(3)  -the value of hwLoopLineTestABDcCurrent is not support
        "
      ::= { hwLoopLineTestOprEntry 166 }

    hwLoopLineTestBADcCurrent OBJECT-TYPE
      SYNTAX Integer32
      MAX-ACCESS read-only
      STATUS current
      DESCRIPTION
        "Indicates the B->A Dc current. 
         Unit: uA
        " 
      ::= { hwLoopLineTestOprEntry 167 }

    hwLoopLineTestBADcCurrentFlag OBJECT-TYPE
      SYNTAX INTEGER
      {
      valid(1),
      invalid(2),
      notsupport(3)
      }
      MAX-ACCESS read-only
      STATUS current
      DESCRIPTION
        "Indicates whether the value of hwLoopLineTestBADcCurrent is valid.
         Options:
         1. valid(1)       -the value of hwLoopLineTestBADcCurrent is valid
         2. invalid(2)     -the value of hwLoopLineTestBADcCurrent is invalid
         3. notsupport(3)  -the value of hwLoopLineTestBADcCurrent is not support
        "
      ::= { hwLoopLineTestOprEntry 168 }

    hwLoopLineTestABAcCurrent OBJECT-TYPE
      SYNTAX Integer32
      MAX-ACCESS read-only
      STATUS current
      DESCRIPTION
        "Indicates the A->B Ac current. 
         Unit: uArms
        " 
      ::= { hwLoopLineTestOprEntry 169 }

    hwLoopLineTestABAcCurrentFlag OBJECT-TYPE
      SYNTAX INTEGER
      {
      valid(1),
      invalid(2),
      notsupport(3)
      }
      MAX-ACCESS read-only
      STATUS current
      DESCRIPTION
        "Indicates whether the value of hwLoopLineTestABAcCurrent is valid.
         Options:
         1. valid(1)       -the value of hwLoopLineTestABAcCurrent is valid
         2. invalid(2)     -the value of hwLoopLineTestABAcCurrent is invalid
         3. notsupport(3)  -the value of hwLoopLineTestABAcCurrent is not support
        "
      ::= { hwLoopLineTestOprEntry 170 }

    hwLoopLineTestBAAcCurrent OBJECT-TYPE
      SYNTAX Integer32
      MAX-ACCESS read-only
      STATUS current
      DESCRIPTION
        "Indicates the B->A Ac current. 
         Unit: uArms
        " 
      ::= { hwLoopLineTestOprEntry 171 }

    hwLoopLineTestBAAcCurrentFlag OBJECT-TYPE
      SYNTAX INTEGER
      {
      valid(1),
      invalid(2),
      notsupport(3)
      }
      MAX-ACCESS read-only
      STATUS current
      DESCRIPTION
        "Indicates whether the value of hwLoopLineTestBAAcCurrent is valid.
         Options:
         1. valid(1)       -the value of hwLoopLineTestBAAcCurrent is valid
         2. invalid(2)     -the value of hwLoopLineTestBAAcCurrent is invalid
         3. notsupport(3)  -the value of hwLoopLineTestBAAcCurrent is not support
        "
      ::= { hwLoopLineTestOprEntry 172 }
    
    hwLoopLineTestCSfrequencyForTest OBJECT-TYPE
      SYNTAX Integer32
      MAX-ACCESS read-only
      STATUS current
      DESCRIPTION
        "Indicates the frequency for test capacitance and conductance. 
         Unit: Hz
        " 
      ::= { hwLoopLineTestOprEntry 173 }

    hwLoopLineTestCSfrequencyForTestFlag OBJECT-TYPE
      SYNTAX INTEGER
      {
      valid(1),
      invalid(2),
      notsupport(3)
      }
      MAX-ACCESS read-only
      STATUS current
      DESCRIPTION
        "Indicates whether the value of hwLoopLineTestCSfrequencyForTest is valid.
         Options:
         1. valid(1)       -the value of hwLoopLineTestCSfrequencyForTest is valid
         2. invalid(2)     -the value of hwLoopLineTestCSfrequencyForTest is invalid
         3. notsupport(3)  -the value of hwLoopLineTestCSfrequencyForTest is not support
        "
      ::= { hwLoopLineTestOprEntry 174 }

    hwLoopLineTestImpedanceForTest OBJECT-TYPE
      SYNTAX Integer32
      MAX-ACCESS read-only
      STATUS current
      DESCRIPTION
        "Indicates the resistance inputed in test abnormal voltage. 
         Unit: ohm
        " 
      ::= { hwLoopLineTestOprEntry 175 }

    hwLoopLineTestImpedanceForTestFlag OBJECT-TYPE
      SYNTAX INTEGER
      {
      valid(1),
      invalid(2),
      notsupport(3)
      }
      MAX-ACCESS read-only
      STATUS current
      DESCRIPTION
        "Indicates whether the value of hwLoopLineTestImpedanceForTest is valid.
         Options:
         1. valid(1)       -the value of hwLoopLineTestImpedanceForTest is valid
         2. invalid(2)     -the value of hwLoopLineTestImpedanceForTest is invalid
         3. notsupport(3)  -the value of hwLoopLineTestImpedanceForTest is not support
        "
      ::= { hwLoopLineTestOprEntry 176 }

    hwLoopLineTestMaxVForSignature OBJECT-TYPE
      SYNTAX Integer32
      MAX-ACCESS read-only
      STATUS current
      DESCRIPTION
        "Indicates the maximum voltage for signature. 
         Unit: mV
        " 
      ::= { hwLoopLineTestOprEntry 177 }

    hwLoopLineTestMaxVForSignatureFlag OBJECT-TYPE
      SYNTAX INTEGER
      {
      valid(1),
      invalid(2),
      notsupport(3)
      }
      MAX-ACCESS read-only
      STATUS current
      DESCRIPTION
        "Indicates whether the value of hwLoopLineTestMaxVForSignature is valid.
         Options:
         1. valid(1)       -the value of hwLoopLineTestMaxVForSignature is valid
         2. invalid(2)     -the value of hwLoopLineTestMaxVForSignature is invalid
         3. notsupport(3)  -the value of hwLoopLineTestMaxVForSignature is not support
        "
      ::= { hwLoopLineTestOprEntry 178 }

    hwLoopLineTestAGMaxVForTest OBJECT-TYPE
      SYNTAX Integer32
      MAX-ACCESS read-only
      STATUS current
      DESCRIPTION
        "Indicates the A->ground max voltage in testing. 
         Unit: mV
        " 
      ::= { hwLoopLineTestOprEntry 179 }

    hwLoopLineTestAGMaxVForTestFlag OBJECT-TYPE
      SYNTAX INTEGER
      {
      valid(1),
      invalid(2),
      notsupport(3)
      }
      MAX-ACCESS read-only
      STATUS current
      DESCRIPTION
        "Indicates whether the value of hwLoopLineTestAGMaxVForTest is valid.
         Options:
         1. valid(1)       -the value of hwLoopLineTestAGMaxVForTest is valid
         2. invalid(2)     -the value of hwLoopLineTestAGMaxVForTest is invalid
         3. notsupport(3)  -the value of hwLoopLineTestAGMaxVForTest is not support
        "
      ::= { hwLoopLineTestOprEntry 180 }

    hwLoopLineTestAGMinVForTest OBJECT-TYPE
      SYNTAX Integer32
      MAX-ACCESS read-only
      STATUS current
      DESCRIPTION
        "Indicates the A->ground min voltage in testing. 
         Unit: mV
        " 
      ::= { hwLoopLineTestOprEntry 181 }

    hwLoopLineTestAGMinVForTestFlag OBJECT-TYPE
      SYNTAX INTEGER
      {
      valid(1),
      invalid(2),
      notsupport(3)
      }
      MAX-ACCESS read-only
      STATUS current
      DESCRIPTION
        "Indicates whether the value of hwLoopLineTestAGMinVForTest is valid.
         Options:
         1. valid(1)       -the value of hwLoopLineTestAGMinVForTest is valid
         2. invalid(2)     -the value of hwLoopLineTestAGMinVForTest is invalid
         3. notsupport(3)  -the value of hwLoopLineTestAGMinVForTest is not support
        "
      ::= { hwLoopLineTestOprEntry 182 }

    
    hwLoopLineTestBGMaxVForTest OBJECT-TYPE
          SYNTAX Integer32
          MAX-ACCESS read-only
          STATUS current
          DESCRIPTION
            "Indicates the B->ground max voltage in testing. 
             Unit: mV
            " 
          ::= { hwLoopLineTestOprEntry 183 }
    
    hwLoopLineTestBGMaxVForTestFlag OBJECT-TYPE
      SYNTAX INTEGER
      {
      valid(1),
      invalid(2),
      notsupport(3)
      }
      MAX-ACCESS read-only
      STATUS current
      DESCRIPTION
        "Indicates whether the value of hwLoopLineTestBGMaxVForTest is valid.
         Options:
         1. valid(1)       -the value of hwLoopLineTestBGMaxVForTest is valid
         2. invalid(2)     -the value of hwLoopLineTestBGMaxVForTest is invalid
         3. notsupport(3)  -the value of hwLoopLineTestBGMaxVForTest is not support
        "
      ::= { hwLoopLineTestOprEntry 184 }

    hwLoopLineTestBGMinVForTest OBJECT-TYPE
          SYNTAX Integer32
          MAX-ACCESS read-only
          STATUS current
          DESCRIPTION
            "Indicates the B->ground min voltage in testing. 
             Unit: mV
            " 
          ::= { hwLoopLineTestOprEntry 185 }
    
    hwLoopLineTestBGMinVForTestFlag OBJECT-TYPE
      SYNTAX INTEGER
      {
      valid(1),
      invalid(2),
      notsupport(3)
      }
      MAX-ACCESS read-only
      STATUS current
      DESCRIPTION
        "Indicates whether the value of hwLoopLineTestBGMinVForTest is valid.
         Options:
         1. valid(1)       -the value of hwLoopLineTestBGMinVForTest is valid
         2. invalid(2)     -the value of hwLoopLineTestBGMinVForTest is invalid
         3. notsupport(3)  -the value of hwLoopLineTestBGMinVForTest is not support
        "
      ::= { hwLoopLineTestOprEntry 186 }

    hwLoopLineTestABMaxVForTest OBJECT-TYPE
          SYNTAX Integer32
          MAX-ACCESS read-only
          STATUS current
          DESCRIPTION
            "Indicates the A->B max voltage in testing. 
             Unit: mV
            " 
          ::= { hwLoopLineTestOprEntry 187 }
    
    hwLoopLineTestABMaxVForTestFlag OBJECT-TYPE
      SYNTAX INTEGER
      {
      valid(1),
      invalid(2),
      notsupport(3)
      }
      MAX-ACCESS read-only
      STATUS current
      DESCRIPTION
        "Indicates whether the value of hwLoopLineTestABMaxVForTest is valid.
         Options:
         1. valid(1)       -the value of hwLoopLineTestABMaxVForTest is valid
         2. invalid(2)     -the value of hwLoopLineTestABMaxVForTest is invalid
         3. notsupport(3)  -the value of hwLoopLineTestABMaxVForTest is not support
        "
      ::= { hwLoopLineTestOprEntry 188 }

    hwLoopLineTestABMinVForTest OBJECT-TYPE
          SYNTAX Integer32
          MAX-ACCESS read-only
          STATUS current
          DESCRIPTION
            "Indicates the A->ground min voltage in testing. 
             Unit: mV
            " 
          ::= { hwLoopLineTestOprEntry 189 }
    
    hwLoopLineTestABMinVForTestFlag OBJECT-TYPE
      SYNTAX INTEGER
      {
      valid(1),
      invalid(2),
      notsupport(3)
      }
      MAX-ACCESS read-only
      STATUS current
      DESCRIPTION
        "Indicates whether the value of hwLoopLineTestABMinVForTest is valid.
         Options:
         1. valid(1)       -the value of hwLoopLineTestABMinVForTest is valid
         2. invalid(2)     -the value of hwLoopLineTestABMinVForTest is invalid
         3. notsupport(3)  -the value of hwLoopLineTestABMinVForTest is not support
        "
      ::= { hwLoopLineTestOprEntry 190 }

    hwLoopLineTestAGMaxCForTest OBJECT-TYPE
          SYNTAX Integer32
          MAX-ACCESS read-only
          STATUS current
          DESCRIPTION
            "Indicates the A->ground max current. 
             Unit: uA
            " 
          ::= { hwLoopLineTestOprEntry 191 }
    
    hwLoopLineTestAGMaxCForTestFlag OBJECT-TYPE
      SYNTAX INTEGER
      {
      valid(1),
      invalid(2),
      notsupport(3)
      }
      MAX-ACCESS read-only
      STATUS current
      DESCRIPTION
        "Indicates whether the value of hwLoopLineTestAGMaxCForTest is valid.
         Options:
         1. valid(1)       -the value of hwLoopLineTestAGMaxCForTest is valid
         2. invalid(2)     -the value of hwLoopLineTestAGMaxCForTest is invalid
         3. notsupport(3)  -the value of hwLoopLineTestAGMaxCForTest is not support
        "
      ::= { hwLoopLineTestOprEntry 192 }

    hwLoopLineTestAGMinCForTest OBJECT-TYPE
          SYNTAX Integer32
          MAX-ACCESS read-only
          STATUS current
          DESCRIPTION
            "Indicates the A->ground min current. 
             Unit: uA
            " 
          ::= { hwLoopLineTestOprEntry 193 }
    
    hwLoopLineTestAGMinCForTestFlag OBJECT-TYPE
      SYNTAX INTEGER
      {
      valid(1),
      invalid(2),
      notsupport(3)
      }
      MAX-ACCESS read-only
      STATUS current
      DESCRIPTION
        "Indicates whether the value of hwLoopLineTestAGMinCForTest is valid.
         Options:
         1. valid(1)       -the value of hwLoopLineTestAGMinCForTest is valid
         2. invalid(2)     -the value of hwLoopLineTestAGMinCForTest is invalid
         3. notsupport(3)  -the value of hwLoopLineTestAGMinCForTest is not support
        "
      ::= { hwLoopLineTestOprEntry 194 }
         
    hwLoopLineTestBGMaxCForTest OBJECT-TYPE
          SYNTAX Integer32
          MAX-ACCESS read-only
          STATUS current
          DESCRIPTION
            "Indicates the B->ground max current. 
             Unit: uA
            " 
          ::= { hwLoopLineTestOprEntry 195 }
    
    hwLoopLineTestBGMaxCForTestFlag OBJECT-TYPE
      SYNTAX INTEGER
      {
      valid(1),
      invalid(2),
      notsupport(3)
      }
      MAX-ACCESS read-only
      STATUS current
      DESCRIPTION
        "Indicates whether the value of hwLoopLineTestBGMaxCForTest is valid.
         Options:
         1. valid(1)       -the value of hwLoopLineTestBGMaxCForTest is valid
         2. invalid(2)     -the value of hwLoopLineTestBGMaxCForTest is invalid
         3. notsupport(3)  -the value of hwLoopLineTestBGMaxCForTest is not support
        "
      ::= { hwLoopLineTestOprEntry 196 }

    hwLoopLineTestBGMinCForTest OBJECT-TYPE
          SYNTAX Integer32
          MAX-ACCESS read-only
          STATUS current
          DESCRIPTION
            "Indicates the B->ground min current. 
             Unit: uA
            " 
          ::= { hwLoopLineTestOprEntry 197 }
    
    hwLoopLineTestBGMinCForTestFlag OBJECT-TYPE
      SYNTAX INTEGER
      {
      valid(1),
      invalid(2),
      notsupport(3)
      }
      MAX-ACCESS read-only
      STATUS current
      DESCRIPTION
        "Indicates whether the value of hwLoopLineTestBGMinCForTest is valid.
         Options:
         1. valid(1)       -the value of hwLoopLineTestBGMinCForTest is valid
         2. invalid(2)     -the value of hwLoopLineTestBGMinCForTest is invalid
         3. notsupport(3)  -the value of hwLoopLineTestBGMinCForTest is not support
        "
      ::= { hwLoopLineTestOprEntry 198 }

    hwLoopLineTestABMaxCForTest OBJECT-TYPE
          SYNTAX Integer32
          MAX-ACCESS read-only
          STATUS current
          DESCRIPTION
            "Indicates the A->B max current 
             Unit: uA
            " 
          ::= { hwLoopLineTestOprEntry 199 }
    
    hwLoopLineTestABMaxCForTestFlag OBJECT-TYPE
      SYNTAX INTEGER
      {
      valid(1),
      invalid(2),
      notsupport(3)
      }
      MAX-ACCESS read-only
      STATUS current
      DESCRIPTION
        "Indicates whether the value of hwLoopLineTestABMaxCForTest is valid.
         Options:
         1. valid(1)       -the value of hwLoopLineTestABMaxCForTest is valid
         2. invalid(2)     -the value of hwLoopLineTestABMaxCForTest is invalid
         3. notsupport(3)  -the value of hwLoopLineTestABMaxCForTest is not support
        "
      ::= { hwLoopLineTestOprEntry 200 }

    hwLoopLineTestABMaxNegCForTest OBJECT-TYPE
          SYNTAX Integer32
          MAX-ACCESS read-only
          STATUS current
          DESCRIPTION
            "Indicates the A->ground min current 
             Unit: uA
            " 
          ::= { hwLoopLineTestOprEntry 201 }
    
    hwLoopLineTestABMaxNegCForTestFlag OBJECT-TYPE
      SYNTAX INTEGER
      {
      valid(1),
      invalid(2),
      notsupport(3)
      }
      MAX-ACCESS read-only
      STATUS current
      DESCRIPTION
        "Indicates whether the value of hwLoopLineTestABMaxNegCForTest is valid.
         Options:
         1. valid(1)       -the value of hwLoopLineTestABMaxNegCForTest is valid
         2. invalid(2)     -the value of hwLoopLineTestABMaxNegCForTest is invalid
         3. notsupport(3)  -the value of hwLoopLineTestABMaxNegCForTest is not support
        "
      ::= { hwLoopLineTestOprEntry 202 }

    hwLoopLineTestLineALength OBJECT-TYPE
          SYNTAX Integer32
          MAX-ACCESS read-only
          STATUS current
          DESCRIPTION
            "Indicates length of line A 
             Unit: m
            " 
          ::= { hwLoopLineTestOprEntry 203 }
         
    hwLoopLineTestLineBLength OBJECT-TYPE
          SYNTAX Integer32
          MAX-ACCESS read-only
          STATUS current
          DESCRIPTION
            "Indicates length of line B 
             Unit: m
            " 
          ::= { hwLoopLineTestOprEntry 204 }
                        
   hwLoopLineTestTermimalConcusion  OBJECT-TYPE
          SYNTAX INTEGER
          {     
            noPhone(1),                   
            offHook(2),                   
            eTSIxDSLsignature(3),         
            abMixed(4) ,                  
            rcNetWork(5) ,
            elecRing(6),                  
            other(7) ,
            abMixInMDF(8) ,               
            abMixOutMDF(9) ,              
            invalid(-1)           
          }
          MAX-ACCESS read-only
          STATUS current
          DESCRIPTION
            "Indicates Termimal Concusion 
             Options:
             1. noPhone(1)                      -the TermimalConcusion is not connect Phone 
             2. offHook(2)                      -the TermimalConcusion is connect phone and offhook
             3. eTSIxDSLsignature(3)            -the TermimalConcusion is ETSI XDSL Signature 
             4. abMixed(4)                      -the TermimalConcusion is ab line short
             5. rcNetWork(5)                    -the TermimalConcusion is rcNetWork
             6. elecRing(6)                     -the TermimalConcusion is elecRing
             7. other(7)                        -the TermimalConcusion is other unknown terminal 
             8. abMixInMDF(8)                   -the TermimalConcusion is abMixInMDF
             9. abMixOutMDF(9)                  -the TermimalConcusion is abMixOutMDF
             10. invalid(-1)                     -the TermimalConcusion is invalid 
            " 
          ::= { hwLoopLineTestOprEntry 205 } 
          
   hwLoopLineTestMoreDataFlag  OBJECT-TYPE
          SYNTAX INTEGER
          {
            more(1),
            invalid(-1)
          }
          MAX-ACCESS read-only
          STATUS current
          DESCRIPTION
            "Indicates is there more data 
             Options:
             1. more(1)               -Indicates there is more data needs report,but needs a SNMP-GET oper. to get other data. 
             2. invalid(-1)           -Indicates the value is invalid 
            " 
          ::= { hwLoopLineTestOprEntry 206 } 
          
   hwLoopLineTestCtrLV  OBJECT-TYPE
          SYNTAX Integer32
          MAX-ACCESS read-only
          STATUS current
          DESCRIPTION
            "Aggregate tip-ring capacitance: CtrLV = Cco + Ctr + Cring, measured by means of low voltage ramps,
             such that it does NOT include the capacitance Csig whenever the ETSI Signature terminates the subscriber loop.
             Unit: nF
            "
          ::= { hwLoopLineTestOprEntry 207 }
  
   hwLoopLineTestCtrLVFlag  OBJECT-TYPE
          SYNTAX INTEGER
          {
          valid(1),
          invalid(2),
          notsupport(3)
          }
          MAX-ACCESS read-only
          STATUS current
          DESCRIPTION
            "Indicates whether the value of hwLoopLineTestCtrLV is valid.
             Options:
             1. valid(1)       -the value of hwLoopLineTestCtrLV is valid 
             2. invalid(2)     -the value of hwLoopLineTestCtrLV is invalid
             3. notsupport(3)  -the value of hwLoopLineTestCtrLV is not support
            "
          ::= { hwLoopLineTestOprEntry 208 }

   hwLoopLineTestCtrHV  OBJECT-TYPE
          SYNTAX Integer32
          MAX-ACCESS read-only
          STATUS current
          DESCRIPTION
            "Aggregate tip-ring capacitance: CtrHV = Cco + Ctr + Cring + Csig, measured by means of high voltage ramps.
             It includes the capacitance Csig of an ETSI Signature whenever connected to the tip and ring wires.
             Unit: nF
            "
          ::= { hwLoopLineTestOprEntry 209 }
  
   hwLoopLineTestCtrHVFlag  OBJECT-TYPE
          SYNTAX INTEGER
          {
          valid(1),
          invalid(2),
          notsupport(3)
          }
          MAX-ACCESS read-only
          STATUS current
          DESCRIPTION
            "Indicates whether the value of hwLoopLineTestCtrHV is valid.
             Options:
             1. valid(1)       -the value of hwLoopLineTestCtrHV is valid 
             2. invalid(2)     -the value of hwLoopLineTestCtrHV is invalid
             3. notsupport(3)  -the value of hwLoopLineTestCtrHV is not support
            "
          ::= { hwLoopLineTestOprEntry 210 }

   hwLoopLineTestCtrAc  OBJECT-TYPE
          SYNTAX Integer32
          MAX-ACCESS read-only
          STATUS current
          DESCRIPTION
            "Aggregate tip-ring capacitance: CtrAc = Cco + Ctr + Cring, measured by means of a low amplitude
             AC signal (either 25 Hz or 275 Hz). It does NOT include Csig.
             Unit: nF
            "
          ::= { hwLoopLineTestOprEntry 211 }
  
   hwLoopLineTestCtrAcFlag  OBJECT-TYPE
          SYNTAX INTEGER
          {
          valid(1),
          invalid(2),
          notsupport(3)
          }
          MAX-ACCESS read-only
          STATUS current
          DESCRIPTION
            "Indicates whether the value of hwLoopLineTestCtrAc is valid.
             Options:
             1. valid(1)       -the value of hwLoopLineTestCtrAc is valid 
             2. invalid(2)     -the value of hwLoopLineTestCtrAc is invalid
             3. notsupport(3)  -the value of hwLoopLineTestCtrAc is not support
            "
          ::= { hwLoopLineTestOprEntry 212 }

   hwLoopLineTestRtgSer  OBJECT-TYPE
          SYNTAX Integer32
          MAX-ACCESS read-only
          STATUS current
          DESCRIPTION
            "Resistance in series with Ctg, measured at the selected AC frequency (either 25 Hz or 275 Hz)
             by means of a low amplitude AC signal.
             Unit: ohm
            "
          ::= { hwLoopLineTestOprEntry 213 }
  
   hwLoopLineTestRtgSerFlag  OBJECT-TYPE
          SYNTAX INTEGER
          {
          valid(1),
          invalid(2),
          notsupport(3)
          }
          MAX-ACCESS read-only
          STATUS current
          DESCRIPTION
            "Indicates whether the value of hwLoopLineTestRtgSer is valid.
             Options:
             1. valid(1)       -the value of hwLoopLineTestRtgSer is valid 
             2. invalid(2)     -the value of hwLoopLineTestRtgSer is invalid
             3. notsupport(3)  -the value of hwLoopLineTestRtgSer is not support
            "
          ::= { hwLoopLineTestOprEntry 214 }

   hwLoopLineTestRrgSer  OBJECT-TYPE
          SYNTAX Integer32
          MAX-ACCESS read-only
          STATUS current
          DESCRIPTION
            "Resistance in series with Crg, measured at the selected AC frequency (either 25 Hz or 275 Hz)
             by means of a low amplitude AC signal.
             Unit: ohm
            "
          ::= { hwLoopLineTestOprEntry 215 }
  
   hwLoopLineTestRrgSerFlag  OBJECT-TYPE
          SYNTAX INTEGER
          {
          valid(1),
          invalid(2),
          notsupport(3)
          }
          MAX-ACCESS read-only
          STATUS current
          DESCRIPTION
            "Indicates whether the value of hwLoopLineTestRrgSer is valid.
             Options:
             1. valid(1)       -the value of hwLoopLineTestRrgSer is valid 
             2. invalid(2)     -the value of hwLoopLineTestRrgSer is invalid
             3. notsupport(3)  -the value of hwLoopLineTestRrgSer is not support
            "
          ::= { hwLoopLineTestOprEntry 216 }

   hwLoopLineTestRtrSer  OBJECT-TYPE
          SYNTAX Integer32
          MAX-ACCESS read-only
          STATUS current
          DESCRIPTION
            "Resistance in series with Ctring, measured at the selected AC frequency (either 25 Hz or 275 Hz)
             by means of a low amplitude AC signal.
             Unit: ohm
            "
          ::= { hwLoopLineTestOprEntry 217 }
  
   hwLoopLineTestRtrSerFlag  OBJECT-TYPE
          SYNTAX INTEGER
          {
          valid(1),
          invalid(2),
          notsupport(3)
          }
          MAX-ACCESS read-only
          STATUS current
          DESCRIPTION
            "Indicates whether the value of hwLoopLineTestRtrSer is valid.
             Options:
             1. valid(1)       -the value of hwLoopLineTestRtrSer is valid 
             2. invalid(2)     -the value of hwLoopLineTestRtrSer is invalid
             3. notsupport(3)  -the value of hwLoopLineTestRtrSer is not support
            "
          ::= { hwLoopLineTestOprEntry 218 }

   hwLoopLineTestUtgAcAdmit  OBJECT-TYPE
          SYNTAX Integer32
          MAX-ACCESS read-only
          STATUS current
          DESCRIPTION
            "Amplitude of the AC signal (either 25 Hz or 275 Hz) applied to the tipground admittance Ytg = Gtg + i * Btg.
             Unit: V
            "
          ::= { hwLoopLineTestOprEntry 219 }
  
   hwLoopLineTestUtgAcAdmitFlag  OBJECT-TYPE
          SYNTAX INTEGER
          {
          valid(1),
          invalid(2),
          notsupport(3)
          }
          MAX-ACCESS read-only
          STATUS current
          DESCRIPTION
            "Indicates whether the value of hwLoopLineTestUtgAcAdmit is valid.
             Options:
             1. valid(1)       -the value of hwLoopLineTestUtgAcAdmit is valid 
             2. invalid(2)     -the value of hwLoopLineTestUtgAcAdmit is invalid
             3. notsupport(3)  -the value of hwLoopLineTestUtgAcAdmit is not support
            "
          ::= { hwLoopLineTestOprEntry 220 }

   hwLoopLineTestUrgAcAdmit  OBJECT-TYPE
          SYNTAX Integer32
          MAX-ACCESS read-only
          STATUS current
          DESCRIPTION
            "Amplitude of the AC signal (either 25 Hz or 275 Hz) applied to the ringground admittance Yrg = Grg + i * Brg.
             Unit: V
            "
          ::= { hwLoopLineTestOprEntry 221 }
  
   hwLoopLineTestUrgAcAdmitFlag  OBJECT-TYPE
          SYNTAX INTEGER
          {
          valid(1),
          invalid(2),
          notsupport(3)
          }
          MAX-ACCESS read-only
          STATUS current
          DESCRIPTION
            "Indicates whether the value of hwLoopLineTestUrgAcAdmit is valid.
             Options:
             1. valid(1)       -the value of hwLoopLineTestUrgAcAdmit is valid 
             2. invalid(2)     -the value of hwLoopLineTestUrgAcAdmit is invalid
             3. notsupport(3)  -the value of hwLoopLineTestUrgAcAdmit is not support
            "
          ::= { hwLoopLineTestOprEntry 222 }

   hwLoopLineTestUtrAcAdmit  OBJECT-TYPE
          SYNTAX Integer32
          MAX-ACCESS read-only
          STATUS current
          DESCRIPTION
            "Amplitude of the AC signal (either 25 Hz or 275 Hz) applied to the tip-ring admittance Ytr = Gtr + i * Btr.
             Unit: V
            "
          ::= { hwLoopLineTestOprEntry 223 }
  
   hwLoopLineTestUtrAcAdmitFlag  OBJECT-TYPE
          SYNTAX INTEGER
          {
          valid(1),
          invalid(2),
          notsupport(3)
          }
          MAX-ACCESS read-only
          STATUS current
          DESCRIPTION
            "Indicates whether the value of hwLoopLineTestUtrAcAdmit is valid.
             Options:
             1. valid(1)       -the value of hwLoopLineTestUtrAcAdmit is valid 
             2. invalid(2)     -the value of hwLoopLineTestUtrAcAdmit is invalid
             3. notsupport(3)  -the value of hwLoopLineTestUtrAcAdmit is not support
            "
          ::= { hwLoopLineTestOprEntry 224 }

   hwLoopLineTestCapterminal  OBJECT-TYPE
          SYNTAX INTEGER
          {
          noexist(1),
          exist(2)
          }
          MAX-ACCESS read-only
          STATUS current
          DESCRIPTION
            "A capacitive termination of the access line shall be identified by the capacitance measurement and the associated evaluation.
             The following average value for the capacitance Cabk of the measured cable can be assumed:
             Cabk = 0.083(Cae + Cbe).
             If the measured capacitance is Cab > Cabk + 50 nF for ADSL&VDSL, or Cab > Cabk + 100 nF for SHDSL, respectively, 
             It can be assumed that a terminal device with a significant self-capacitance is connected to the line.
             The cable-factor 0.083 is determined by hwLoopLineTestSysConfigCableFactor.
             Options:
             1. noexist(1)     -Significant terminal device capacitance is not detected
             2. exist(2)       -Significant terminal device capacitance is detected
            "
          ::= { hwLoopLineTestOprEntry 225 }

   hwLoopLineTestCapterminalFlag  OBJECT-TYPE
          SYNTAX INTEGER
          {
          valid(1),
          invalid(2),
          notsupport(3)
          }
          MAX-ACCESS read-only
          STATUS current
          DESCRIPTION
            "Indicates whether the value of hwLoopLineTestCapterminal is valid.
             Options:
             1. valid(1)       -the value of hwLoopLineTestCapterminal is valid 
             2. invalid(2)     -the value of hwLoopLineTestCapterminal is invalid
             3. notsupport(3)  -the value of hwLoopLineTestCapterminal is not support
            "
          ::= { hwLoopLineTestOprEntry 226 }

    hwMeterTestOprTable OBJECT-TYPE
      SYNTAX SEQUENCE OF HwMeterTestOprEntry
      MAX-ACCESS not-accessible
      STATUS current
      DESCRIPTION 
        "Operation table of the meter test.
         It implements the meter test function in the system. The test board provides the interface connected to the external test meter such as a multimeter through the meter test function.
         The index of this table is ifIndex.
        "
      ::= { hwTestCommonMIBObjects 3 }
    
    hwMeterTestOprEntry OBJECT-TYPE
      SYNTAX HwMeterTestOprEntry
      MAX-ACCESS not-accessible
      STATUS current
      DESCRIPTION
        "Operation table of the meter test.
         It implements the meter test function in the system. The test board provides the interface connected to the external test meter such as a multimeter through the meter test function.
         The index of this entry is ifIndex.
        "
      INDEX { ifIndex }
      ::= { hwMeterTestOprTable 1 }
    
    HwMeterTestOprEntry ::=
      SEQUENCE 
      { 
        hwMeterTestOprType
          INTEGER,
        hwMeterTestItem
          INTEGER,
        hwMeterTestStatus
          INTEGER,
        hwMeterTestBusyFlag
          INTEGER
      }

    hwMeterTestOprType OBJECT-TYPE
      SYNTAX INTEGER
      {
        stop(1),
        start(2)
      }
      MAX-ACCESS read-create
      STATUS current
      DESCRIPTION
        "Operation type.
         Options:
         1. stop(1)        -operation type is stop
         2. start(2)       -operation type is start
        "
      ::= { hwMeterTestOprEntry 1 }
    
    hwMeterTestItem OBJECT-TYPE
      SYNTAX INTEGER
      {
        inline(1),
        outline(2)
      }
      MAX-ACCESS read-create
      STATUS current
      DESCRIPTION
        "Test items.
         Options:
         1. inline(1)        -in test
         2. outline(2)       -out test
        "
      ::= { hwMeterTestOprEntry 2 }
    
    hwMeterTestStatus OBJECT-TYPE
      SYNTAX INTEGER
      {
        success(1),
        fail(2),
        portbusy(3),
        outoftime(4),
        testingAbnormal(5),
        broadbandtesting(6),capturefail(7),notratb(8)
      }
      MAX-ACCESS read-only
      STATUS current
      DESCRIPTION
        "Test status.
         Options:
         1. success(1)                   -no test on busy
         2. fail(2)                      -remedy test on busy
         3. portbusy(3)                  -forced test on busy
         4. outoftime(4)                 -test out of time
         5. testingAbnormal(5)           -test abnormal 
         6. broadbandtesting(6)          -broadband testing
         7. capturefail(7)               -capture fail
         8. notratb(8)                   -relay transfer board not exist
        "
      ::= { hwMeterTestOprEntry 3 }
    
    hwMeterTestBusyFlag OBJECT-TYPE
      SYNTAX INTEGER   
      {
        busyNoTest(1),
        busyTest(2),
        busystrenTest(3)
      }
      MAX-ACCESS  read-write
      STATUS current
      DESCRIPTION
        "Meter test busy flag.
         Options:
         1. busyNoTest(1)        -no test on busy
         2. busyTest(2)          -test on busy
         3. busystrenTest(3)     -forced test on busy
       "
      ::= { hwMeterTestOprEntry 4 }

    hwTestBoardDiagnoseTestOprTable OBJECT-TYPE
      SYNTAX SEQUENCE OF HwTestBoardDiagnoseTestOprEntry
      MAX-ACCESS not-accessible
      STATUS current
      DESCRIPTION
        "Operation table of the self-test on the test board.
         It implements the self-test on the test board in the system. The self-test checks whether the test board can work in the normal state.
         The index of this table is ifIndex.
        "
      ::= { hwTestCommonMIBObjects 4 }
    
    hwTestBoardDiagnoseTestOprEntry OBJECT-TYPE
      SYNTAX HwTestBoardDiagnoseTestOprEntry
      MAX-ACCESS not-accessible
      STATUS current
      DESCRIPTION 
        "Operation table of the self-test on the test board.
         It implements the self-test on the test board in the system. The self-test checks whether the test board can work in the normal state.
         The index of this entry is ifIndex.
        "
      INDEX { ifIndex }
      ::= { hwTestBoardDiagnoseTestOprTable 1 }
    
    HwTestBoardDiagnoseTestOprEntry ::=
      SEQUENCE 
      { 
        hwTestBoardDiagnoseTestOprType
          INTEGER,
        hwTestBoardDiagnoseTestResult
          INTEGER,
        hwTestBoardDiagnoseTestRAM
          INTEGER,
        hwTestBoardDiagnoseTestVoltage
          INTEGER,
        hwTestBoardDiagnoseTestResistance
          INTEGER,
        hwTestBoardDiagnoseTestSignal
          INTEGER,
        hwTestBoardDiagnoseTestDTMF
          INTEGER,
        hwTestBoardDiagnoseTestRing
          INTEGER,
        hwTestBoardDiagnoseTestOnOffHook
          INTEGER,
        hwTestBoardDiagnoseTestPole
          INTEGER,
        hwTestBoardDiagnoseTestISDNU
          INTEGER,
        hwTestBoardDiagnoseTestBitErrCode
          INTEGER,
        hwTestBoardDiagnoseTestCapacitance
          INTEGER
      }

    hwTestBoardDiagnoseTestOprType OBJECT-TYPE
      SYNTAX INTEGER { start(2) }
      MAX-ACCESS read-create
      STATUS current
      DESCRIPTION
        "Operation type.
         Options:
         1. start(2)    -operation type is start
        "
      ::= { hwTestBoardDiagnoseTestOprEntry 1 }
    
    hwTestBoardDiagnoseTestResult OBJECT-TYPE
      SYNTAX INTEGER
      {
        selfTestOver(1),
        selfTestFail(2),
        testingAbnormal(3)
      }
      MAX-ACCESS read-only
      STATUS current
      DESCRIPTION
        "Self-diagnosis result.
         Options:
         1. selfTestOver(1)      -self-diagnosis successful
         2. selfTestFail(2)      -self-diagnosis failure  
         3. testingAbnormal(3)   -test abnormal
       "
      ::= { hwTestBoardDiagnoseTestOprEntry 2 }
    
    hwTestBoardDiagnoseTestRAM OBJECT-TYPE
      SYNTAX INTEGER
      {
        normal(1),
        abnormal(2)
      }
      MAX-ACCESS read-only
      STATUS current
      DESCRIPTION
        "System RAMRAM.
         Options:
         1. normal(1)       -normal
         2. abnormal(2)     -abnormal
        "
      ::= { hwTestBoardDiagnoseTestOprEntry 3 }
    
    hwTestBoardDiagnoseTestVoltage OBJECT-TYPE
      SYNTAX INTEGER
      {
        normal(1),
        abnormal(2)
      }
      MAX-ACCESS read-only
      STATUS current
      DESCRIPTION
        "Voltage.
         Options:
         1. normal(1)       -normal
         2. abnormal(2)     -abnormal
        "
      ::= { hwTestBoardDiagnoseTestOprEntry 4 }
    
    hwTestBoardDiagnoseTestResistance OBJECT-TYPE
      SYNTAX INTEGER
      {
        normal(1),
        abnormal(2)
      }
      MAX-ACCESS read-only
      STATUS current
      DESCRIPTION
        "Resistance.
         Options:
         1. normal(1)       -normal
         2. abnormal(2)     -abnormal
        "
      ::= { hwTestBoardDiagnoseTestOprEntry 5 }
    
    hwTestBoardDiagnoseTestSignal OBJECT-TYPE
      SYNTAX INTEGER
      {
        normal(1),
        abnormal(2)
      }
      MAX-ACCESS read-only
      STATUS current
      DESCRIPTION
        "Signal circuit.
         Options:
         1. normal(1)       -normal
         2. abnormal(2)     -abnormal
        "
      ::= { hwTestBoardDiagnoseTestOprEntry 6 }
    
    hwTestBoardDiagnoseTestDTMF OBJECT-TYPE
      SYNTAX INTEGER
      {
        normal(1),
        abnormal(2)
      }
      MAX-ACCESS read-only
      STATUS current
      DESCRIPTION
        "DTMF.
         Options:
         1. normal(1)       -normal
         2. abnormal(2)     -abnormal
        "
      ::= { hwTestBoardDiagnoseTestOprEntry 7 }
    
    hwTestBoardDiagnoseTestRing OBJECT-TYPE
      SYNTAX INTEGER
      {
        normal(1),
        abnormal(2)
      }
      MAX-ACCESS read-only
      STATUS current
      DESCRIPTION
        "Ringing.
         Options:
         1. normal(1)       -normal
         2. abnormal(2)     -abnormal
        "
      ::= { hwTestBoardDiagnoseTestOprEntry 8 }
    
    hwTestBoardDiagnoseTestOnOffHook OBJECT-TYPE
      SYNTAX INTEGER
      {
        normal(1),
        abnormal(2)
      }
      MAX-ACCESS read-only
      STATUS current
      DESCRIPTION
        "On/off hook.
         Options:
         1. normal(1)       -normal
         2. abnormal(2)     -abnormal
        "
      ::= { hwTestBoardDiagnoseTestOprEntry 9 }
    
    hwTestBoardDiagnoseTestPole OBJECT-TYPE
      SYNTAX INTEGER
      {
        normal(1),
        abnormal(2)
      }
      MAX-ACCESS read-only
      STATUS current
      DESCRIPTION
        "Polarity reversal.
         Options:
         1. normal(1)       -normal
         2. abnormal(2)     -abnormal
        "
      ::= { hwTestBoardDiagnoseTestOprEntry 10 }
    
    hwTestBoardDiagnoseTestISDNU OBJECT-TYPE
      SYNTAX INTEGER
      {
        normal(1),
        abnormal(2)
      }
      MAX-ACCESS read-only
      STATUS current
      DESCRIPTION
        "ISDN U port.
         Options:
         1. normal(1)       -normal
         2. abnormal(2)     -abnormal
        "
      ::= { hwTestBoardDiagnoseTestOprEntry 11 }
    
    hwTestBoardDiagnoseTestBitErrCode OBJECT-TYPE
      SYNTAX INTEGER
      {
        normal(1),
        abnormal(2)
      }
      MAX-ACCESS read-only
      STATUS current
      DESCRIPTION
        "Error code test.
         Options:
         1. normal(1)       -normal
         2. abnormal(2)     -abnormal
        "
      ::= { hwTestBoardDiagnoseTestOprEntry 12 }
          
    hwTestBoardDiagnoseTestCapacitance OBJECT-TYPE
      SYNTAX INTEGER
      {
        normal(1),
        abnormal(2)
      }
      MAX-ACCESS read-only
      STATUS current
      DESCRIPTION
        "Capacitance.
         Options:
         1. normal(1)       -normal
         2. abnormal(2)     -abnormal
        "
      ::= { hwTestBoardDiagnoseTestOprEntry 13 }
      
    hwTestBoardStatusQueryOprTable OBJECT-TYPE
      SYNTAX SEQUENCE OF HwTestBoardStatusQueryOprEntry
      MAX-ACCESS not-accessible
      STATUS current
      DESCRIPTION
        "Operation table for querying the status of the test board.
         It implements the function of querying the status of the test board in the system. You can query the current status of the test board through this function.
         The index of this table is ifIndex.
        "
      ::= { hwTestCommonMIBObjects 5 }
    
    hwTestBoardStatusQueryOprEntry OBJECT-TYPE
      SYNTAX HwTestBoardStatusQueryOprEntry
      MAX-ACCESS not-accessible
      STATUS current
      DESCRIPTION
        "Operation table for querying the status of the test board.
         It implements the function of querying the status of the test board in the system. You can query the current status of the test board through this function.
         The index of this entry is ifIndex.
        "
      INDEX { ifIndex }
      ::= { hwTestBoardStatusQueryOprTable 1 }
    
    HwTestBoardStatusQueryOprEntry ::=
      SEQUENCE 
      { 
        hwTestBoardStatusQueryOprType
          INTEGER,
        hwTestBoardStatusQueryResult
          INTEGER,
        hwTestBoardStatusQueryVersion
          Integer32,
        hwTestBoardStatusQueryTestItem
          INTEGER,
        hwTestBoardStatusTestedBoardIfIndex
          Integer32
       }

    hwTestBoardStatusQueryOprType OBJECT-TYPE
      SYNTAX INTEGER { beginQuery(2) }
      MAX-ACCESS read-create
      STATUS current
      DESCRIPTION
        "Operation type.
         Options:
         1. beginQuery(2)       -start
        " 
      ::= { hwTestBoardStatusQueryOprEntry 1 }
    
    hwTestBoardStatusQueryResult OBJECT-TYPE
      SYNTAX INTEGER
      {
        querySuccess(1),
        queryFail(2)
      }
      MAX-ACCESS read-only
      STATUS current
      DESCRIPTION
        "Query status.
         Options:
         1. querySuccess(1)     -query status successful 
         2. queryFail(2)        -query status failure
        "
      ::= { hwTestBoardStatusQueryOprEntry 2 }
    
    hwTestBoardStatusQueryVersion OBJECT-TYPE
      SYNTAX Integer32
      MAX-ACCESS read-only
      STATUS current
      DESCRIPTION
        "Version."
      ::= { hwTestBoardStatusQueryOprEntry 3 }
    
    hwTestBoardStatusQueryTestItem OBJECT-TYPE
      SYNTAX INTEGER
      {
        testIdle(1),
        pstnUserInLineTest(2),
        userLineTest(3),
        phoneTest(4),
        manTestOutLine(5),
        manTestInnerLine(6),
        halfAutoUserCircuit(7),
        halfAutoTssPhoneCircuit(8),
        tssSelfTest(9),
        testInnerBus(10),
        testOuterBus(11),
        digUserOutLineTest(12),
        digUserInnerLineTest(13),
        switchToStandIsdnTerminal(14),
        switchToIsdnSpecialcode(15),
        testBoarDfault(16),
        pstnRemoteCallTest(17),  
        indialtest(18),
        coEmulate(33),
        cqtTest(34),
        cqtFRTest(35),
        cqtTDRTest(36),
        cqtDMTTest(37),
        cqtNSETest(38),
        cqtLBTest(39),
        cqtLCTest(40),
        internalcaptureTestedPort(61),
        externalcaptureTestedPort(62),
        monitorTest(63),
        seltTest(64),
        sendtoneTest(65),
        checktoneTest(66),
        autocalltest(67),
        anothermainboardistesting(241)
      } 
      MAX-ACCESS read-only
      STATUS current
      DESCRIPTION
        "Test item.
         Options:
         1. testIdle(1)                           -idle
         2. pstnUserInLineTest(2)                 -pstn inline test    
         3. userLineTest(3)                       -loop line test
         4. phoneTest(4)                          -telephone test
         5. manTestOutLine(5)                     -manual test outline
         6. manTestInnerLine(6)                   -manual test inline
         7. halfAutoUserCircuit(7)                -half auto tss user circuit
                                                  -meter interface
         8. halfAutoTssPhoneCircuit(8)            -half auto tss telephone circuit
                                                  -meter interface
         9. tssSelfTest(9)                        -Tss self test
         10. testInnerBus(10)                     -test inline bus test
         11. testOuterBus(11)                     -test outline bus test
         12. digUserOutLineTest(12)               -isdn outline test
         13. digUserInnerLineTest(13)             -isdn inline test
         14. switchToStandIsdnTerminal(14)        -switch to standard isdn terminal
         15. switchToIsdnSpecialcode(15)          -switch to isdn special service telephone number
         16. testBoarDfault(16)                   -test board fault
         17. pstnRemoteCallTest(17)               -pstn user remote call test 
         18. indialtest(18)                       -in-dial test                                          
         19. coEmulate(33)                        -CO simulation test
         20. cqtTest(34)                          -CQT test
         21. cqtFRTest(35)                        -CQT Frequency Response Measurement
         22. cqtTDRTest(36)                       -CQT Time Domain Reflectometry Measurement
         23. cqtDMTTest(37)                       -CQT Data Rate Prediction Measurement                 
         24. cqtNSETest(38)                       -CQT Noise Measurement
         25. cqtLBTest(39)                        -CQT Longitudinal Balance Measurement
         26. cqtLCTest(40)                        -CQT Load Coil Detection
         27. internalcaptureTestedPort(61)        -Capture tested port loopline 
         28. externalcaptureTestedPort(62)        -Capture tested port inline
         29. monitorTest(63)                      -monitor test
         30. seltTest(64)                         -selt test
         31. sendtoneTest(65)                     -tone send test 
         32. checktoneTest(66)                    -tone check test
         33. autocalltest(67)                     -auto call test
         34. anothermainboardistesting(241)       -another main board is testing 
      "
      ::= { hwTestBoardStatusQueryOprEntry 4 }
    
    hwTestBoardStatusTestedBoardIfIndex OBJECT-TYPE
      SYNTAX Integer32
      MAX-ACCESS read-only
      STATUS current
      DESCRIPTION
        "Index of the tested port."
      ::= { hwTestBoardStatusQueryOprEntry 5 }
   
    hwSearchingToneOprTable OBJECT-TYPE
      SYNTAX SEQUENCE OF HwSearchingToneOprEntry
      MAX-ACCESS not-accessible
      STATUS current
      DESCRIPTION
        "This table is used for enabling the searching tone test by setting the searching tone
         test voltage level, test frequency, and test duration. The searching tone test
         is to locate a specific line from various lines by transmitting pulse tones to lines.
         This test helps carriers locate faults and provision services.
         The index of this table is ifindex.
         "
      ::= { hwTestCommonMIBObjects 6 }
    
    -- 1.3.6.1.4.1.2011.6.21.1.1.1.6.1
    hwSearchingToneOprEntry OBJECT-TYPE
      SYNTAX HwSearchingToneOprEntry
      MAX-ACCESS not-accessible
      STATUS current
      DESCRIPTION      
        "This table is used for enabling the searching tone test by setting the searching tone
         test voltage level, test frequency, and test duration. The searching tone test
         is to locate a specific line from various lines by transmitting pulse tones to lines.
         This test helps carriers locate faults and provision services.
         The index of this entry is ifindex.
         "
      INDEX { ifIndex }
      ::= { hwSearchingToneOprTable 1 }
    
    HwSearchingToneOprEntry ::=
      SEQUENCE 
      { 
        hwSearchingToneOprType
          INTEGER,
        hwSearchingToneLevel
          Integer32,
        hwSearchingToneFrequency
          Integer32,
        hwSearchingToneDurationTime
          Integer32,
        hwSearchingToneRemainingTime
          Integer32,  
        hwSearchingToneBusyProcFlag
          INTEGER                                           
       }      

    hwSearchingToneOprType OBJECT-TYPE
      SYNTAX INTEGER
      {
        stop(1),
        start(2),
        invalid(-1)
      }
      MAX-ACCESS read-write
      STATUS current
      DESCRIPTION
        "Searching tone test-operation type. 
         Options:
         1. stop(1)     -stop a searching tone test 
         2. start(2)    -start a searching tone test
         3. invalid(-1) -invalid value
         "
      ::= { hwSearchingToneOprEntry 1 }       

    hwSearchingToneLevel OBJECT-TYPE
      SYNTAX Integer32 (-1 | 80..500)
      MAX-ACCESS read-write
      STATUS current      
      DESCRIPTION
        "Indicates the test voltage level of a searching tone test.
         Options:
         1. -1             -Invalid value
         2. 80..500        -(XDSL Range: 80-126  MXU voice Range: 80-500)
         Default: 120      -(XDSL Default: 120   MXU voice default:295)
         Unit: mV
        "
      DEFVAL { 120 }
      ::= { hwSearchingToneOprEntry 2 }   

    hwSearchingToneFrequency OBJECT-TYPE
      SYNTAX Integer32 (-1 | 300..3400)     
      MAX-ACCESS read-write
      STATUS current
      DESCRIPTION
        "Indicates the test frequency of a searching tone test.
         Default: 800
         Unit: Hz
         "
      DEFVAL { 800 }
      ::= { hwSearchingToneOprEntry 3 }   

    hwSearchingToneDurationTime OBJECT-TYPE
      SYNTAX Integer32 (-1 | 1..54000)      
      MAX-ACCESS read-write
      STATUS current
      DESCRIPTION
        "Indicates the test duration of a searching tone test. 
         Default: 9000
         Unit: 0.1s
        "
      DEFVAL { 9000 }
      ::= { hwSearchingToneOprEntry 4 }   

    hwSearchingToneRemainingTime OBJECT-TYPE
      SYNTAX Integer32      
      MAX-ACCESS read-only
      STATUS current
      DESCRIPTION
        "Indicates the test remaining time of a searching tone test.
         Unit: 0.1s 
        "
      ::= { hwSearchingToneOprEntry 5 }   
     
     hwSearchingToneBusyProcFlag OBJECT-TYPE
      SYNTAX INTEGER
      {
        cancel(1),
        force(2),
        invalid(-1)     
      }      
      MAX-ACCESS read-write
      STATUS current
      DESCRIPTION
        "Searching tone test-busy flag. 
         Options:
         1. cancel(1)   -when port is busy do not start a searching tone test
         2. force(2)    -when port is busy force to start a searching tone test  
         3. invalid(-1) -invalid value
         " 
      ::= { hwSearchingToneOprEntry 6 }  
      
    hwLoopLineTestCalibrationTable OBJECT-TYPE
      SYNTAX SEQUENCE OF HwLoopLineTestCalibrationEntry
      MAX-ACCESS not-accessible
      STATUS current
      DESCRIPTION
        "This table provides the test calibration data of a line. Before delivery,
         each port is performed with a test in which no user is connected to the
         port and the test result is saved as standard data. The standard data is used for
         calibrating the test result of tests in the actual environment.
         The index of this table is ifindex.
        "
      ::= { hwTestCommonMIBObjects 7 }
      
    hwLoopLineTestCalibrationEntry OBJECT-TYPE
      SYNTAX HwLoopLineTestCalibrationEntry
      MAX-ACCESS not-accessible
      STATUS current
      DESCRIPTION      
        "This table provides the test calibration data of a line. Before delivery,
         each port is performed with a test in which no user is connected to the
         port and the test result is saved as standard data. The standard data is used for
         calibrating the test result of tests in the actual environment.
         The index of this entry is ifindex.
        "
      INDEX { ifIndex }
      ::= { hwLoopLineTestCalibrationTable 1 }
      
    HwLoopLineTestCalibrationEntry ::=
      SEQUENCE
      { 
        hwLoopLineTestAGCalibration
          Integer32,
        hwLoopLineTestBGCalibration
          Integer32,
        hwLoopLineTestABCalibration
          Integer32
      }   
       
    hwLoopLineTestAGCalibration OBJECT-TYPE
      SYNTAX Integer32
      MAX-ACCESS read-only
      STATUS current      
      DESCRIPTION
        "Indicates the test calibration data of A->Ground capacitance.
         Unit: nF
        "
      ::= { hwLoopLineTestCalibrationEntry 1 }      

    hwLoopLineTestBGCalibration OBJECT-TYPE
      SYNTAX Integer32
      MAX-ACCESS read-only
      STATUS current      
      DESCRIPTION
        "Indicates the test calibration data of B->Ground capacitance.
         Unit: nF
        "
      ::= { hwLoopLineTestCalibrationEntry 2 }  

    hwLoopLineTestABCalibration OBJECT-TYPE
      SYNTAX Integer32
      MAX-ACCESS read-only
      STATUS current      
      DESCRIPTION
        "Indicates the test calibration data of A->B capacitance.
         Unit: nF
        "
      ::= { hwLoopLineTestCalibrationEntry 3 }    
      
    hwTestCommonTraps OBJECT IDENTIFIER ::= { hwTestCommon 2 }
    
    hwTestCommonTrapVbOids OBJECT IDENTIFIER ::= { hwTestCommonTraps 1 }
    
    hwTestCommonVbOidsReason OBJECT IDENTIFIER ::= { hwTestCommonTrapVbOids 2 }
    
    hwTestClearedReason OBJECT-TYPE
      SYNTAX INTEGER
      {
        testBoardFail(1),
        testedBoardFail(2),
        userCmd(3),
        switchOver(4),
        anotherMainBoardIsTesting(5),
        unknowError(255)
      }
      MAX-ACCESS accessible-for-notify
      STATUS current
      DESCRIPTION
        "Definition of the test-canceling reasons.
         Options:
         1. testBoardFail(1)              -the test-canceling reason is testBoardFail 
         2. testedBoardFail(2)            -the test-canceling reason is testedBoardFail
         3. userCmd(3)                    -the test-canceling reason is userCmd
         4. switchOver(4)                 -the test-canceling reason is switchOver
         5. anotherMainBoardIsTesting(5)  -the test-canceling reason is anotherMainBoardIsTesting
         6. unknowError(255)              -the test-canceling reason is unknowError
        "
      ::= { hwTestCommonVbOidsReason 1 }
    
    hwTestRingSrcAlarmReason OBJECT-TYPE
      SYNTAX INTEGER
      {
        testRingSrcFail(1),
        testRingSrcRestore(2)
      }
      MAX-ACCESS accessible-for-notify
      STATUS current
      DESCRIPTION
        "Definition of the ringing source alarms.
         Options:
         1. testRingSrcFail(1)         -the ringing source alarm is testRingSrcFail 
         2. testRingSrcRestore(2)      -the ringing source alarm is testRingSrcRestore
        "
      ::= { hwTestCommonVbOidsReason 2 }
      
    hwTestCommonRequestID OBJECT-TYPE
      SYNTAX Integer32
      MAX-ACCESS accessible-for-notify
      STATUS current
      DESCRIPTION
        "NMS request ID."
      ::= { hwTestCommonTrapVbOids 3 }
      
    hwTestMeltChipID OBJECT-TYPE
      SYNTAX Integer32
      MAX-ACCESS accessible-for-notify
      STATUS current
      DESCRIPTION
        "Melt chip ID."
      ::= { hwTestCommonTrapVbOids 4 }
    
    hwTestCommonAlarmTraps OBJECT IDENTIFIER ::= { hwTestCommonTraps 2 }
    
    hwTestCommonAlarmTrapsOIDs OBJECT IDENTIFIER ::= { hwTestCommonAlarmTraps 0 }
    
    hwTestRingSrcFailTrap NOTIFICATION-TYPE
      OBJECTS { hwTestBoardIfIndex, hwTestRingSrcAlarmReason }
      STATUS current
      DESCRIPTION 
        "The btss ring source failed trap:
        1: hwTestBoardIfIndex; 2: hwTestRingSrcAlarmReason (1: the ring source of BTSS doesn't work)
        Troubleshooting suggestions: (1) Check the BTSS board; (2) Reset the BTSS board; (3) Replace the BTSS board.
        This trap will send when the btss ring source failed."
      ::= { hwTestCommonAlarmTrapsOIDs 1 }
    
    hwTestRingSrcRestoreTrap NOTIFICATION-TYPE
      OBJECTS { hwTestBoardIfIndex, hwTestRingSrcAlarmReason }
      STATUS current
      DESCRIPTION 
        "Test ringing source restore trap:
        1: hwTestBoardIfIndex; 2: hwTestRingSrcAlarmReason (1: the ring source of BTSS is normal)
        The advice: none.
        This trap will send when test ringing source restore."
      ::= { hwTestCommonAlarmTrapsOIDs  2 }
    
    hwTestAutoClearedTrap NOTIFICATION-TYPE
      OBJECTS { hwTestBoardIfIndex, hwTestBoardStatusTestedBoardIfIndex, hwTestClearedReason }
      STATUS current
      DESCRIPTION 
        "Trap of test automatically cancelled:
        1: hwTestBoardIfIndex; 2: hwTestBoardStatusTestedBoardIfIndex; 3: hwTestClearedReason.
        This trap will send when the test automatically cancelled."
      ::= { hwTestCommonAlarmTrapsOIDs 3 }
      
    hwTestMeltChipFaultAlarmTrap NOTIFICATION-TYPE
      OBJECTS { hwFrameIndex, hwSlotIndex, hwTestMeltChipID, hwPortMeltChipStateList }
      STATUS current
      DESCRIPTION 
        "MELT chip fault trap:
        1: hwFrameIndex; 2: hwSlotIndex; 3: hwTestMeltChipID; 4: hwPortMeltChipStateList.
        When detecting a MELT chip fault, the system generates this trap."
      ::= { hwTestCommonAlarmTrapsOIDs 4 }
      
    hwTestMeltChipRecoveryAlarmTrap NOTIFICATION-TYPE
      OBJECTS { hwFrameIndex, hwSlotIndex, hwTestMeltChipID, hwPortMeltChipStateList }
      STATUS current
      DESCRIPTION 
        "MELT chip fault clear trap:
        1: hwFrameIndex; 2: hwSlotIndex; 3: hwTestMeltChipID; 4: hwPortMeltChipStateList.
        When detecting that a MELT chip fault is cleared, the system generates this trap."
      ::= { hwTestCommonAlarmTrapsOIDs 5 }
    
    hwTestCommonGeneralTraps OBJECT IDENTIFIER ::= { hwTestCommonTraps 3 }
    
    hwTestCommonGeneralTrapsOIDs OBJECT IDENTIFIER ::= { hwTestCommonGeneralTraps 0 }
    
    hwLoopLineTestTrap NOTIFICATION-TYPE
      OBJECTS 
      { 
       hwLoopLineTestRequestID, 
       hwLoopLineTestStatus, 
       hwLoopLineTestConclusion, 
       hwLoopLineTestACAG, 
       hwLoopLineTestACBG, 
       hwLoopLineTestACAB, 
       hwLoopLineTestDCAG, 
       hwLoopLineTestDCBG, 
       hwLoopLineTestDCAB, 
       hwLoopLineTestRAG, 
       hwLoopLineTestRBG, 
       hwLoopLineTestRAB, 
       hwLoopLineTestCapAG, 
       hwLoopLineTestCapBG, 
       hwLoopLineTestCapAB, 
       hwLoopLineTestLR, 
       hwLoopLineTestRABResPole,  
       hwLoopLineTestMSocket,  
       hwLoopLineTestPPAResult,
       hwLoopLineTestIfIndex,
       hwLoopLineTestMoreDataFlag
       }
      STATUS current
      DESCRIPTION 
        "This trap will be sent when a loop-line test finished successfully. The trap shows 
         the result of the loop-line test.
         1. hwLoopLineTestRequestID, 
         2. hwLoopLineTestStatus, 
         3. hwLoopLineTestConclusion, 
         4. hwLoopLineTestACAG, 
         5. hwLoopLineTestACBG, 
         6. hwLoopLineTestACAB, 
         7. hwLoopLineTestDCAG, 
         8. hwLoopLineTestDCBG, 
         9. hwLoopLineTestDCAB, 
         10. hwLoopLineTestRAG, 
         11. hwLoopLineTestRBG, 
         12. hwLoopLineTestRAB, 
         13. hwLoopLineTestCapAG, 
         14. hwLoopLineTestCapBG, 
         15. hwLoopLineTestCapAB, 
         16. hwLoopLineTestLR, 
         17. hwLoopLineTestRABResPole,
         18. hwLoopLineTestMSocket,  
         19. hwLoopLineTestPPAResult,
         19. hwLoopLineTestIfIndex,
         20. hwLoopLineTestMoreDataFlag
        "
      ::= { hwTestCommonGeneralTrapsOIDs 1 }
    
    hwMeterTestTrap NOTIFICATION-TYPE
      OBJECTS { hwMeterTestStatus }
      STATUS current
      DESCRIPTION 
        "Meter test result trap: 1: hwMeterTestStatus.
         This trap will send when meter test result return."
      ::= { hwTestCommonGeneralTrapsOIDs 2 }
    
    hwTestBoardDiagnoseTestTrap NOTIFICATION-TYPE
      OBJECTS { hwTestBoardDiagnoseTestResult, hwTestBoardDiagnoseTestRAM, hwTestBoardDiagnoseTestVoltage, hwTestBoardDiagnoseTestResistance, hwTestBoardDiagnoseTestSignal, 
        hwTestBoardDiagnoseTestDTMF, hwTestBoardDiagnoseTestRing, hwTestBoardDiagnoseTestOnOffHook, hwTestBoardDiagnoseTestPole, hwTestBoardDiagnoseTestISDNU, 
        hwTestBoardDiagnoseTestBitErrCode, hwTestBoardDiagnoseTestCapacitance }
      STATUS current
      DESCRIPTION 
        "Test board self-test result trap:
        1: hwTestBoardDiagnoseTestResult; 2: hwTestBoardDiagnoseTestRAM; 3: hwTestBoardDiagnoseTestVoltage; 
        4: hwTestBoardDiagnoseTestResistance; 
        5: hwTestBoardDiagnoseTestSignal; 6: hwTestBoardDiagnoseTestDTMF; 7: hwTestBoardDiagnoseTestRing; 
        8: hwTestBoardDiagnoseTestOnOffHook; 
        9: hwTestBoardDiagnoseTestPole; 10: hwTestBoardDiagnoseTestISDNU; 11: hwTestBoardDiagnoseTestBitErrCode; 
        12: hwTestBoardDiagnoseTestCapacitance.
        This trap will send when the test board self-test result return."
      ::= { hwTestCommonGeneralTrapsOIDs 3 }
    
    hwTestBoardStatusQueryTrap NOTIFICATION-TYPE
      OBJECTS { hwTestBoardStatusQueryResult, hwTestBoardStatusQueryVersion, 
          hwTestBoardStatusQueryTestItem, hwTestBoardStatusTestedBoardIfIndex }
      STATUS current
      DESCRIPTION 
        "Test board status query result trap:
        1: hwTestBoardStatusQueryResult; 2: hwTestBoardStatusQueryVersion; 3: hwTestBoardStatusQueryTestItem; 
        4: hwTestBoardStatusTestedBoardIfIndex.
        This trap will send when the test board status query result return."
      ::= { hwTestCommonGeneralTrapsOIDs 4 }
      
    hwTestOntPotsTestResultTrap NOTIFICATION-TYPE
      OBJECTS 
      { 
        hwTestCommonRequestID,
        ifIndex,
        hwONTPotsTestONTIndex,
        hwONTPotsTestONTPstnPortIndex,
        hwONTPotsTestItem,
        hwONTPotsTestHazardousVoltResult,
        hwONTPotsTestEMFResult,
        hwONTPotsTestResistacneResult,
        hwONTPotsTestOffHookResult,
        hwONTPotsTestRingerResult,
        hwONTPotsTestNT1DCSignalResult,
        hwONTPotsTestSelfTestResult,
        hwONTPotsTestDrawDialToneResult,
        hwONTPotsTestBreakDialToneResult,
        hwONTPotsTestQuietEnergyResult,
        hwONTPotsTestDialToneEnergyResult,
        hwONTPotsTestLoopDCAGVoltResult,
        hwONTPotsTestLoopDCBGVoltResult,
        hwONTPotsTestLoopACAGVoltResult,       
        hwONTPotsTestLoopACBGVoltResult,       
        hwONTPotsTestLoopResistanceAGResult,   
        hwONTPotsTestLoopResistanceBGResult,   
        hwONTPotsTestLoopResistanceABResult,   
        hwONTPotsTestLoopRingerLoadTestResult, 
        hwONTPotsTestDrawDialToneTimeValue,    
        hwONTPotsTestBreakDialToneTimeValue,   
        hwONTPotsTestQuietEnergyValue,         
        hwONTPotsTestDialToneEnergyValue,      
        hwONTPotsTestLoopDCAGVoltValue,        
        hwONTPotsTestLoopDCBGVoltValue,        
        hwONTPotsTestLoopACAGVoltValue,        
        hwONTPotsTestLoopACBGVoltValue,        
        hwONTPotsTestLoopResistanceAGValue,    
        hwONTPotsTestLoopResistanceBGValue,    
        hwONTPotsTestLoopResistanceABValue,    
        hwONTPotsTestLoopRingerLoadTestValue,
        hwONTPotsTestSubscriberLineTestResult,
        hwONTPotsTestLoopDCABVoltValue,
        hwONTPotsTestLoopACABVoltValue,
        hwONTPotsTestLoopAGCapacitanceValue,
        hwONTPotsTestLoopBGCapacitanceValue,
        hwONTPotsTestLoopABCapacitanceValue,
        hwONTPotsTestLoopDCAGVoltCompensativeValue,            
        hwONTPotsTestLoopDCBGVoltCompensativeValue,    
        hwONTPotsTestLoopDCABVoltCompensativeValue,    
        hwONTPotsTestLoopACAGVoltCompensativeValue,    
        hwONTPotsTestLoopACBGVoltCompensativeValue,    
        hwONTPotsTestLoopACABVoltCompensativeValue,    
        hwONTPotsTestLoopResistanceAGCompensativeValue,
        hwONTPotsTestLoopResistanceBGCompensativeValue,
        hwONTPotsTestLoopResistanceABCompensativeValue
      }
      STATUS current                                                                      
      DESCRIPTION                                                                         
        "This trap indicates that a POTS port line test finished successfully, and shows 
         the result of the line test.
         This trap will send when a POTS port line test finished successfully."                                     
      ::= { hwTestCommonGeneralTrapsOIDs 5 }                                                    

    hwTestCommonMeltTestResultTrap NOTIFICATION-TYPE
      OBJECTS 
      {
        hwTestCommonRequestID,
        ifIndex,
        hwLoopLineTestStartTime,    
        hwLoopLineTestEndTime,       
        hwLoopLineTestStatus,        
        hwLoopLineTestConclusion,    
        hwLoopLineTestACAG,          
        hwLoopLineTestACBG,          
        hwLoopLineTestACAB,          
        hwLoopLineTestDCAG,          
        hwLoopLineTestDCBG,         
        hwLoopLineTestDCAB,         
        hwLoopLineTestRAG,          
        hwLoopLineTestRBG,          
        hwLoopLineTestRAB,          
        hwLoopLineTestCapAG,        
        hwLoopLineTestCapBG,        
        hwLoopLineTestCapAB,        
        hwLoopLineTestLR,           
        hwLoopLineTestRABResPole,   
        hwLoopLineTestMSocket,      
        hwLoopLineTestPPA,          
        hwLoopLineTestUtgAcFreq,    
        hwLoopLineTestUrgAcFreq,    
        hwLoopLineTestUtrAcFreq,    
        hwLoopLineTestItipAc,       
        hwLoopLineTestIringAc,      
        hwLoopLineTestItipDc,       
        hwLoopLineTestIringDc,      
        hwLoopLineTestRbattip,     
        hwLoopLineTestRbatring,    
        hwLoopLineTestRring,        
        hwLoopLineTestCsig,         
        hwLoopLineTestPPARes,       
        hwLoopLineTestVzener,       
        hwLoopLineTestRzener,       
        hwLoopLineTestGtg,          
        hwLoopLineTestBtg,          
        hwLoopLineTestGrg,          
        hwLoopLineTestBrg,          
        hwLoopLineTestGtr,          
        hwLoopLineTestBtr,          
        hwLoopLineTestSIGN,         
        hwLoopLineTestACFEM,        
        hwLoopLineTestDCFEM,        
        hwLoopLineTestONHK,         
        hwLoopLineTestOPEN,         
        hwLoopLineTestSHORT,        
        hwLoopLineTestROH,          
        hwLoopLineTestUtgDcUp,      
        hwLoopLineTestUtgDcDown,    
        hwLoopLineTestUrgDcUp,      
        hwLoopLineTestUrgDcDown,    
        hwLoopLineTestUtrPos,       
        hwLoopLineTestUtrNeg,       
        hwLoopLineTestItgDcUp,      
        hwLoopLineTestItgDcDown,    
        hwLoopLineTestIrgDcUp,      
        hwLoopLineTestIrgDcDown,    
        hwLoopLineTestItrPos,       
        hwLoopLineTestItrNeg,       
        hwLoopLineTestRinger,
        hwLoopLineTestOprMeasuredFreq,
        hwLoopLineTestRABPole,
        hwLoopLineTestACAGFlag,
        hwLoopLineTestACBGFlag,
        hwLoopLineTestACABFlag,
        hwLoopLineTestDCAGFlag,
        hwLoopLineTestDCBGFlag,
        hwLoopLineTestDCABFlag,
        hwLoopLineTestRAGFlag,
        hwLoopLineTestRBGFlag,
        hwLoopLineTestRABFlag,
        hwLoopLineTestRABPoleFlag,
        hwLoopLineTestRABResPoleFlag,
        hwLoopLineTestCapAGFlag,
        hwLoopLineTestCapBGFlag,
        hwLoopLineTestCapABFlag,
        hwLoopLineTestRbattipFlag,
        hwLoopLineTestRbatringFlag,
        hwLoopLineTestRringFlag,
        hwLoopLineTestCsigFlag,
        hwLoopLineTestPPAResFlag,
        hwLoopLineTestVzenerFlag,
        hwLoopLineTestRzenerFlag,
        hwLoopLineTestSNMPRab,
        hwLoopLineTestSNMPRabFlag,
        hwLoopLineTestSNMPRba,
        hwLoopLineTestSNMPRbaFlag,
        hwLoopLineTestPPAResultFlag,
        hwLoopLineTestUtgAcFreqFlag,
        hwLoopLineTestUrgAcFreqFlag,
        hwLoopLineTestUtrAcFreqFlag,
        hwLoopLineTestItipAcFlag,   
        hwLoopLineTestIringAcFlag,  
        hwLoopLineTestItipDcFlag,   
        hwLoopLineTestIringDcFlag,  
        hwLoopLineTestGtgFlag,      
        hwLoopLineTestBtgFlag,      
        hwLoopLineTestGrgFlag,      
        hwLoopLineTestBrgFlag,      
        hwLoopLineTestGtrFlag,      
        hwLoopLineTestBtrFlag,      
        hwLoopLineTestSIGNFlag,     
        hwLoopLineTestACFEMFlag,    
        hwLoopLineTestDCFEMFlag,    
        hwLoopLineTestONHKFlag,     
        hwLoopLineTestOPENFlag,     
        hwLoopLineTestSHORTFlag,    
        hwLoopLineTestROHFlag,      
        hwLoopLineTestUtgDcUpFlag,  
        hwLoopLineTestUtgDcDownFlag,
        hwLoopLineTestUrgDcUpFlag,  
        hwLoopLineTestUrgDcDownFlag,
        hwLoopLineTestUtrPosFlag,   
        hwLoopLineTestUtrNegFlag,   
        hwLoopLineTestItgDcUpFlag,  
        hwLoopLineTestItgDcDownFlag,
        hwLoopLineTestIrgDcUpFlag,  
        hwLoopLineTestIrgDcDownFlag,
        hwLoopLineTestItrPosFlag,   
        hwLoopLineTestItrNegFlag,   
        hwLoopLineTestRingerFlag,
        hwLoopLineTestMoreDataFlag
      } 
      STATUS current
      DESCRIPTION
        "This trap indicates that MELT test finished successfully, and show 
         the result of the melt test
         This trap will send when the MELT test finished successfully.
        "
      ::= { hwTestCommonGeneralTrapsOIDs 6 }
        
    hwTestCommonMeltTestFaileTrap NOTIFICATION-TYPE
      OBJECTS 
      {
        hwTestCommonRequestID,
        ifIndex,
        hwLoopLineTestStatus    
      } 
      STATUS current
      DESCRIPTION
        "This trap indicates that MELT test fails.
         This trap will send when the MELT test failed."
      ::= { hwTestCommonGeneralTrapsOIDs 7 }
      
    hwTestMeltChipStateCheckResultTrap NOTIFICATION-TYPE
      OBJECTS 
      {
        hwTestCommonRequestID,
        hwFrameIndex,
        hwSlotIndex,
        hwBoardMeltChipStateCheckResult    
      } 
      STATUS current
      DESCRIPTION
        "This trap indicates the MELT chip status check result.
         This trap will send when the MELT chip status check finished."
      ::= { hwTestCommonGeneralTrapsOIDs 8 }
        
          
    hwLoopLineTestMeltVerTable OBJECT-TYPE
      SYNTAX SEQUENCE OF HwLoopLineTestMeltVerEntry
      MAX-ACCESS not-accessible
      STATUS current
      DESCRIPTION
        "This table provides the information about the MELT chip on the board,
         including the vendor, hardware version, and software version.
         The indexes of this table are hwFrameIndex and hwSlotIndex.
         "
      ::= { hwTestCommonMIBObjects 8 }
    
    hwLoopLineTestMeltVerEntry OBJECT-TYPE
      SYNTAX HwLoopLineTestMeltVerEntry
      MAX-ACCESS not-accessible
      STATUS current
      DESCRIPTION      
        "This table provides the information about the MELT chip on the board,
         including the vendor, hardware version, and software version.
         The indexes of this entry are hwFrameIndex and hwSlotIndex.
         "
      INDEX { hwFrameIndex, hwSlotIndex }
      ::= { hwLoopLineTestMeltVerTable 1 }
    
    HwLoopLineTestMeltVerEntry ::=
      SEQUENCE
      { 
        hwLoopLineTestMeltFactory
          OCTET STRING,
        hwLoopLineTestMeltChip
          OCTET STRING,
        hwLoopLineTestMeltFirmwareVer
          OCTET STRING
      }
    
    hwLoopLineTestMeltFactory OBJECT-TYPE
      SYNTAX OCTET STRING (SIZE (0..32))
      MAX-ACCESS read-only
      STATUS current
      DESCRIPTION
        "MELT chipset manufacturer information
         Maximum length: 32 Octets
         "
      ::= { hwLoopLineTestMeltVerEntry 1 }
    
    hwLoopLineTestMeltChip OBJECT-TYPE
      SYNTAX OCTET STRING (SIZE (0..128))
      MAX-ACCESS read-only
      STATUS current
      DESCRIPTION
        "MELT chipset manufacturer hardware information
         Maximum length: 128 Octets
         "
      ::= { hwLoopLineTestMeltVerEntry 2 }
      
    hwLoopLineTestMeltFirmwareVer OBJECT-TYPE
      SYNTAX OCTET STRING (SIZE (0..16))
      MAX-ACCESS read-only
      STATUS current
      DESCRIPTION
        "MELT chipset manufacturer version information
         Maximum length: 16 Octets
         "
      ::= { hwLoopLineTestMeltVerEntry 3 }  
        
  hwLoopLineTestSysConfigPara OBJECT IDENTIFIER ::= { hwTestCommonMIBObjects 9 }

  hwLoopLineTestSysConfigConvertAB OBJECT-TYPE
      SYNTAX INTEGER 
      { 
      normal(1),
      reverse(2),
      invalid(-1) 
      }
      MAX-ACCESS read-write
      STATUS current
      DESCRIPTION
        "Indicates the polarity of A wire and B wire.
         Options:
         1. normal(1)   -default polarity of A wire and B wire 
         2. reverse(2)  -reverse polarity of A wire and B wire
         3. invalid(-1) -invalid value 
         Default: normal(1)
        "
      ::= { hwLoopLineTestSysConfigPara 1 }

  hwLoopLineTestSysConfigCableFactor OBJECT-TYPE
      SYNTAX      Unsigned32 (1..1000)
      MAX-ACCESS read-write
      STATUS current
      DESCRIPTION
        "The cable-factor used to detect significant terminal device capacitance.
         The cable-factor ranges from 1 to 1000 units of 0.001
         (Physical values are 0.001 to 1, default: 0.083).
        "
      ::= { hwLoopLineTestSysConfigPara 2 }      

  hwLoopLineTestSysConfigSigCapUpperLimit OBJECT-TYPE
      SYNTAX      Unsigned32 (50..2500)
      MAX-ACCESS read-write
      STATUS current
      DESCRIPTION
        "The three parameters(capacitance's upper-limit value, lower-limit value and resistance value) are used to determine the signature's existence.
         The capacitance ranges from 50nF to 2500nF, default: 1350nF.
         The capacitance's upper-limit value >= the capacitance's lower-limit value.
        "
      ::= { hwLoopLineTestSysConfigPara 3 }      

  hwLoopLineTestSysConfigSigCapLowerLimit OBJECT-TYPE
      SYNTAX      Unsigned32 (50..2500)
      MAX-ACCESS read-write
      STATUS current
      DESCRIPTION
        "The three parameters(capacitance's upper-limit value, lower-limit value and resistance value) are used to determine the signature's existence.
         The capacitance ranges from 50nF to 2500nF, default: 250nF.
         The capacitance's upper-limit value >= the capacitance's lower-limit value.
        "
      ::= { hwLoopLineTestSysConfigPara 4 }      
      
  hwLoopLineTestSysConfigSigResistance OBJECT-TYPE
      SYNTAX      Unsigned32 (10000..1000000)
      MAX-ACCESS read-write
      STATUS current
      DESCRIPTION
        "The three parameters(capacitance's upper-limit value, lower-limit value and resistance value) are used to determine the signature's existence.
         The resistance ranges from 10000ohm to 1000000ohm, default: 55000ohm.
        "
      ::= { hwLoopLineTestSysConfigPara 5 }      
      
-- Begin Add Table hwONTPotsTestOprTable<add by t66722 2009-12-1>
  hwONTPotsTestOprTable OBJECT-TYPE
      SYNTAX     SEQUENCE OF HwONTPotsTestOprEntry
      MAX-ACCESS not-accessible
      STATUS     current
      DESCRIPTION
        "This table is used for enabling the POTS port line test of the ONT by setting the test
         item, test frequency, and test threshold. This test helps operators locate faults and
         provision services.
         The indexes of this table are ifindex, hwONTPotsTestONTIndex and hwONTPotsTestONTPstnPortIndex.
         "
           ::= { hwTestCommonMIBObjects 10 } 
           
  hwONTPotsTestOprEntry OBJECT-TYPE
      SYNTAX     HwONTPotsTestOprEntry
      MAX-ACCESS not-accessible
      STATUS     current
      DESCRIPTION
        "This table is used for enabling the POTS port line test of the ONT by setting the test
         item, test frequency, and test threshold. This test helps operators locate faults and
         provision services.
         The indexes of this entry are ifindex, hwONTPotsTestONTIndex and hwONTPotsTestONTPstnPortIndex.
         "
      INDEX       { ifIndex, hwONTPotsTestONTIndex, hwONTPotsTestONTPstnPortIndex }
      ::= { hwONTPotsTestOprTable 1 }

-- 1.3.6.1.4.1.2011.6.21.1.1.1.10.1
  HwONTPotsTestOprEntry ::=  
       SEQUENCE 
       {  
        hwONTPotsTestONTIndex                                Integer32, 
        hwONTPotsTestONTPstnPortIndex                        Integer32, 
        hwONTPotsTestOprType                                 INTEGER,
        hwONTPotsTestItem                                    INTEGER,
        hwONTPotsTestBusyProcFlag                            INTEGER,
        hwONTPotsTestT1Threshold                             Integer32,
        hwONTPotsTestT2Threshold                             Integer32,
        hwONTPotsTestT3Threshold                             Integer32,
        hwONTPotsTestT4Threshold                             Integer32,
        hwONTPotsTestDtmfDigit                               INTEGER,
        hwONTPotsTestDialType                                INTEGER,
        hwONTPotsTestDialToneFreq1                           Integer32,
        hwONTPotsTestDialToneFreq2                           Integer32,
        hwONTPotsTestDialToneFreq3                           Integer32,
        hwONTPotsTestDialToneEnergyThreshold                 Integer32,
        hwONTPotsTestIdleChannelEnergyThreshold              Integer32,
        hwONTPotsTestDCHazardousVoltThreshold                Integer32,
        hwONTPotsTestACHazardousVoltThreshold                Integer32,
        hwONTPotsTestDCForeignVoltThreshold                  Integer32,
        hwONTPotsTestACForeignVoltThreshold                  Integer32,
        hwONTPotsTestAGBGResistanceThreshold                 Integer32,
        hwONTPotsTestABResistanceThreshold                   Integer32,
        hwONTPotsTestRingerEquivMinThreshold                 Integer32,
        hwONTPotsTestRingerEquivMaxThreshold                 Integer32,
        hwONTPotsTestMLTResult                               INTEGER,
        hwONTPotsTestHazardousVoltResult                     INTEGER,
        hwONTPotsTestEMFResult                               INTEGER,
        hwONTPotsTestResistacneResult                        INTEGER,
        hwONTPotsTestOffHookResult                           INTEGER,
        hwONTPotsTestRingerResult                            INTEGER,
        hwONTPotsTestNT1DCSignalResult                       INTEGER,
        hwONTPotsTestSelfTestResult                          INTEGER,
        hwONTPotsTestDrawDialToneResult                      INTEGER,
        hwONTPotsTestBreakDialToneResult                     INTEGER,
        hwONTPotsTestQuietEnergyResult                       INTEGER,
        hwONTPotsTestDialToneEnergyResult                    INTEGER,
        hwONTPotsTestLoopDCAGVoltResult                      INTEGER,
        hwONTPotsTestLoopDCBGVoltResult                      INTEGER,
        hwONTPotsTestLoopACAGVoltResult                      INTEGER,
        hwONTPotsTestLoopACBGVoltResult                      INTEGER,
        hwONTPotsTestLoopResistanceAGResult                  INTEGER,
        hwONTPotsTestLoopResistanceBGResult                  INTEGER,
        hwONTPotsTestLoopResistanceABResult                  INTEGER,
        hwONTPotsTestLoopRingerLoadTestResult                INTEGER,
        hwONTPotsTestDrawDialToneTimeValue                   Integer32,
        hwONTPotsTestBreakDialToneTimeValue                  Integer32,
        hwONTPotsTestQuietEnergyValue                        Integer32,
        hwONTPotsTestDialToneEnergyValue                     Integer32,
        hwONTPotsTestLoopDCAGVoltValue                       Integer32,
        hwONTPotsTestLoopDCBGVoltValue                       Integer32,
        hwONTPotsTestLoopACAGVoltValue                       Integer32,
        hwONTPotsTestLoopACBGVoltValue                       Integer32,
        hwONTPotsTestLoopResistanceAGValue                   Integer32,
        hwONTPotsTestLoopResistanceBGValue                   Integer32,
        hwONTPotsTestLoopResistanceABValue                   Integer32,
        hwONTPotsTestLoopRingerLoadTestValue                 Integer32,
        hwONTPotsTestSubscriberLineTestResult                INTEGER,
        hwONTPotsTestLoopDCABVoltValue                       Integer32,
        hwONTPotsTestLoopACABVoltValue                       Integer32,
        hwONTPotsTestLoopAGCapacitanceValue                  Integer32,
        hwONTPotsTestLoopBGCapacitanceValue                  Integer32,
        hwONTPotsTestLoopABCapacitanceValue                  Integer32,
        hwONTPotsTestLoopDCAGVoltCompensativeValue           Integer32,        
        hwONTPotsTestLoopDCBGVoltCompensativeValue           Integer32,
        hwONTPotsTestLoopDCABVoltCompensativeValue           Integer32,
        hwONTPotsTestLoopACAGVoltCompensativeValue           Integer32,
        hwONTPotsTestLoopACBGVoltCompensativeValue           Integer32,
        hwONTPotsTestLoopACABVoltCompensativeValue           Integer32,
        hwONTPotsTestLoopResistanceAGCompensativeValue       Integer32,
        hwONTPotsTestLoopResistanceBGCompensativeValue       Integer32,
        hwONTPotsTestLoopResistanceABCompensativeValue       Integer32
       }

  hwONTPotsTestONTIndex OBJECT-TYPE
      SYNTAX Integer32
      MAX-ACCESS accessible-for-notify
      STATUS  current
      DESCRIPTION
           "ONT ID."
      ::= { hwONTPotsTestOprEntry 1 }   
                        
  hwONTPotsTestONTPstnPortIndex OBJECT-TYPE
      SYNTAX Integer32
      MAX-ACCESS accessible-for-notify
      STATUS  current
      DESCRIPTION
           "ONT port ID."
      ::= { hwONTPotsTestOprEntry 2 }   
                        
  hwONTPotsTestOprType  OBJECT-TYPE  
      SYNTAX     INTEGER
      {
      stop (1),
      start (2),
      invalid(-1)
      }
      MAX-ACCESS   read-create
      STATUS      current
      DESCRIPTION 
        "POTS port line Test-operation type. 
         Options:
         1. stop(1)     -stop a POTS port line test 
         2. start(2)    -start a POTS port line test
         3. invalid(-1) -invalid value
        "
      ::= { hwONTPotsTestOprEntry 3 }                    
      
  hwONTPotsTestItem  OBJECT-TYPE  
      SYNTAX     INTEGER
      {
       allMLTTests (1),
       hazardousPotential (2),
       foreignEMF (3),
       resistiveFaults (4),
       receiverOffHook (5),
       ringer (6),
       nT1DcSignatureTest (7),
       selfTest (8),
       dialToneMakeBreakTest (9),
       subscriberLine (10),
       vendorSpecificTest2 (11),
       vendorSpecificTest3 (12),
       vendorSpecificTest4 (13),
       vendorSpecificTest5 (14),
       vendorSpecificTest6 (15),
       vendorSpecificTest7 (16)
      }
      MAX-ACCESS   read-create
      STATUS      current
      DESCRIPTION 
        "POTS port line test item. 
         Options:
         1. allMLTTests(1)               -outdoor connection test
         2. hazardousPotential(2)        -hazardous potential test
         3. foreignEMF(3)                -foreign electromotive force(EMF) test
         4. resistiveFaults(4)           -resistive faults test
         5. receiverOffHook(5)           -receiver off-hook test
         6. ringer(6)                    -ringer impedance test
         7. nT1DcSignatureTest(7)        -NT1 dc signature test
         8. selfTest(8)                  -self test
         9. dialToneMakeBreakTest(9)     -dial tone make-break test
         10. subscriberLine(10)          -subscriber line test 
         11. vendorSpecificTest2(11)     -vendor-specific test
                                          all results are returned in a test result message
         12. vendorSpecificTest3(12)     -vendor-specific test
                                          all results are returned in a test result message
         13. vendorSpecificTest4(13)     -vendor-specific test
                                          the test results are returned in general purpose buffer ME
                                          the ONT must deny a test operation command if bytes 39-40 do not point to a GP buffer
         14. vendorSpecificTest5(14)     -vendor-specific test
                                          the test results are returned in general purpose buffer ME
                                          the ONT must deny a test operation command if bytes 39-40 do not point to a GP buffer
         15. vendorSpecificTest6(15)     -vendor-specific test
                                          the test results are returned in general purpose buffer ME
                                          the ONT must deny a test operation command if bytes 39-40 do not point to a GP buffer
         16. vendorSpecificTest7(16)     -vendor-specific test
                                          the test results are returned in general purpose buffer ME
                                          the ONT must deny a test operation command if bytes 39-40 do not point to a GP buffer
        "
    ::= { hwONTPotsTestOprEntry 4 }            
      
  hwONTPotsTestBusyProcFlag  OBJECT-TYPE  
      SYNTAX     INTEGER{
      cancel(1),
      force(2)
      }
      MAX-ACCESS   read-create
      STATUS      current
      DESCRIPTION 
        "Test mode when a line is busy. 
         Options:
         1. cancel(1)  -deny a test if a line is busy
         2. force(2)   -forced mode
        "  
      ::= { hwONTPotsTestOprEntry 5 }     
      
  hwONTPotsTestT1Threshold  OBJECT-TYPE  
      SYNTAX     Integer32(0 | 100..6000)
      MAX-ACCESS   read-create
      STATUS      current
      DESCRIPTION 
        "Slow dial tone threshold.
         Options:
         1. 0          -Invalid value. It indicates that an ONT will use its default value
         2. 100..6000  -Valid value range
        "  
      ::= { hwONTPotsTestOprEntry 6 }                   
      
  hwONTPotsTestT2Threshold  OBJECT-TYPE  
      SYNTAX     Integer32(0 | 1000..10000)
      MAX-ACCESS   read-create
      STATUS      current
      DESCRIPTION 
        "No dial tone threshold.
         Options:
         1. 0            -Invalid value. It indicates that an ONT will use its default value
         2. 1000..10000  -Valid value range
        "  
      ::= { hwONTPotsTestOprEntry 7 }     

  hwONTPotsTestT3Threshold  OBJECT-TYPE  
      SYNTAX     Integer32(0 | 100..3000)
      MAX-ACCESS   read-create
      STATUS      current
      DESCRIPTION 
        "Slow break dial tone threshold.
         Options:
         1. 0          -Invalid value. It indicates that an ONT will use its default value
         2. 100..3000  -Valid value range
        "  
      ::= { hwONTPotsTestOprEntry 8 }     

  hwONTPotsTestT4Threshold  OBJECT-TYPE  
      SYNTAX     Integer32(0 | 1000..3000)
      MAX-ACCESS   read-create
      STATUS      current
      DESCRIPTION 
        "No break dial tone threshold.
         Options:
         1. 0           -Invalid value. It indicates that an ONT will use its default value
         2. 1000..3000  -Valid value range
        "  
      ::= { hwONTPotsTestOprEntry 9 }     

  hwONTPotsTestDtmfDigit  OBJECT-TYPE  
      SYNTAX     INTEGER
      {
       zero (1),
       one (2),
       two (3),
       three (4),
       four (5),
       five (6),
       six (7),
       seven (8),
       eight (9),
       nine (10),
       symbolStar (11),
       symbolSharp (12),
       default (13)
      }
      MAX-ACCESS   read-create
      STATUS      current
      DESCRIPTION 
        "DTMF test number.
         Options:
         1. zero(1)         -the test number is 0
         2. one(2)          -the test number is 1
         3. two(3)          -the test number is 2
         4. three(4)        -the test number is 3
         5. four(5)         -the test number is 4
         6. five(6)         -the test number is 5
         7. six(7)          -the test number is 6
         8. seven(8)        -the test number is 7
         9. eight(9)        -the test number is 8
         10. nine(10)       -the test number is 9
         11. symbolStar(11) -the test number is *
         12. symbolSharp(12)-the test number is #
         13. default(13)    -use the default value (number) of the system
        "  
      ::= { hwONTPotsTestOprEntry 10 }                                 

  hwONTPotsTestDialType  OBJECT-TYPE  
      SYNTAX     INTEGER{
      dtmf (1),
      pulse (2)
      }
      MAX-ACCESS   read-create
      STATUS      current
      DESCRIPTION 
        "The dialling type of dialling tone test.
         Options:
         1. dtmf(1)         -dtmf type
         2. pulse(2)        -pulse type
        "  
      ::= { hwONTPotsTestOprEntry 11 }     

  hwONTPotsTestDialToneFreq1  OBJECT-TYPE  
      SYNTAX     Integer32
      MAX-ACCESS   read-create
      STATUS      current
      DESCRIPTION 
        "The frequency1 in the dialling tone test.
         0 -unused
         Unit: Hz
        "  
      ::= { hwONTPotsTestOprEntry 12 }     

  hwONTPotsTestDialToneFreq2  OBJECT-TYPE  
      SYNTAX     Integer32
      MAX-ACCESS   read-create
      STATUS      current
      DESCRIPTION 
        "The frequency2 in the dialling tone test.
         0 -unused
         Unit: Hz
        "  
      ::= { hwONTPotsTestOprEntry 13 }                          

  hwONTPotsTestDialToneFreq3  OBJECT-TYPE  
      SYNTAX     Integer32
      MAX-ACCESS   read-create
      STATUS      current
      DESCRIPTION 
        "The frequency3 in the dialling tone test.
         0 -unused
         Unit: Hz
         "  
      ::= { hwONTPotsTestOprEntry 14 }            
      
  hwONTPotsTestDialToneEnergyThreshold  OBJECT-TYPE  
      SYNTAX     Integer32
      MAX-ACCESS   read-create
      STATUS      current
      DESCRIPTION 
        "The value of energy threshold in the dialling tone test.
         Valid value:
         1. 0x00: unspecified
         2. 0x01-0xFD: -0.1 dBm0 to -25.3 dBm0  
         Unit: 0.1 dBm0
        "  
      ::= { hwONTPotsTestOprEntry 15 }     
      
  hwONTPotsTestIdleChannelEnergyThreshold  OBJECT-TYPE  
      SYNTAX     Integer32
      MAX-ACCESS   read-create
      STATUS      current
      DESCRIPTION 
        "The value of energy threshold in the dialling tone test when the line 
         is in the idle state.
         Valid value:
         1. 0x00: unspecified
         2. 0x01-0x5A: -1 dBm0 to -90 dBm0 
         Unit: 1 dBm0
        "  
      ::= { hwONTPotsTestOprEntry 16 }                   
      
  hwONTPotsTestDCHazardousVoltThreshold  OBJECT-TYPE  
      SYNTAX     Integer32
      MAX-ACCESS   read-create
      STATUS      current
      DESCRIPTION 
        "The value of DC voltage threshold in the hazardous potential test.
         0x00 -unspecified
         Unit: volt
        "  
      ::= { hwONTPotsTestOprEntry 17 }     

  hwONTPotsTestACHazardousVoltThreshold  OBJECT-TYPE  
      SYNTAX     Integer32
      MAX-ACCESS   read-create
      STATUS      current
      DESCRIPTION 
        "The value of AC voltage threshold in the hazardous potential test.
         0x00 -unspecified
         Unit: volt.
        "  
      ::= { hwONTPotsTestOprEntry 18 }     

  hwONTPotsTestDCForeignVoltThreshold  OBJECT-TYPE  
      SYNTAX     Integer32
      MAX-ACCESS   read-create
      STATUS      current
      DESCRIPTION 
        "The value of DC voltage threshold in the foreign volt test.
         0x00 -unspecified
         Unit: volt
        "  
      ::= { hwONTPotsTestOprEntry 19 }     

  hwONTPotsTestACForeignVoltThreshold  OBJECT-TYPE  
      SYNTAX     Integer32
      MAX-ACCESS   read-create
      STATUS      current
      DESCRIPTION 
        "The value of AC voltage threshold in the foreign volt test.
         0x00 -unspecified
         Unit: volt
        "
      ::= { hwONTPotsTestOprEntry 20 }                                 

  hwONTPotsTestAGBGResistanceThreshold  OBJECT-TYPE  
      SYNTAX     Integer32
      MAX-ACCESS   read-create
      STATUS      current
      DESCRIPTION 
        "The resistance (tip to ground, ring to ground) threshold in the 
         resistive faults test.
         0x00 -unspecified
         Unit: kilohm
        "
      ::= { hwONTPotsTestOprEntry 21 }

  hwONTPotsTestABResistanceThreshold  OBJECT-TYPE  
      SYNTAX     Integer32
      MAX-ACCESS   read-create
      STATUS      current
      DESCRIPTION 
        "The resistance (tip to ring) threshold in the resistive faults test.
         0x00 -unspecified
         Unit: kilohm
        "
      ::= { hwONTPotsTestOprEntry 22 }     

  hwONTPotsTestRingerEquivMinThreshold  OBJECT-TYPE  
      SYNTAX     Integer32
      MAX-ACCESS   read-create
      STATUS      current
      DESCRIPTION 
        "Ringer equivalence minimum threshold.
         0x00 -unspecified
         Unit: 0.01 REN
        "
      ::= { hwONTPotsTestOprEntry 23 }     
      
  hwONTPotsTestRingerEquivMaxThreshold  OBJECT-TYPE  
      SYNTAX     Integer32
      MAX-ACCESS   read-create
      STATUS      current
      DESCRIPTION 
        "Ringer equivalence maximum threshold.
         0x00 -unspecified
         Unit: 0.01 REN
        "
      ::= { hwONTPotsTestOprEntry 24 }            
      
  hwONTPotsTestMLTResult  OBJECT-TYPE  
      SYNTAX     INTEGER
      {
      failed (1),
      passOrNotRun (2)
      }
      MAX-ACCESS   read-only
      STATUS      current
      DESCRIPTION 
        "MLT qualitative test result.
         Options:
         1. failed(1)       -a test fails
         2. passOrNotRun(2) -a test passes or the test does not run
         "  
      ::= { hwONTPotsTestOprEntry 25 }     
      
  hwONTPotsTestHazardousVoltResult  OBJECT-TYPE  
      SYNTAX     INTEGER
      {
      failed (1),
      passOrNotRun (2)
      }
      MAX-ACCESS   read-only
      STATUS      current
      DESCRIPTION 
        "Hazardous volt test result.
         Options:
         1. failed(1)       -a test fails
         2. passOrNotRun(2) -a test passes or the test does not run
        "  
      ::= { hwONTPotsTestOprEntry 26 }
      
  hwONTPotsTestEMFResult  OBJECT-TYPE  
      SYNTAX     INTEGER
      {
      failed (1),
      passOrNotRun (2)
      }
      MAX-ACCESS   read-only
      STATUS      current
      DESCRIPTION 
        "EMF test result.
         Options:
         1. failed(1)       -a test fails
         2. passOrNotRun(2) -a test passes or the test does not run
        "  
      ::= { hwONTPotsTestOprEntry 27 }     

  hwONTPotsTestResistacneResult  OBJECT-TYPE  
      SYNTAX     INTEGER{
      failed (1),
      passOrNotRun (2)
      }
      MAX-ACCESS   read-only
      STATUS      current
      DESCRIPTION 
        "Resistacne test result.
         Options:
         1. failed(1)       -a test fails
         2. passOrNotRun(2) -a test passes or the test does not run
        "  
      ::= { hwONTPotsTestOprEntry 28 }     

  hwONTPotsTestOffHookResult  OBJECT-TYPE  
      SYNTAX     INTEGER
      {
      failed (1),
      passOrNotRun (2)
      }
      MAX-ACCESS   read-only
      STATUS      current
      DESCRIPTION 
        "The off-hook test result.
         Options:
         1. failed(1)       -a test fails
         2. passOrNotRun(2) -a test passes or the test does not run
        "  
      ::= { hwONTPotsTestOprEntry 29 }     

  hwONTPotsTestRingerResult  OBJECT-TYPE  
      SYNTAX     INTEGER
      {
      failed (1),
      passOrNotRun (2)
      }
      MAX-ACCESS   read-only
      STATUS      current
      DESCRIPTION 
        "Ringer test result.
         Options:
         1. failed(1)       -a test fails
         2. passOrNotRun(2) -a test passes or the test does not run
        "  
      ::= { hwONTPotsTestOprEntry 30 }                                 

  hwONTPotsTestNT1DCSignalResult  OBJECT-TYPE  
      SYNTAX     INTEGER
      {
      failed (1),
      passOrNotRun (2)
      }
      MAX-ACCESS   read-only
      STATUS      current
      DESCRIPTION 
        "NT1 DC Signal test result.
         Options:
         1. failed(1)       -a test fails
         2. passOrNotRun(2) -a test passes or the test does not run
        "  
      ::= { hwONTPotsTestOprEntry 31 }     

  hwONTPotsTestSelfTestResult  OBJECT-TYPE  
      SYNTAX     INTEGER
      {
      failed (1),
      passOrNotRun (2),
      notCompleted(3)
      }
      MAX-ACCESS   read-only
      STATUS      current
      DESCRIPTION 
        "Self test result.
         Options:
         1. failed(1)       -a test fails
         2. passOrNotRun(2) -a test passes or the test does not run
         3. notCompleted(3) -a test is not complete yet
        "  
      ::= { hwONTPotsTestOprEntry 32 }     

  hwONTPotsTestDrawDialToneResult  OBJECT-TYPE  
      SYNTAX     INTEGER
      {
      notRun (1),
      couldNotDraw1 (3),
      couldNotDraw2 (4),
      slowDraw1 (5),
      slowDraw2 (6),
      pass1 (7),
      pass2 (8)
      }
      MAX-ACCESS   read-only
      STATUS      current
      DESCRIPTION 
        "Draw dialling tone test result.
         Options:
         1. notRun(1)        -a test does not run
         2. couldNotDraw1(3) -a test fails to draw                     
         3. couldNotDraw2(4) -a test fails to draw                     
         4. slowDraw1(5)     -slow draw
         5. slowDraw2(6)     -slow draw
         6. pass1(7)         -a test passes
         7. pass2(8)         -a test passes
        "  
      ::= { hwONTPotsTestOprEntry 33 }     
         
  hwONTPotsTestBreakDialToneResult  OBJECT-TYPE  
      SYNTAX     INTEGER
      {
      notRun (1),
      couldNotDraw1 (3),
      couldNotDraw2 (4),
      slowDraw1 (5),
      slowDraw2 (6),
      pass1 (7),
      pass2 (8)
      }
      MAX-ACCESS   read-only
      STATUS      current
      DESCRIPTION 
        "The break dialling tone test result.
         Options:
         1. notRun(1)        -a test does not run
         2. couldNotDraw1(3) -a test fails to draw                      
         3. couldNotDraw2(4) -a test fails to draw                           
         4. slowDraw1(5)     -slow draw
         5. slowDraw2(6)     -slow draw
         6. pass1(7)         -a test passes
         7. pass2(8)         -a test passes
        "  
      ::= { hwONTPotsTestOprEntry 34 }

  hwONTPotsTestQuietEnergyResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The quiet energy test result.
         Options:
         1. notRun(1)                      -a test does not run
         2. failMeasurementNotReported(3)  -a test fails
                                            the measurement is not reported
         3. failMeasurementReported(4)     -a test fails
                                            the measurement is reported
         4. passMeasurementNotReported(7)  -a test passes
                                            the measurement is not reported
         5. passMeasurementReported(8)     -a test passes
                                            the measurement is reported
        "  
      ::= { hwONTPotsTestOprEntry 35 }            
      
  hwONTPotsTestDialToneEnergyResult  OBJECT-TYPE  
      SYNTAX     INTEGER{
      notRun (1),
      failMeasurementNotReported (3),
      failMeasurementReported (4),
      passMeasurementNotReported (7),
      passMeasurementReported (8)
      }
      MAX-ACCESS   read-only
      STATUS      current
      DESCRIPTION 
        "The dialling tone energy test result.
         Options:
         1. notRun(1)                      -a test does not run
         2. failMeasurementNotReported(3)  -a test fails
                                            the measurement is not reported
         3. failMeasurementReported(4)     -a test fails.
                                            the measurement is reported
         4. passMeasurementNotReported(7)  -a test passes
                                            the measurement is not reported
         5. passMeasurementReported(8)     -a test passes
                                            the measurement is reported
        "  
      ::= { hwONTPotsTestOprEntry 36 }     
      
  hwONTPotsTestLoopDCAGVoltResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The DC A-G (tip to ground) volt loop test result.
         Options:
         1. notRun(1)                      -a test does not run
         2. failMeasurementNotReported(3)  -a test fails
                                            the measurement is not reported
         3. failMeasurementReported(4)     -a test fails
                                            the measurement is reported
         4. passMeasurementNotReported(7)  -a test passes
                                            the measurement is not reported
         5. passMeasurementReported(8)     -a test passes
                                            the measurement is reported
        "  
      ::= { hwONTPotsTestOprEntry 37 }                   
      
  hwONTPotsTestLoopDCBGVoltResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The DC B-G (ring to ground) volt loop test result.
         Options:
         1. notRun(1)                      -a test does not run.

         2. failMeasurementNotReported(3)  -a test fails
                                            the measurement is not reported
         3. failMeasurementReported(4)     -a test fails
                                            the measurement is reported
         4. passMeasurementNotReported(7)  -a test passes
                                            the measurement is not reported
         5. passMeasurementReported(8)     -a test passes
                                            the measurement is reported
        "  
      ::= { hwONTPotsTestOprEntry 38 }     

  hwONTPotsTestLoopACAGVoltResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The AC A-G (tip to ground) volt loop test result.
         Options:
         1. notRun(1)                      -a test does not run
         2. failMeasurementNotReported(3)  -a test fails
                                            the measurement is not reported
         3. failMeasurementReported(4)     -a test fails
                                            the measurement is reported
         4. passMeasurementNotReported(7)  -a test passes
                                            the measurement is not reported
         5. passMeasurementReported(8)     -a test passes
                                            the measurement is reported
        "  
      ::= { hwONTPotsTestOprEntry 39 }     

  hwONTPotsTestLoopACBGVoltResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The AC B-G (ring to ground) volt loop test result.
         Options:
         1. notRun(1)                      -a test does not run
         2. failMeasurementNotReported(3)  -a test fails
                                            the measurement is not reported
         3. failMeasurementReported(4)     -a test fails
                                            the measurement is reported   
         4. passMeasurementNotReported(7)  -a test passes
                                            the measurement is not reported
         5. passMeasurementReported(8)     -a test passes
                                            the measurement is reported
        "  
      ::= { hwONTPotsTestOprEntry 40 }     

  hwONTPotsTestLoopResistanceAGResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The A-G (ring to ground) resistance loop test result.
         Options:
         1. notRun(1)                      -a test does not run
         2. failMeasurementNotReported(3)  -a test fails
                                            the measurement is not reported
         3. failMeasurementReported(4)     -a test fails
                                            the measurement is reported
         4. passMeasurementNotReported(7)  -a test passes
                                            the measurement is not reported
         5. passMeasurementReported(8)     -a test passes
                                            the measurement is reported
        "  
      ::= { hwONTPotsTestOprEntry 41 }                                 

  hwONTPotsTestLoopResistanceBGResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The B-G (ring to ground) resistance loop test result.
         Options:
         1. notRun(1)                      -a test does not run
         2. failMeasurementNotReported(3)  -a test fails
                                            the measurement is not reported
         3. failMeasurementReported(4)     -a test fails
                                            the measurement is reported
         4. passMeasurementNotReported(7)  -a test passes
                                            the measurement is not reported
         5. passMeasurementReported(8)     -a test passes
                                            the measurement is reported
        "  
      ::= { hwONTPotsTestOprEntry 42 }     

  hwONTPotsTestLoopResistanceABResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The A-B (tip to ring) resistance loop test result.
         Options:
         1. notRun(1)                      -a test does not run
         2. failMeasurementNotReported(3)  -a test fails
                                            the measurement is not reported
         3. failMeasurementReported(4)     -a test fails
                                            the measurement is reported
         4. passMeasurementNotReported(7)  -a test passes
                                            the measurement is not reported
         5. passMeasurementReported(8)     -a test passes
                                            the measurement is reported
        "  
      ::= { hwONTPotsTestOprEntry 43 }     

  hwONTPotsTestLoopRingerLoadTestResult  OBJECT-TYPE  
      SYNTAX     INTEGER
      {
      notRun (1),
      failMeasurementNotReported (3),
      failMeasurementReported (4),
      passMeasurementNotReported (7),
      passMeasurementReported (8)
      }
      MAX-ACCESS   read-only
      STATUS      current
      DESCRIPTION 
        "The ringer load Loop test result.
         Options:
         1. notRun(1)                      -a test does not run
         2. failMeasurementNotReported(3)  -a test fails
                                            the measurement is not reported
         3. failMeasurementReported(4)     -a test fails
                                            the measurement is reported
         4. passMeasurementNotReported(7)  -a test passes
                                            the measurement is not reported
         5. passMeasurementReported(8)     -a test passes
                                            the measurement is reported
        "  
      ::= { hwONTPotsTestOprEntry 44 }
      
  hwONTPotsTestDrawDialToneTimeValue  OBJECT-TYPE  
      SYNTAX     Integer32
      MAX-ACCESS   read-only
      STATUS      current
      DESCRIPTION 
        "The draw dial tone test result. Valid only if value of hwONTPotsTestDrawDialToneResult
         is couldNotDraw2(4), slowDraw2(6) or pass2(8).
         Unit: 100ms.
         Step: 100ms.
        "  
      ::= { hwONTPotsTestOprEntry 45 }            
      
  hwONTPotsTestBreakDialToneTimeValue  OBJECT-TYPE  
      SYNTAX     Integer32
      MAX-ACCESS   read-only
      STATUS      current
      DESCRIPTION 
        "The break dial tone test result. Valid only if value of hwONTPotsTestBreakDialToneResult
         is couldNotDraw2(4), slowDraw2(6) or pass2(8).
         Unit: 100ms.
         Step: 100 ms.
        "  
      ::= { hwONTPotsTestOprEntry 46 }     
      
  hwONTPotsTestQuietEnergyValue  OBJECT-TYPE  
      SYNTAX     Integer32(0..90)
      MAX-ACCESS   read-only
      STATUS      current
      DESCRIPTION 
        "The quiet energy test result. Valid only if value of hwONTPotsTestQuietEnergyResult
         is failMeasurementReported(4) or passMeasurementReported(8).
         Values:
         0-90 : 0 dBm0 to -90 dBm0
         Step: 1 dBm0
        "  
      ::= { hwONTPotsTestOprEntry 47 }                   
      
  hwONTPotsTestDialToneEnergyValue  OBJECT-TYPE  
      SYNTAX     Integer32(0..255)
      MAX-ACCESS   read-only
      STATUS      current
      DESCRIPTION 
        "The dial energy test result. Valid only if value of hwONTPotsTestDialToneEnergyResult
         is failMeasurementReported(4) or passMeasurementReported(8).
         Values:
         0-255 : 0 dBm0 to -25.5 dBm0
         Values above 0 dBm0 are reported as 0. 
         Step: 0.1 dBm0
        "  
      ::= { hwONTPotsTestOprEntry 48 }     

  hwONTPotsTestLoopDCAGVoltValue  OBJECT-TYPE  
      SYNTAX     Integer32
      MAX-ACCESS   read-only
      STATUS      current
      DESCRIPTION 
        "The DC A-G(Tip-ground) volt Loop test result or Subscriber line test result.
         2s complement, resolution 1V. Valid only if value of hwONTPotsTestLoopDCAGVoltResult
         is failMeasurementReported(4) or passMeasurementReported(8) when loop tested.
         Valid only if value of hwONTPotsTestSubscriberLineTestResult is not testTimeout(29) 
         or testFailed(30) or invalid(-1) when subscriber line test.
         Unit: volt.
        "  
      ::= { hwONTPotsTestOprEntry 49 }     

  hwONTPotsTestLoopDCBGVoltValue  OBJECT-TYPE  
      SYNTAX     Integer32
      MAX-ACCESS   read-only
      STATUS      current
      DESCRIPTION 
        "The DC B-G(Ring-ground) volt Loop test result or Subscriber line test result.
         2s complement, resolution 1V. Valid only if value of hwONTPotsTestLoopDCBGVoltResult
         is failMeasurementReported(4) or passMeasurementReported(8) when loop tested.
         Valid only if value of hwONTPotsTestSubscriberLineTestResult is not testTimeout(29) 
         or testFailed(30) or invalid(-1) when subscriber line test.
         Unit: volt.
        "  
      ::= { hwONTPotsTestOprEntry 50 }     

  hwONTPotsTestLoopACAGVoltValue  OBJECT-TYPE  
      SYNTAX     Integer32
      MAX-ACCESS   read-only
      STATUS      current
      DESCRIPTION 
        "The AC A-G(Tip-ground) volt Loop test result or Subscriber line test result.
         Valid only if value of hwONTPotsTestLoopACAGVoltResult is failMeasurementReported(4)
         or passMeasurementReported(8) when loop tested.
         Valid only if value of hwONTPotsTestSubscriberLineTestResult is not testTimeout(29) 
         or testFailed(30) or invalid(-1) when subscriber line test.
         Unit: volt.
        "  
      ::= { hwONTPotsTestOprEntry 51 }                                 

  hwONTPotsTestLoopACBGVoltValue  OBJECT-TYPE  
      SYNTAX     Integer32
      MAX-ACCESS   read-only
      STATUS      current
      DESCRIPTION 
        "The AC B-G(Ring-ground) volt Loop test result or Subscriber line test result.
         Valid only if value of hwONTPotsTestLoopACBGVoltResult is failMeasurementReported(4)
         or passMeasurementReported(8) when loop tested.
         Valid only if value of hwONTPotsTestSubscriberLineTestResult is not testTimeout(29) 
         or testFailed(30) or invalid(-1) when subscriber line test.
         Unit: volt.
        "  
      ::= { hwONTPotsTestOprEntry 52 }     

  hwONTPotsTestLoopResistanceAGValue  OBJECT-TYPE  
      SYNTAX       Integer32(0..65535)
      MAX-ACCESS   read-only
      STATUS       current
      DESCRIPTION 
        "The A-G (tip to ground) resistance loop test result or Subscriber line test result.
         Unit: kilohm.
         Infinite resistance: 65535.
         Valid only if value of hwONTPotsTestLoopResistanceAGResult is 
         failMeasurementReported(4) or passMeasurementReported(8) when loop tested.
         Valid only if value of hwONTPotsTestSubscriberLineTestResult is not testTimeout(29) 
         or testFailed(30) or invalid(-1) when subscriber line test.
        "  
      ::= { hwONTPotsTestOprEntry 53 }     

  hwONTPotsTestLoopResistanceBGValue  OBJECT-TYPE  
      SYNTAX       Integer32(0..65535)
      MAX-ACCESS   read-only
      STATUS       current
      DESCRIPTION 
        "The B-G (ring to ground) resistance loop test result or Subscriber line test result.
         Unit: kilohm.
         Infinite resistance: 65535.
         Valid only if value of hwONTPotsTestLoopResistanceAGResult is 
         failMeasurementReported(4) or passMeasurementReported(8) when loop tested.
         Valid only if value of hwONTPotsTestSubscriberLineTestResult is not testTimeout(29) 
         or testFailed(30) or invalid(-1) when subscriber line test.
        "  
      ::= { hwONTPotsTestOprEntry 54 }       
      
  hwONTPotsTestLoopResistanceABValue  OBJECT-TYPE  
      SYNTAX     Integer32
      MAX-ACCESS   read-only
      STATUS      current
      DESCRIPTION 
        "The A-B (tip to ring) resistance loop test result or Subscriber line test result.
         Unit: kilohm.
         Infinite resistance: 65535.
         Valid only if value of hwONTPotsTestLoopResistanceAGResult is 
         failMeasurementReported(4) or passMeasurementReported(8) when loop tested.
         Valid only if value of hwONTPotsTestSubscriberLineTestResult is not testTimeout(29) 
         or testFailed(30) or invalid(-1) when subscriber line test.
        "  
      ::= { hwONTPotsTestOprEntry 55 }     
      
  hwONTPotsTestLoopRingerLoadTestValue  OBJECT-TYPE  
      SYNTAX     Integer32
      MAX-ACCESS   read-only
      STATUS      current
      DESCRIPTION 
        "The ringer load test result. Valid only if value of hwONTPotsTestLoopRingerLoadTestResult
         is failMeasurementReported(4) or passMeasurementReported(8).
         Unit: 0.1 REN.
        "  
      ::= { hwONTPotsTestOprEntry 56 }     

  hwONTPotsTestSubscriberLineTestResult  OBJECT-TYPE  
      SYNTAX     INTEGER
      {
      normal (1),
      acCurrentAbnormal (12),
      dcCurrentAbnormal (13),
      loopCurrentAbnormal (14),
      loopResistanceAbnormal (15),
      insulatingResistanceAbnormal (16),
      capacitanceAbnormal (17),
      impedanceAbnormal (18),
      insulatingNotGood (22),
      brokenLines (23),
      lineMixing (24),
      connectedToGround (25),
      abLinereversal (26),
      lineLeaking (27),
      phoneDisconnect (28),
      testTimeout (29),
      testFailed (30),
      invalid (-1)
      }
      MAX-ACCESS   read-only
      STATUS      current
      DESCRIPTION 
        "The subscriber line test result. 
         Options:
         1. normal(1)                         -subscriber line test normal
         2. acCurrentAbnormal(12)             -AC current abnormal
         3. dcCurrentAbnormal(13)             -DC current abnormal
         4. loopCurrentAbnormal(14)           -loop current abnormal
         5. loopResistanceAbnormal(15)        -loop resistance abnormal
         6. insulatingResistanceAbnormal(16)  -insulating resistance abnormal
         7. capacitanceAbnormal(17)           -capacitance abnormal
         8. impedanceAbnormal(18)             -impedance abnormal
         9. insulatingNotGood(22)             -insulating not good
         10. brokenLines(23)                  -broken lines
         11. lineMixing(24)                   -line mixing
         12. connectedToGround(25)            -connected to ground
         13. abLinereversal(26)               -ABLine reversal
         14. lineLeaking(27)                  -line leaking
         15. phoneDisconnect(28)              -phone disconnect
         16. testTimeout(29)                  -test is time out
         17. testFailed(30)                   -test failed
         18. invalid(-1)                      -a test does not run
        "  
      ::= { hwONTPotsTestOprEntry 57 }

  -- End Add Table hwONTPotsTestOprTable<add by t66722 2009-12-1>
  
  hwONTPotsTestLoopDCABVoltValue  OBJECT-TYPE  
      SYNTAX     Integer32
      MAX-ACCESS   read-only
      STATUS      current
      DESCRIPTION 
        "The DC A-B (tip-Ring) volt result of subscriber line test.
         Unit: volt.
        "  
      ::= { hwONTPotsTestOprEntry 58 }
      
  hwONTPotsTestLoopACABVoltValue  OBJECT-TYPE  
      SYNTAX     Integer32
      MAX-ACCESS   read-only
      STATUS      current
      DESCRIPTION 
        "The AC A-B (Tip-Ring) volt result of subscriber line test.
         Unit: volt.
        "  
      ::= { hwONTPotsTestOprEntry 59 }
      
  hwONTPotsTestLoopAGCapacitanceValue OBJECT-TYPE
      SYNTAX Integer32
      MAX-ACCESS read-only
      STATUS current      
      DESCRIPTION
        "The A->G (Tip-Ground) capacitance result of subscriber line test.
         Unit: nF
        "
      ::= { hwONTPotsTestOprEntry 60 }      
      
  hwONTPotsTestLoopBGCapacitanceValue OBJECT-TYPE
      SYNTAX Integer32
      MAX-ACCESS read-only
      STATUS current      
      DESCRIPTION
        "The B->G (Ring-Ground) capacitance result of subscriber line test.
         Unit: nF
        "
      ::= { hwONTPotsTestOprEntry 61 }   
      
  hwONTPotsTestLoopABCapacitanceValue OBJECT-TYPE
      SYNTAX Integer32
      MAX-ACCESS read-only
      STATUS current      
      DESCRIPTION
        "The A->B (Tip-Ring) capacitance result of subscriber line test.
         Unit: nF
        "
      ::= { hwONTPotsTestOprEntry 62 }
      
  hwONTPotsTestLoopDCAGVoltCompensativeValue OBJECT-TYPE
      SYNTAX Integer32
      MAX-ACCESS read-only
      STATUS current      
      DESCRIPTION
        "The DC A->G (Tip-Ground) volt compensative result of subscriber line test.
         Unit: mV
        "
      ::= { hwONTPotsTestOprEntry 63 }
      
  hwONTPotsTestLoopDCBGVoltCompensativeValue OBJECT-TYPE
      SYNTAX Integer32
      MAX-ACCESS read-only
      STATUS current      
      DESCRIPTION
        "The DC B->G (Ring-Ground) volt compensative result of subscriber line test.
         Unit: mV
        "
      ::= { hwONTPotsTestOprEntry 64 }
      
  hwONTPotsTestLoopDCABVoltCompensativeValue OBJECT-TYPE
      SYNTAX Integer32
      MAX-ACCESS read-only
      STATUS current      
      DESCRIPTION
        "The DC A->B (Tip-Ring) volt compensative result of subscriber line test.
         Unit: mV
        "
      ::= { hwONTPotsTestOprEntry 65 }
      
  hwONTPotsTestLoopACAGVoltCompensativeValue OBJECT-TYPE
      SYNTAX Integer32
      MAX-ACCESS read-only
      STATUS current      
      DESCRIPTION
        "The AC A->G (Tip-Ground) volt compensative result of subscriber line test.
         Unit: mVrms
        "
      ::= { hwONTPotsTestOprEntry 66 }
      
  hwONTPotsTestLoopACBGVoltCompensativeValue OBJECT-TYPE
      SYNTAX Integer32
      MAX-ACCESS read-only
      STATUS current      
      DESCRIPTION
        "The AC B->G (Ring-Ground) volt compensative result of subscriber line test.
         Unit: mVrms
        "
      ::= { hwONTPotsTestOprEntry 67 }
      
  hwONTPotsTestLoopACABVoltCompensativeValue OBJECT-TYPE
      SYNTAX Integer32
      MAX-ACCESS read-only
      STATUS current      
      DESCRIPTION
        "The AC A->B (Tip-Ring) volt compensative result of subscriber line test.
         Unit: mVrms
        "
      ::= { hwONTPotsTestOprEntry 68 }
      
  hwONTPotsTestLoopResistanceAGCompensativeValue OBJECT-TYPE
      SYNTAX Integer32
      MAX-ACCESS read-only
      STATUS current      
      DESCRIPTION
        "The A-G (tip to ground) resistance compensative result of subscriber line test.
         Unit: ohm
        "
      ::= { hwONTPotsTestOprEntry 69 }
      
  hwONTPotsTestLoopResistanceBGCompensativeValue OBJECT-TYPE
      SYNTAX Integer32
      MAX-ACCESS read-only
      STATUS current      
      DESCRIPTION
        "The B-G (Ring to ground) resistance compensative result of subscriber line test.
         Unit: ohm
        "
      ::= { hwONTPotsTestOprEntry 70 } 
      
  hwONTPotsTestLoopResistanceABCompensativeValue OBJECT-TYPE
      SYNTAX Integer32
      MAX-ACCESS read-only
      STATUS current      
      DESCRIPTION
        "The A-B (tip to Ring) resistance compensative result of subscriber line test.
         Unit: ohm
        "
      ::= { hwONTPotsTestOprEntry 71 }
  
  hwPortTestingListOprTable OBJECT-TYPE
      SYNTAX SEQUENCE OF HwPortTestingListOprEntry
      MAX-ACCESS not-accessible
      STATUS current
      DESCRIPTION
        "This table is used to query the ports under a test by board.
         The indexes of this table are hwFrameIndex and hwSlotIndex.
        "
      ::= { hwTestCommonMIBObjects 11 }
  
  hwPortTestingListOprEntry OBJECT-TYPE
      SYNTAX HwPortTestingListOprEntry
      MAX-ACCESS not-accessible
      STATUS current
      DESCRIPTION          
        "This table is used to query the ports under a test by board.
         The indexes of this entry are hwFrameIndex and hwSlotIndex.
        "
      INDEX { hwFrameIndex, hwSlotIndex }
      ::= { hwPortTestingListOprTable 1 }
  
  HwPortTestingListOprEntry ::=
      SEQUENCE
      { 
       hwMeltTestingPortList
           BITS,
       hwSearchToneTestingPortList
           BITS
      }
  
  hwMeltTestingPortList OBJECT-TYPE
      SYNTAX BITS 
      {
       port0(0),
       port1(1),
       port2(2),
       port3(3),
       port4(4),
       port5(5),
       port6(6),
       port7(7),
       port8(8),
       port9(9),
       port10(10),
       port11(11),
       port12(12),
       port13(13),
       port14(14),
       port15(15),
       port16(16),
       port17(17),
       port18(18),
       port19(19),
       port20(20),
       port21(21),
       port22(22),
       port23(23),
       port24(24),
       port25(25),
       port26(26),
       port27(27),
       port28(28),
       port29(29),
       port30(30),
       port31(31),
       port32(32),
       port33(33),
       port34(34),
       port35(35),
       port36(36),
       port37(37),
       port38(38),
       port39(39),
       port40(40),
       port41(41),
       port42(42),
       port43(43),
       port44(44),
       port45(45),
       port46(46),
       port47(47),
       port48(48),
       port49(49), 
       port50(50),
       port51(51),
       port52(52),
       port53(53),
       port54(54),
       port55(55),
       port56(56),
       port57(57),
       port58(58),
       port59(59),
       port60(60),
       port61(61),
       port62(62),
       port63(63)
      }   
      MAX-ACCESS read-only
      STATUS current  
      DESCRIPTION     
        "List of ports under a MELT test on a board.
         The result is analyzed as follow: If a bit in the bit string is set to 1, it indicates that the corresponding port is under a MELT test.
         For example, if port 8 is under a MELT test, the eighth character of the string is set to 1, and 0000 0000 1000 0000, namely, 
         # 0x00 0x80 is issued. Note that the value of the bit type starts from 0.
        "           
      ::= { hwPortTestingListOprEntry 1 }
  
  hwSearchToneTestingPortList OBJECT-TYPE
      SYNTAX BITS 
      {
       port0(0),
       port1(1),
       port2(2),
       port3(3),
       port4(4),
       port5(5),
       port6(6),
       port7(7),
       port8(8),
       port9(9),
       port10(10),
       port11(11),
       port12(12),
       port13(13),
       port14(14),
       port15(15),
       port16(16),
       port17(17),
       port18(18),
       port19(19),
       port20(20),
       port21(21),
       port22(22),
       port23(23),
       port24(24),
       port25(25),
       port26(26),
       port27(27),
       port28(28),
       port29(29),
       port30(30),
       port31(31),
       port32(32),
       port33(33),
       port34(34),
       port35(35),
       port36(36),
       port37(37),
       port38(38),
       port39(39),
       port40(40),
       port41(41),
       port42(42),
       port43(43),
       port44(44),
       port45(45),
       port46(46),
       port47(47),
       port48(48),
       port49(49), 
       port50(50),
       port51(51),
       port52(52),
       port53(53),
       port54(54),
       port55(55),
       port56(56),
       port57(57),
       port58(58),
       port59(59),
       port60(60),
       port61(61),
       port62(62),
       port63(63)
      } 
      MAX-ACCESS read-only
      STATUS current
      DESCRIPTION
        "List of ports under a searching tone test on a board.
         The result is analyzed as follow: If a bit in the bit string is set to 1, it indicates that the corresponding port is under a searching tone test.
         For example, if port 8 is under MELT test, the eighth character of the string is set to 1, 
         and 0000 0000 1000 0000, namely, # 0x00 0x80 is issued. Note that the value of the bit type starts from 0.
        "
      ::= { hwPortTestingListOprEntry 2 }
          
  hwWettingCurrentOprTable OBJECT-TYPE
      SYNTAX SEQUENCE OF HwWettingCurrentOprEntry
      MAX-ACCESS not-accessible
      STATUS current
      DESCRIPTION
        "This table is used for enabling the wetting current by setting the wetting current's
         working voltage, maximum voltage and slope.
         The index of this table is ifindex.
         "
      ::= { hwTestCommonMIBObjects 12 }
  
  hwWettingCurrentOprEntry OBJECT-TYPE
      SYNTAX HwWettingCurrentOprEntry
      MAX-ACCESS not-accessible
      STATUS current
      DESCRIPTION      
        "This table is used for enabling the wetting current by setting the wetting current's
         working voltage, maximum voltage and slope.
         The index of this entry is ifindex.
         "
      INDEX { ifIndex }
      ::= { hwWettingCurrentOprTable 1 }
  
  HwWettingCurrentOprEntry ::=
      SEQUENCE 
      { 
        hwWettingCurrentOprStatus
          INTEGER,
        hwWettingCurrentOprWorkingVoltage
          Integer32,
        hwWettingCurrentOprMaximumVoltage
          Integer32,
        hwWettingCurrentOprSlope
          Integer32                                       
       }      
      
  hwWettingCurrentOprStatus OBJECT-TYPE
      SYNTAX INTEGER
      {
        enabled(1),
        disabled(2),
        invalid(-1)
      }
      MAX-ACCESS read-write
      STATUS current
      DESCRIPTION
        "Wetting Current operation type. 
         Options:
         1. enabled(1)     -enable a wetting current port 
         2. disabled(2)    -disable a wetting current port
         3. invalid(-1)    -invalid value
         enabled(1) and disabled(2) options are available in the set operation.
         enabled(1), disabled(2) and invalid(-1) options are available in the get operation.
         "
      ::= { hwWettingCurrentOprEntry 1 }       

  hwWettingCurrentOprWorkingVoltage OBJECT-TYPE
      SYNTAX Integer32 (-1 | 1..120)
      MAX-ACCESS read-write
      STATUS current      
      DESCRIPTION
        "Indicates the working voltage of a wetting current port.
         Options:
         1. -1         -Invalid value
         2. 1..120     -Valid value range
         Default: 90
         Unit: volt
        "
      DEFVAL { 90 }
      ::= { hwWettingCurrentOprEntry 2 }   

  hwWettingCurrentOprMaximumVoltage OBJECT-TYPE
      SYNTAX Integer32 (-1 | 1..120)     
      MAX-ACCESS read-write
      STATUS current
      DESCRIPTION
        "Indicates the maximum voltage of a wetting current port.
         Options:
         1. -1         -Invalid value
         2. 1..120     -Valid value range
         Default: 30
         Unit: volt
         "
      DEFVAL { 30 }
      ::= { hwWettingCurrentOprEntry 3 }   

  hwWettingCurrentOprSlope OBJECT-TYPE
      SYNTAX Integer32 (-1 | 200..20000)      
      MAX-ACCESS read-write
      STATUS current
      DESCRIPTION
        "Indicates the slope of a wetting current port. 
         Options:
         1. -1             -Invalid value
         2. 200..20000     -Valid value range
         Default: 200
         Unit: volt per second
        "
      DEFVAL { 200 }
      ::= { hwWettingCurrentOprEntry 4 }   
       
  hwLoopLineTestMeltChipStateTable OBJECT-TYPE
      SYNTAX SEQUENCE OF HwLoopLineTestMeltChipStateEntry
      MAX-ACCESS not-accessible
      STATUS current
      DESCRIPTION
        "This table is used for manually starting a MELT chip status check on an xDSL board, and obtaining the status of the MELT chip.
         The indexes of this table are hwFrameIndex and hwSlotIndex.
         "
      ::= { hwTestCommonMIBObjects 13 }
      
  hwLoopLineTestMeltChipStateEntry OBJECT-TYPE
      SYNTAX HwLoopLineTestMeltChipStateEntry
      MAX-ACCESS not-accessible
      STATUS current
      DESCRIPTION      
        "This table is used for manually starting a MELT chip status check on an xDSL board, and obtaining the status of the MELT chip.
         The indexes of this table are hwFrameIndex and hwSlotIndex.
         "
      INDEX { hwFrameIndex, hwSlotIndex }
      ::= { hwLoopLineTestMeltChipStateTable 1 }
      
  HwLoopLineTestMeltChipStateEntry ::=
      SEQUENCE 
      { 
        hwBoardMeltChipStateCheckConfig
          INTEGER,
        hwBoardMeltChipStateCheckResult
          INTEGER,
        hwPortMeltChipStateList
          BITS,
        hwBoardMeltChipStateCheckDCVolUpperLimit
          Integer32,
        hwBoardMeltChipStateCheckDCVolLowerLimit
          Integer32                                       
       }
       
  hwBoardMeltChipStateCheckConfig OBJECT-TYPE
      SYNTAX INTEGER
      {
        enabled(1),
        invalid(-1)
      }
      MAX-ACCESS read-write
      STATUS current
      DESCRIPTION
        "Enables the melt chip status check of the board. 
         Options:
         1. enabled(1)     -Enables the melt chip status check 
         2. invalid(-1)    -Invalid value
         enabled(1) option is available in the set operation.
         invalid(-1) option is available in the get operation.
         "
      ::= { hwLoopLineTestMeltChipStateEntry 1 }
  
  hwBoardMeltChipStateCheckResult OBJECT-TYPE
      SYNTAX INTEGER
      {
        success(1),
        fail(2)
      }
      MAX-ACCESS accessible-for-notify
      STATUS current
      DESCRIPTION
        "Melt chip status check result.
         Options:
         1. success(1)         -Melt chip status check success
         2. fail(2)            -Melt chip status check fail
        "
      ::= { hwLoopLineTestMeltChipStateEntry 2 }
  
  hwPortMeltChipStateList OBJECT-TYPE
      SYNTAX BITS 
      {
       port0(0),
       port1(1),
       port2(2),
       port3(3),
       port4(4),
       port5(5),
       port6(6),
       port7(7),
       port8(8),
       port9(9),
       port10(10),
       port11(11),
       port12(12),
       port13(13),
       port14(14),
       port15(15),
       port16(16),
       port17(17),
       port18(18),
       port19(19),
       port20(20),
       port21(21),
       port22(22),
       port23(23),
       port24(24),
       port25(25),
       port26(26),
       port27(27),
       port28(28),
       port29(29),
       port30(30),
       port31(31),
       port32(32),
       port33(33),
       port34(34),
       port35(35),
       port36(36),
       port37(37),
       port38(38),
       port39(39),
       port40(40),
       port41(41),
       port42(42),
       port43(43),
       port44(44),
       port45(45),
       port46(46),
       port47(47),
       port48(48),
       port49(49), 
       port50(50),
       port51(51),
       port52(52),
       port53(53),
       port54(54),
       port55(55),
       port56(56),
       port57(57),
       port58(58),
       port59(59),
       port60(60),
       port61(61),
       port62(62),
       port63(63)
      }   
      MAX-ACCESS read-only
      STATUS current  
      DESCRIPTION     
        "Lists the status of the MELT chip for xDSL port.
         The result is analyzed as follow: If a bit in the bit string is set to 1, the MELT chip of a port is faulty. 
         For example, if the MELT chip of port 8 is faulty, the eighth character of the string is set to 1, 
         and 0000 0000 1000 0000, namely, # 0x00 0x80 is issued. 
         Note that the value of the bit type starts from 0.
        "           
      ::= { hwLoopLineTestMeltChipStateEntry 3 }
      
  hwBoardMeltChipStateCheckDCVolUpperLimit OBJECT-TYPE
      SYNTAX Integer32 (2147483647 | -60..60)
      MAX-ACCESS read-write
      STATUS current      
      DESCRIPTION
        "Indicates the upper limit of dc-voltage for melt chip status check.
         Options:
         1. -60..60     -Valid value range
	       2. 2147483647  -Invalid value
         Default: 1
         Unit: volt
        "
      DEFVAL { 1 }
      ::= { hwLoopLineTestMeltChipStateEntry 4 }   

  hwBoardMeltChipStateCheckDCVolLowerLimit OBJECT-TYPE
      SYNTAX Integer32 (2147483647 | -60..60)
      MAX-ACCESS read-write
      STATUS current
      DESCRIPTION
        "Indicates the lower limit of dc-voltage for melt chip status check.
         Options:
         1. -60..60     -Valid value range
	       2. 2147483647  -Invalid value
         Default: -1
         Unit: volt
        "
      DEFVAL { -1 }
      ::= { hwLoopLineTestMeltChipStateEntry 5 }

  hwMeltChipStateCheck OBJECT IDENTIFIER ::= { hwTestCommonMIBObjects 14 }

  hwMeltChipStateCheckConfig OBJECT-TYPE
      SYNTAX INTEGER 
      { 
      enabled(1),
      disabled(2)
      }
      MAX-ACCESS read-write
      STATUS current
      DESCRIPTION
        "Enables or disables MELT chip status check.
         Options:
         1. enabled(1)   -Enables MELT chip status check 
         2. disabled(2)  -Disables MELT chip status check
         Default: disabled(2)
        "
      ::= { hwMeltChipStateCheck 1 }

  hwMeltChipStateCheckTime OBJECT-TYPE
      SYNTAX TimeTicks
      MAX-ACCESS read-write
      STATUS current
      DESCRIPTION
        "Indicates the start time of the MELT chip status check.
         This value can be converted into the hexadecimal 
 	       number 0x00hhmmss (hh representing hour, mm representing minute, 
 	       and ss representing second), and then can be converted into the value of 
 	       the object through a decimal conversion. If the time of MELT chip status check 
 	       needs to be set to 22:30:00, the corresponding value is 0x00161E00=1449472, 
 	       with 1449472 being the set value.
        "        
      ::= { hwMeltChipStateCheck 2 }      

  hwMeltChipStateCheckDCVolUpperLimit OBJECT-TYPE
      SYNTAX      Integer32 (-60..60)
      MAX-ACCESS read-write
      STATUS current
      DESCRIPTION
        "Indicates the upper limit of dc-voltage for melt chip status check.
         Options:
         1. -60..60     -Valid value range
         Default: 1
         Unit: volt
        "
      ::= { hwMeltChipStateCheck 3 }      

  hwMeltChipStateCheckDCVolLowerLimit OBJECT-TYPE
      SYNTAX      Integer32 (-60..60)
      MAX-ACCESS read-write
      STATUS current
      DESCRIPTION
        "Indicates the lower limit of dc-voltage for melt chip status check.
         Options:
         1. -60..60     -Valid value range
         Default: -1
         Unit: volt
        "
      ::= { hwMeltChipStateCheck 4 }


  END
