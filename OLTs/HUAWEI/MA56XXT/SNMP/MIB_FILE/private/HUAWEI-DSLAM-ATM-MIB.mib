-- ============================================================================
-- Copyright (C) 2014 by  HUAWEI TECHNOLOGIES. All rights reserved.
-- Description: The MIB module defines MIB objects which provide ATM interfaces 
--              management.
-- Reference:  
-- Version: V1.09
-- ============================================================================

  HUAWEI-DSLAM-ATM-MIB DEFINITIONS ::= BEGIN

    IMPORTS 
      ifIndex, InterfaceIndex
        FROM IF-MIB
      huaweiUtility
        FROM HUAWEI-MIB       
      hwFrameIndex, hwSlotIndex, hwFrameIndex, hwSlotIndex, hwPortIndex
        FROM HUAWEI-DEVICE-MIB      
      Gauge32, Integer32, OBJECT-TYPE, MODULE-IDENTITY, NOTIFICATION-TYPE     
        FROM SNMPv2-SMI     
      DateAndTime, RowStatus      
        FROM SNMPv2-TC;

    hwmusaAtm MODULE-IDENTITY
      LAST-UPDATED "201406300000Z"
      ORGANIZATION
        "Huawei Technologies Co.,Ltd."  
      CONTACT-INFO 
        "Huawei Industrial Base
         Bantian, Longgang
         Shenzhen 518129
         People's Republic of China
         Website: http://www.huawei.com
         Email: support@huawei.com
        "
      DESCRIPTION
        "The MIB module defines MIB objects which provide ATM interfaces management."

--  Revision history
      REVISION "201406300000Z"
      DESCRIPTION
        "V1.09, modified the mib file name HUAWEI-ATM-MIB to HUAWEI-DSLAM-ATM-MIB, because HUAWEI-ATM-MIB already exists in new OMSYS tool."
	
      REVISION "201011200000Z"
      DESCRIPTION
        "V1.08, modified the description of MIB.
        "
      REVISION "201010090000Z"
      DESCRIPTION
        "V1.07, modified the description of MIB.
        "
      REVISION "201006220000Z"
      DESCRIPTION
        "V1.06, modified the mib file name HWMUSA-ATM-MIB to HUAWEI-ATM-MIB.
        "
      REVISION "201004020000Z"
      DESCRIPTION
        "V1.05, added leaf hwAtmReferenceColckRecoverAlarmTrap.
         Modified the syntax error."
        
      REVISION "201002080000Z"
      DESCRIPTION
        "V1.04, modified the definition of the leaf."
        
      REVISION "201001120000Z"
      DESCRIPTION
        "V1.03, added the definition of the leaf."
      
      REVISION "200904140000Z"
      DESCRIPTION
        "V1.02, modified compiling error."
        
      REVISION "200805310000Z"
      DESCRIPTION
        "V1.01, deleted chinese character."

      REVISION "200611240000Z"
      DESCRIPTION
        "V1.00, initial version."
        
      ::= { huaweiUtility 99 }


    hwmusaAtmInterfaceExtTable OBJECT-TYPE
      SYNTAX SEQUENCE OF HwmusaAtmInterfaceExtEntry
      MAX-ACCESS not-accessible
      STATUS current
      DESCRIPTION
        "ATM interface extend table, it is used for setting or querying atm port extend configuration.
         The index of this table is ifIndex."
      ::= { hwmusaAtm 100 }

    hwmusaAtmInterfaceExtEntry OBJECT-TYPE
      SYNTAX HwmusaAtmInterfaceExtEntry
      MAX-ACCESS not-accessible
      STATUS current
      DESCRIPTION
        "ATM interface extend table, it is used for setting or querying atm port extend configuration.
         The index of this entry is ifIndex."
      INDEX { ifIndex }
      ::= { hwmusaAtmInterfaceExtTable 1 }

    HwmusaAtmInterfaceExtEntry ::=
      SEQUENCE
       { 
        hwmusaAtmInterfaceUpcNpcFlag
                INTEGER,
        hwmusaAtmInterfaceAlarmStatus
                Integer32,
        hwmusaAtmInterfaceVcSubSpace
                Integer32,
        hwmusaAtmInterfaceMyNeighborIfIndex
                InterfaceIndex,
        hwmusaAtmInterfaceInCurBandWidth
                Integer32,
        hwmusaAtmInterfaceOutCurBandwidth
                Integer32,
        hwmusaAtmInterfacePhyType
                INTEGER,
        hwmusaAtmInterfaceLineState
                INTEGER,
        hwmusaAtmInterfaceAlsStatus
                INTEGER,
        hwmusaAtmInterfaceAlsDelayTime
                Integer32,
        hwmusaAtmInterfaceAlsTxOnTime
                Integer32,
        hwmusaAtmInterfaceAlsManualTxOnTime
                Integer32,
        hwmusaAtmInterfaceMaxVpiNo
                Integer32,
        hwmusaAtmInterfaceMinVpiNo
                Integer32,
        hwmusaAtmInterfaceMaxVciNo
                Integer32,
        hwmusaAtmInterfaceMinVciNo
                Integer32,        
        hwmusaAtmInterfacePortMode
                INTEGER,
        hwmusaAtmInterfaceUNINNIMode
                INTEGER,
        hwmusaAtmInterfaceInTotalBandWidth
                Integer32,
        hwmusaAtmInterfaceOutTotalBandwidth
                Integer32,
        hwmusaAtmInterfaceTxClock
                INTEGER,
        hwmusaAtmInterfaceEventInsert
                Integer32,
        hwmusaAtmInterfaceBipInsert
                INTEGER
      }

    hwmusaAtmInterfaceUpcNpcFlag OBJECT-TYPE
      SYNTAX      INTEGER 
      {
      enabled(1),
      disabled(2)
      }
      MAX-ACCESS  read-write
      STATUS      current
      DESCRIPTION 
        "The flag of UPC/NPC interface.
         Options:
         1. enabled(1)  -the flag of UPC/NPC interface is enabled 
         2. disabled(2) -the flag of UPC/NPC interface is disabled
        "
      DEFVAL { enabled }
      ::= { hwmusaAtmInterfaceExtEntry 1 }

    hwmusaAtmInterfaceAlarmStatus OBJECT-TYPE
      SYNTAX      Integer32
      MAX-ACCESS  read-only
      STATUS      current
      DESCRIPTION     
        "The alarm status of atm interface physical layer.
         The meaning of values:
         oof(0)      -out of frame    
         lof(1)      -loss of frame   
         los(2)      -loss of signal  
         lrdi(3)     -line remote defect indication   
         lais(4)     -line alarm indication signal    
         lop(5)      -loss of pointer (not supported currently)
         pais(6)     -path alarm indication signal    
         prdi(7)     -path remote defect indication   
         psbf(8)     -protection switching byte failure  
         sbip(9)     -section BIP     
         sbipe(10)   -section BIP exceeding threshold (not supported currently)
         lbip(11)    -line BIP        
         lbipe(12)   -line BIP exceeding threshold (not supported currently)
         lfebe(13)   -line far end block error        
         lfebee(14)  -line far end block error exceeding threshold (not supported currently)
         pbip(15)    -path BIP        
         pbipe(16)   -path BIP exceeding threshold (not supported currently)
         pfebe(17)   -path far end block error        
         pfebee(18)  -path far end block error exceeding threshold (not supported currently)
         hcs(19)     -head check sequence             
         chcs(20)    -correctable head check sequence 
         uhcs(21)    -uncorrectable head check sequence 
         lcd(22)     -loss of cell delineation        
         ocd(23)     -out of cell delineation         
         aprdi(24)   -auxiliary path remote defect indication (not supported currently)
         ber(25)     -bit error rate (not supported currently) 
        "
      ::= { hwmusaAtmInterfaceExtEntry 2 }

    hwmusaAtmInterfaceVcSubSpace OBJECT-TYPE
      SYNTAX      Integer32
      MAX-ACCESS  read-write
      STATUS      current
      DESCRIPTION 
        "The vpi number of setting vc.
         The value ranges from 1 to 256 and is an integer power of 2 in MA5600T product.
         The default 16 in MA5600T product.
        "
      DEFVAL { 256 }
      ::= { hwmusaAtmInterfaceExtEntry 3 }

    hwmusaAtmInterfaceMyNeighborIfIndex OBJECT-TYPE
      SYNTAX      InterfaceIndex
      MAX-ACCESS  read-write
      STATUS      current
      DESCRIPTION 
        "The neighbor system ifIndex. "
        ::= { hwmusaAtmInterfaceExtEntry 4 }

    hwmusaAtmInterfaceInCurBandWidth OBJECT-TYPE
      SYNTAX      Integer32
      MAX-ACCESS  read-only
      STATUS      current
      DESCRIPTION 
        "The current bandwidth is available for the port incoming streams. 
         Unit: kbit/s"
      ::= { hwmusaAtmInterfaceExtEntry 5 }

    hwmusaAtmInterfaceOutCurBandwidth OBJECT-TYPE
      SYNTAX      Integer32
      MAX-ACCESS  read-only
      STATUS      current
      DESCRIPTION 
        "The current bandwidth is available for the port outgoing streams.
         Unit: kbit/s"
      ::= { hwmusaAtmInterfaceExtEntry 6 }

    hwmusaAtmInterfacePhyType OBJECT-TYPE
      SYNTAX      INTEGER
      {
      unknown(1),
      singleMode(2),
      multiMode(3),
      electricPort(4)
      }
      MAX-ACCESS  read-only
      STATUS      current
      DESCRIPTION 
        "The ATM interface physical attribute.
         Options:
         1. unknown(1)       -unknown
         2. singleMode(2)    -single mode fiber
         3. multiMode(3)     -multi mode fiber
         4. electricPort(4)  -electric port
        "
      ::= { hwmusaAtmInterfaceExtEntry 7 }

    hwmusaAtmInterfaceLineState OBJECT-TYPE
      SYNTAX      INTEGER
      {
      noSignal(1),
      haveSignal(2)
      }
      MAX-ACCESS  read-only
      STATUS      current
      DESCRIPTION 
        "ATM interface line state.
         Options:
         1. noSignal(1)     -the ATM interface no signal
         2. haveSignal(2)   -the ATM interface have signal
        "
      ::= { hwmusaAtmInterfaceExtEntry 8 }    

    hwmusaAtmInterfaceAlsStatus OBJECT-TYPE
      SYNTAX      INTEGER 
      {
      off(1),
      on(2)
      }
      MAX-ACCESS  read-write
      STATUS      current
      DESCRIPTION 
        "ALS switch state.
         Options:
         1. off(1)   -ALS switch off
         2. on(2)    -ALS switch on
        "
      ::= { hwmusaAtmInterfaceExtEntry 9 }    

    hwmusaAtmInterfaceAlsDelayTime OBJECT-TYPE
      SYNTAX Integer32 (60..300)
      MAX-ACCESS  read-write
      STATUS      current
      DESCRIPTION 
        "ALS auto delay time for start TxOn signal."
      ::= { hwmusaAtmInterfaceExtEntry 10 }    

    hwmusaAtmInterfaceAlsTxOnTime OBJECT-TYPE
      SYNTAX Integer32 (1..90)
      MAX-ACCESS  read-write
      STATUS      current
      DESCRIPTION 
        "ALS auto time for start TxOn signal."
      ::= { hwmusaAtmInterfaceExtEntry 11 }

    hwmusaAtmInterfaceAlsManualTxOnTime OBJECT-TYPE
      SYNTAX Integer32 (1..90)
      MAX-ACCESS  read-write
      STATUS      current
      DESCRIPTION 
        "ALS user time for start manual TxOn signal."
      ::= { hwmusaAtmInterfaceExtEntry 12 }
    
    hwmusaAtmInterfaceMaxVpiNo OBJECT-TYPE
      SYNTAX Integer32(0..4095)
      MAX-ACCESS read-write
      STATUS current
      DESCRIPTION
        "Indicate the max VPI number."
      ::= { hwmusaAtmInterfaceExtEntry 101 }

    hwmusaAtmInterfaceMinVpiNo OBJECT-TYPE
      SYNTAX Integer32(0..4095)
      MAX-ACCESS read-write
      STATUS current
      DESCRIPTION
        "Indicate the min VPI number."
      ::= { hwmusaAtmInterfaceExtEntry 102 }

    hwmusaAtmInterfaceMaxVciNo OBJECT-TYPE
      SYNTAX Integer32(32..1023)
      MAX-ACCESS read-write
      STATUS current
      DESCRIPTION
        "Indicate the max VCI number."
      ::= { hwmusaAtmInterfaceExtEntry 103 }

    hwmusaAtmInterfaceMinVciNo OBJECT-TYPE
      SYNTAX Integer32(32..1023)
      MAX-ACCESS read-write
      STATUS current
      DESCRIPTION
        "Indicate the min VCI number."
      ::= { hwmusaAtmInterfaceExtEntry 104 }
      
    hwmusaAtmInterfacePortMode OBJECT-TYPE
      SYNTAX INTEGER 
      {
      oc3corsts3(1),
      stm1(2),
      oc12corsts12(3),
      stm4(4)
      }
      MAX-ACCESS read-write
      STATUS current
      DESCRIPTION
        "Indicate the mode of ATM interface port.
         Options:
         1. oc3corsts3(1)    -OC3
         2. stm1(2)          -STM1
         3. oc12corsts12(3)  -OC1
         4. stm4(4)          -STM4
         "
      ::= { hwmusaAtmInterfaceExtEntry 105 }
      
    hwmusaAtmInterfaceUNINNIMode OBJECT-TYPE
      SYNTAX INTEGER 
      {
      uni(1),
      nni(2)
      }
      MAX-ACCESS read-write
      STATUS current
      DESCRIPTION
        "Indicate the UNI/NNI type of ATM interface.
         Options:
         1. uni(1)   -UNI mode
         2. nni(2)   -NNI mode
         "
      ::= { hwmusaAtmInterfaceExtEntry 106 }

    hwmusaAtmInterfaceInTotalBandWidth OBJECT-TYPE
      SYNTAX      Integer32
      MAX-ACCESS  read-only
      STATUS      current
      DESCRIPTION 
        "The total current bandwidth for the port incoming streams. 
         Unit: kbit/s
        "
      ::= { hwmusaAtmInterfaceExtEntry 107 }

    hwmusaAtmInterfaceOutTotalBandwidth OBJECT-TYPE
      SYNTAX      Integer32
      MAX-ACCESS  read-only
      STATUS      current
      DESCRIPTION 
        "The total current bandwidth for the port outgoing streams. 
         Unit: kbit/s
        "
      ::= { hwmusaAtmInterfaceExtEntry 108 }
                        
    hwmusaAtmInterfaceTxClock OBJECT-TYPE
      SYNTAX INTEGER 
      {
      system(1),
      line(2),
      invalid(-1)
      }
      MAX-ACCESS read-write
      STATUS current
      DESCRIPTION
        "The transmit clock type of the interface.
         Options:
         1. system(1)     -system transmit clock
         2. line(2)       -line transmit clock
         3. invalid(-1)   -invalid value
         "
      ::= { hwmusaAtmInterfaceExtEntry 109 }
      
    hwmusaAtmInterfaceEventInsert OBJECT-TYPE
      SYNTAX Integer32 (0..31)
      MAX-ACCESS read-write
      STATUS current
      DESCRIPTION
        "Insert or cancel alarm event in the interface.
         The value is bit map, set the bit can insert the event, clear the bit can cancel the event.
         The various bit positions are:
         1   -LAIS
         2   -LOF  
         4   -LOS
         8   -LRDI
         16  -PAIS"
      ::= { hwmusaAtmInterfaceExtEntry 110 }
      
    hwmusaAtmInterfaceBipInsert OBJECT-TYPE
      SYNTAX INTEGER 
      {
      lbip(1),
      pbip(2),
      sbip(3)
      }
      MAX-ACCESS read-write
      STATUS current
      DESCRIPTION
        "Insert BIP error code type in the interface.
         Options:
         1. lbip(1)   -L-bip
         2. pbip(2)   -P-bip
         3. sbip(3)   -S-bip
         "
      ::= { hwmusaAtmInterfaceExtEntry 111 }

    hwmusaAtmStatisticTable OBJECT-TYPE
      SYNTAX SEQUENCE OF HwmusaAtmStatisticEntry
      MAX-ACCESS not-accessible
      STATUS current
      DESCRIPTION
        "The table of ATM interface statistic, it is used for querying Tx/Rx number of cells.
         The index of this table is ifIndex."
      ::= { hwmusaAtm 101 }
    
    hwmusaAtmStatisticEntry OBJECT-TYPE
      SYNTAX HwmusaAtmStatisticEntry
      MAX-ACCESS not-accessible
      STATUS current
      DESCRIPTION
        "The table of ATM interface statistic, it is used for querying Tx/Rx number of cells.
         The index of this entry is ifIndex."
      INDEX { ifIndex }
      ::= { hwmusaAtmStatisticTable 1 }

    HwmusaAtmStatisticEntry ::=
      SEQUENCE 
      { 
        hwmusaAtmStatisticTxCellSucc
          Gauge32,
        hwmusaAtmStatisticRxCellSucc
          Gauge32,
        hwmusaAtmStatisticRowStatus
          RowStatus
       }

    hwmusaAtmStatisticTxCellSucc OBJECT-TYPE
      SYNTAX Gauge32
      MAX-ACCESS read-only
      STATUS current
      DESCRIPTION
        "Indicate the number of cells transmitted in the atm interface.
        "
      ::= { hwmusaAtmStatisticEntry 1 }

    hwmusaAtmStatisticRxCellSucc OBJECT-TYPE
      SYNTAX Gauge32
      MAX-ACCESS read-only
      STATUS current
      DESCRIPTION
        "Indicate the number of cells received in the atm interface."
      ::= { hwmusaAtmStatisticEntry 2 }

    hwmusaAtmStatisticRowStatus OBJECT-TYPE
      SYNTAX RowStatus
      MAX-ACCESS read-create
      STATUS current
      DESCRIPTION
        "The present operation status of the row.
         Options:
         1. active(1),        -the status of the row is active 
         2. notInService(2),  -the status of the row is notInService
         3. notReady(3),      -the status of the row is notReady
         4. createAndGo(4),   -the status of the row is createAndGo
         5. createAndWait(5), -the status of the row is createAndWait
         6. destroy(6)        -the status of the row is destroy
         "
      ::= { hwmusaAtmStatisticEntry 3 }
          
    hwAtmECSMonitorControlTable OBJECT-TYPE
      SYNTAX      SEQUENCE OF HwAtmECSMonitorControlEntry
      MAX-ACCESS  not-accessible
      STATUS      current
      DESCRIPTION
        "
        perform monitor status control table
        --STM-1/STM-4 Control table of the enabling state of the transmission performance monitoring
        The indexes of this table are ifIndex and hwAtmECSMonitorPeriodType.
        "
      ::= { hwmusaAtm 102 }

    hwAtmECSMonitorControlEntry OBJECT-TYPE
      SYNTAX      HwAtmECSMonitorControlEntry
      MAX-ACCESS  not-accessible
      STATUS      current
      DESCRIPTION
        "
        perform monitor status control table
        --STM-1/STM-4 Control table of the enabling state of the transmission performance monitoring
        The indexes of this entry are ifIndex and hwAtmECSMonitorPeriodType.
        "
      INDEX { 
              ifIndex,
              hwAtmECSMonitorPeriodType
            }
      ::= { hwAtmECSMonitorControlTable 1 }

    HwAtmECSMonitorControlEntry ::=
      SEQUENCE
      {
       hwAtmECSMonitorPeriodType                   INTEGER,
       hwAtmECSMonitorStatusReal                   INTEGER,
       hwAtmECSMonitorStartTimeReal                DateAndTime,     
       hwAtmECSMonitorStatusUserSet                INTEGER,
       hwAtmECSMonitorStartTimeUserSet             DateAndTime             
      }
      
    hwAtmECSMonitorPeriodType OBJECT-TYPE
      SYNTAX      INTEGER{quarter(1),day(2)}
      MAX-ACCESS  read-write
      STATUS      current
      DESCRIPTION
          "
          the period of the monitor, 1:quarter, 2:day.
          The monitoring periods of the bit error statistics of the SDH transmission performance, which are 15 minutes and 24 hours.
          Options:
          1. quarter(1)   -The quarter period of the monitor 
          2. day(2)       -The day period of the monitor
          "
      ::={ hwAtmECSMonitorControlEntry 1 }
    
    hwAtmECSMonitorStatusReal OBJECT-TYPE
      SYNTAX      INTEGER{disable(0),enable(1)}
      MAX-ACCESS  read-only
      STATUS      current
      DESCRIPTION
          "
          current monitor status, 0:disable, 1:enable.
          The actual states of the monitoring function of the SDH transmission performance bit error statistics, which are enable and disable.
          DEFVAL {enable}
          "
    
      ::={ hwAtmECSMonitorControlEntry 2 }

    hwAtmECSMonitorStartTimeReal OBJECT-TYPE
      SYNTAX      DateAndTime
      MAX-ACCESS  read-only
      STATUS      current
      DESCRIPTION
          "
          The actual start time of the monitoring period of the SDH transmission performance bit error statistics. 
          "
      ::={ hwAtmECSMonitorControlEntry 3 }
    
    hwAtmECSMonitorStatusUserSet OBJECT-TYPE
      SYNTAX      INTEGER{disable(0),enable(1)}
      MAX-ACCESS  read-write
      STATUS      current
      DESCRIPTION
          "
          The actual state of the monitoring function of the SDH transmission performance bit error statistics set by the user, which is enable or disable.
          "
      DEFVAL {1}
      ::={ hwAtmECSMonitorControlEntry 4 }

    hwAtmECSMonitorStartTimeUserSet OBJECT-TYPE
      SYNTAX      DateAndTime
      MAX-ACCESS  read-write
      STATUS      current
      DESCRIPTION
          "
          The time of enabling or disabling the periodical monitoring of the SDH transmission performance bit error statistics set by the user.
          "
      ::={ hwAtmECSMonitorControlEntry 5 }

--STM-1/STM-4 Control table of the enabling state of the transmission performance monitoring threshold
      
    hwAtmECSThresholdControlTable OBJECT-TYPE
      SYNTAX      SEQUENCE OF HwAtmECSThresholdControlEntry
      MAX-ACCESS  not-accessible
      STATUS      current
      DESCRIPTION
        "
        STM-1/STM-4 threshold enable table
        --STM-1/STM-4 Control table of the enabling state of the transmission performance monitoring.
        The indexes of this table are ifIndex, hwAtmECSMonitorObjType and hwAtmECSMonitorPeriodType.
        "
      ::= { hwmusaAtm 103 }

    hwAtmECSThresholdControlEntry OBJECT-TYPE
      SYNTAX      HwAtmECSThresholdControlEntry
      MAX-ACCESS  not-accessible
      STATUS      current
      DESCRIPTION
        "
        STM-1/STM-4 threshold enable table
        --STM-1/STM-4 Control table of the enabling state of the transmission performance monitoring.
        The indexes of this entry are ifIndex, hwAtmECSMonitorObjType and hwAtmECSMonitorPeriodType.
        "
      INDEX { 
              ifIndex,
              hwAtmECSMonitorObjType,
              hwAtmECSMonitorPeriodType
            }
      ::= { hwAtmECSThresholdControlTable 1 }
      
    HwAtmECSThresholdControlEntry ::=
      SEQUENCE
      {
       hwAtmECSMonitorObjType                 INTEGER,
       hwAtmECSThresholdEnabled               INTEGER
      
      }
      
    hwAtmECSMonitorObjType OBJECT-TYPE
      SYNTAX      INTEGER{rs(0),ms(1),hp(2)}
      MAX-ACCESS  read-write
      STATUS      current
      DESCRIPTION
          "
           the section of the perform monitor,
           Options:
           1. rs(0)       -The regenerator section
           2. ms(1)       -The multiplex section
           3. hp(2)       -The higher order path 
           
           The monitoring objects of the SDH transmission performance bit error statistics, which are the regenerator section, multiplex section, and higher order path
          "
      ::={ hwAtmECSThresholdControlEntry 1 }
      
    hwAtmECSThresholdEnabled OBJECT-TYPE
      SYNTAX      INTEGER{disable(0),enable(1)}
      MAX-ACCESS  read-write
      STATUS      current
      DESCRIPTION
          "
           SDH threshold enable
           The enabling state of the monitoring threshold of the SDH transmission performance bit error statistics
          "
      DEFVAL {1}
      ::={ hwAtmECSThresholdControlEntry 2 }
          
          
--The monitoring threshold table of the STM-1/STM-4 transmission performance bit error statistics of the ATM port
      
    hwAtmECSThresholdTable OBJECT-TYPE
      SYNTAX      SEQUENCE OF HwAtmECSThresholdEntry
      MAX-ACCESS  not-accessible
      STATUS      current
      DESCRIPTION
        "
         STM-1/STM-4 monitor threshold table
         The monitoring threshold table of the STM-1/STM-4 transmission performance bit error statistics of the ATM port
         The indexes of this table are ifIndex, hwAtmECSMonitorObjType and hwAtmECSMonitorPeriodType.
        "
      ::= { hwmusaAtm 104 }

    hwAtmECSThresholdEntry OBJECT-TYPE
      SYNTAX      HwAtmECSThresholdEntry
      MAX-ACCESS  not-accessible
      STATUS      current
      DESCRIPTION
        "
         STM-1/STM-4 monitor threshold table
         The monitoring threshold table of the STM-1/STM-4 transmission performance bit error statistics of the ATM port
         The indexes of this entry are ifIndex, hwAtmECSMonitorObjType and hwAtmECSMonitorPeriodType.
        "
      INDEX { 
              ifIndex,
              hwAtmECSMonitorObjType,
              hwAtmECSMonitorPeriodType
            }
      ::= { hwAtmECSThresholdTable 1 }

    HwAtmECSThresholdEntry ::=
      SEQUENCE
      {
        hwAtmECSThresholdOFS          Gauge32,
        hwAtmECSThresholdLowBBE       Gauge32,
        hwAtmECSThresholdHighBBE      Gauge32,
        hwAtmECSThresholdLowFEBBE     Gauge32,
        hwAtmECSThresholdHighFEBBE    Gauge32,
        hwAtmECSThresholdLowES        Gauge32,
        hwAtmECSThresholdHighES       Gauge32,
        hwAtmECSThresholdLowFEES      Gauge32,
        hwAtmECSThresholdHighFEES     Gauge32,
        hwAtmECSThresholdSES          Gauge32,
        hwAtmECSThresholdFESES        Gauge32,
        hwAtmECSThresholdUAS          Gauge32,
        hwAtmECSThresholdCSES         Gauge32
        
      }
    
    hwAtmECSThresholdOFS OBJECT-TYPE
      SYNTAX      Gauge32
      MAX-ACCESS  read-write
      STATUS      current
      DESCRIPTION
          "
          The monitoring threshold of the out-of-frame seconds of the SDH transmission performance bit error statistics
          "
      ::={ hwAtmECSThresholdEntry 1 }
   
    hwAtmECSThresholdLowBBE OBJECT-TYPE
      SYNTAX      Gauge32
      MAX-ACCESS  read-write
      STATUS      current
      DESCRIPTION
          "
          The lower threshold of the background block error of the SDH transmission performance bit error statistics
          "
      ::={ hwAtmECSThresholdEntry 2 }
      
    hwAtmECSThresholdHighBBE OBJECT-TYPE
      SYNTAX      Gauge32
      MAX-ACCESS  read-write
      STATUS      current
      DESCRIPTION
          "
          The upper threshold of the background block error of the SDH transmission performance bit error statistics
          "
      ::={ hwAtmECSThresholdEntry 3 }
    
    hwAtmECSThresholdLowFEBBE OBJECT-TYPE
      SYNTAX      Gauge32
      MAX-ACCESS  read-write
      STATUS      current
      DESCRIPTION
          "
          The lower threshold of the far-end background block error of the SDH transmission performance bit error statistics
          "
      ::={ hwAtmECSThresholdEntry 4 }
    
    hwAtmECSThresholdHighFEBBE OBJECT-TYPE
      SYNTAX      Gauge32
      MAX-ACCESS  read-write
      STATUS      current
      DESCRIPTION
          "
          The upper threshold of the far-end background block error of the SDH transmission performance bit error statistics
          "
      ::={ hwAtmECSThresholdEntry 5 }

    hwAtmECSThresholdLowES OBJECT-TYPE
      SYNTAX      Gauge32
      MAX-ACCESS  read-write
      STATUS      current
      DESCRIPTION
          "
          The lower threshold of the errored seconds of the SDH transmission performance bit error statistics
          "
      ::={ hwAtmECSThresholdEntry 6 }

    hwAtmECSThresholdHighES OBJECT-TYPE
      SYNTAX      Gauge32
      MAX-ACCESS  read-write
      STATUS      current
      DESCRIPTION
          "
          The upper threshold of the errored seconds of the SDH transmission performance bit error statistics
          "
      ::={ hwAtmECSThresholdEntry 7 }
      
    hwAtmECSThresholdLowFEES OBJECT-TYPE
      SYNTAX      Gauge32
      MAX-ACCESS  read-write
      STATUS      current
      DESCRIPTION
          "
          The lower threshold of the far-end errored seconds of the SDH transmission performance bit error statistics
          "
      ::={ hwAtmECSThresholdEntry 8 }
    
    hwAtmECSThresholdHighFEES OBJECT-TYPE
      SYNTAX      Gauge32
      MAX-ACCESS  read-write
      STATUS      current
      DESCRIPTION
          "
          The upper threshold of the far-end errored seconds of the SDH transmission performance bit error statistics
          "
      ::={ hwAtmECSThresholdEntry 9 }
    
    hwAtmECSThresholdSES OBJECT-TYPE
      SYNTAX      Gauge32
      MAX-ACCESS  read-write
      STATUS      current
      DESCRIPTION
          "
          The monitoring threshold of the severely errored seconds of the SDH transmission performance bit error statistics
          "
      ::={ hwAtmECSThresholdEntry 10 }

    hwAtmECSThresholdFESES OBJECT-TYPE
      SYNTAX      Gauge32
      MAX-ACCESS  read-write
      STATUS      current
      DESCRIPTION
          "
          The monitoring threshold of the far-end severely errored seconds of the SDH transmission performance bit error statistics
          "
      ::={ hwAtmECSThresholdEntry 11 }

    hwAtmECSThresholdUAS OBJECT-TYPE
      SYNTAX      Gauge32
      MAX-ACCESS  read-write
      STATUS      current
      DESCRIPTION
          "
          The monitoring threshold of the unavailable seconds of the SDH transmission performance bit error statistics
          "
      ::={ hwAtmECSThresholdEntry 12 }
     
    hwAtmECSThresholdCSES OBJECT-TYPE
      SYNTAX      Gauge32
      MAX-ACCESS  read-write
      STATUS      current
      DESCRIPTION
          "
          The monitoring threshold of the consecutive severely errored seconds of the SDH transmission performance bit error statistics
          "
      ::={ hwAtmECSThresholdEntry 13 }
      
--The bit error statistical table of the STM-1/STM-4 transmission performance of the ATM port
      
    hwAtmECSDataTable OBJECT-TYPE
      SYNTAX      SEQUENCE OF HwAtmECSDataEntry
      MAX-ACCESS  not-accessible
      STATUS      current
      DESCRIPTION
        "
        STM-1/STM-4 perform monitor statistic table
        The bit error statistical table of the STM-1/STM-4 transmission performance of the ATM port
        The indexes of this table are ifIndex, hwAtmECSMonitorObjType, hwAtmECSMonitorPeriodType and hwAtmECSMonitorStage.
        "
      ::= { hwmusaAtm 105 }

    hwAtmECSDataEntry OBJECT-TYPE
      SYNTAX      HwAtmECSDataEntry
      MAX-ACCESS  not-accessible
      STATUS      current
      DESCRIPTION
        "
        STM-1/STM-4 perform monitor statistic table
        The bit error statistical table of the STM-1/STM-4 transmission performance of the ATM port
        The indexes of this entry are ifIndex, hwAtmECSMonitorObjType, hwAtmECSMonitorPeriodType and hwAtmECSMonitorStage.
        "
      INDEX { 
              ifIndex,
              hwAtmECSMonitorObjType,
              hwAtmECSMonitorPeriodType,
              hwAtmECSMonitorStage
            }
      ::= { hwAtmECSDataTable 1 }

    HwAtmECSDataEntry ::=
      SEQUENCE
      { 
        hwAtmECSMonitorStage               INTEGER,
        hwAtmECSMonitorStageStartTime      DateAndTime,
        hwAtmECSDataBBE                    Gauge32,
        hwAtmECSDataFEBBE                  Gauge32,
        hwAtmECSDataES                     Gauge32,
        hwAtmECSDataFEES                   Gauge32,
        hwAtmECSDataSES                    Gauge32,
        hwAtmECSDataFESES                  Gauge32,
        hwAtmECSDataOFS                    Gauge32,
        hwAtmECSDataUAS                    Gauge32
      }
  
    hwAtmECSMonitorStage OBJECT-TYPE
      SYNTAX      INTEGER{current(0),history(1)}
      MAX-ACCESS  read-only
      STATUS      current
      DESCRIPTION
          "
          perform monitor period stage,
          Options:
          1. current(0)       -The monitoring time is current
          2. history(1)       -The monitoring time is history
          
          The monitoring time period of the SDH transmission performance,DEFVAL {current}
          "
      
      ::={ hwAtmECSDataEntry 1 }
       
    hwAtmECSMonitorStageStartTime OBJECT-TYPE
      SYNTAX      DateAndTime
      MAX-ACCESS  read-only
      STATUS      current
      DESCRIPTION
          "
          The start time of the monitoring time period for the SDH transmission performance monitoring
          "
      ::={ hwAtmECSDataEntry 2 }

    hwAtmECSDataBBE OBJECT-TYPE
      SYNTAX      Gauge32
      MAX-ACCESS  read-only
      STATUS      current
      DESCRIPTION
          "
          Statistics of the background block error during the SDH transmission performance monitoring
          "
      ::={ hwAtmECSDataEntry 3 }

    hwAtmECSDataFEBBE OBJECT-TYPE
      SYNTAX      Gauge32
      MAX-ACCESS  read-only
      STATUS      current
      DESCRIPTION
          "
          Statistics of the far-end background block error during the SDH transmission performance monitoring
          "
      ::={ hwAtmECSDataEntry 4 }

    hwAtmECSDataES OBJECT-TYPE
      SYNTAX      Gauge32
      MAX-ACCESS  read-only
      STATUS      current
      DESCRIPTION
          "
          Statistics of the errored seconds during the SDH transmission performance monitoring
          "
      ::={ hwAtmECSDataEntry 5 }
    
    hwAtmECSDataFEES OBJECT-TYPE
      SYNTAX      Gauge32
      MAX-ACCESS  read-only
      STATUS      current
      DESCRIPTION
          "
          Statistics of the far-end errored seconds during the SDH transmission performance monitoring
          "
      ::={ hwAtmECSDataEntry 6 }
    
    hwAtmECSDataSES OBJECT-TYPE
      SYNTAX      Gauge32
      MAX-ACCESS  read-only
      STATUS      current
      DESCRIPTION
          "
          Statistics of the severely errored seconds during the SDH transmission performance monitoring
          "
      ::={ hwAtmECSDataEntry 7 }
    
    hwAtmECSDataFESES OBJECT-TYPE
      SYNTAX      Gauge32
      MAX-ACCESS  read-only
      STATUS      current
      DESCRIPTION
          "
          Statistics of the far-end severely errored seconds during the SDH transmission performance monitoring
          "
      ::={ hwAtmECSDataEntry 8 }
      
    hwAtmECSDataOFS OBJECT-TYPE
      SYNTAX      Gauge32
      MAX-ACCESS  read-only
      STATUS      current
      DESCRIPTION
          "
          Statistics of the out-of-frame seconds during the SDH transmission performance monitoring
          "
      ::={ hwAtmECSDataEntry 9 }
      
    hwAtmECSDataUAS OBJECT-TYPE
      SYNTAX      Gauge32
      MAX-ACCESS  read-only
      STATUS      current
      DESCRIPTION
          "
          Statistics of the unavailable seconds during the SDH transmission performance monitoring
          "
      ::={ hwAtmECSDataEntry 10 }
      
      
--Configuration table of the protection group
    hwmusaAtmProtectTable OBJECT-TYPE
      SYNTAX SEQUENCE OF HwmusaAtmProtectEntry
      MAX-ACCESS not-accessible
      STATUS current
      DESCRIPTION
        "
        This table is used for configuring and querying the 1 + 1, n + 1, 1 + n redundancy of the dual-homing feature.
        The indexes of this table are hwmusaAtmProtectWorkIfindex and hwmusaAtmProtectProtectIfindex."
      ::= { hwmusaAtm 106 }
    
    hwmusaAtmProtectEntry OBJECT-TYPE
      SYNTAX HwmusaAtmProtectEntry
      MAX-ACCESS not-accessible
      STATUS current
      DESCRIPTION
        "
        This table is used for configuring and querying the 1 + 1, n + 1, 1 + n redundancy of the dual-homing feature.
        The indexes of this entry are hwmusaAtmProtectWorkIfindex and hwmusaAtmProtectProtectIfindex."
      INDEX { hwmusaAtmProtectWorkIfindex, hwmusaAtmProtectProtectIfindex }
      ::= { hwmusaAtmProtectTable 1 }

    HwmusaAtmProtectEntry ::=
      SEQUENCE { 
        hwmusaAtmProtectWorkIfindex
          Integer32,
        hwmusaAtmProtectProtectIfindex
          Integer32,
        hwmusaAtmProtectActiveIfindex
          Integer32,
        hwmusaAtmProtectRowStatus
          RowStatus
       }

    hwmusaAtmProtectWorkIfindex OBJECT-TYPE
      SYNTAX Integer32
      MAX-ACCESS read-only
      STATUS current
      DESCRIPTION
        "
        Index of the working interface"
      ::= { hwmusaAtmProtectEntry 1 }

    hwmusaAtmProtectProtectIfindex OBJECT-TYPE
      SYNTAX Integer32
      MAX-ACCESS read-only
      STATUS current
      DESCRIPTION
        "
        Index of the protection interface"
      ::= { hwmusaAtmProtectEntry 2 }

    hwmusaAtmProtectActiveIfindex OBJECT-TYPE
      SYNTAX Integer32
      MAX-ACCESS read-only
      STATUS current
      DESCRIPTION
        "
        Index of the current active interface"
      ::= { hwmusaAtmProtectEntry 3 }
      
    hwmusaAtmProtectRowStatus OBJECT-TYPE
      SYNTAX RowStatus
      MAX-ACCESS read-write
      STATUS current
      DESCRIPTION
        "
        Row status is used to manage the creation and deletion of the conceptual row."
      ::= { hwmusaAtmProtectEntry 4 }
      
  -- traps    
    hwAtmTraps OBJECT IDENTIFIER ::= { hwmusaAtm 155 }
    hwAtmTrapsVbOids OBJECT IDENTIFIER ::= { hwmusaAtm 156 }
      
    hwAtmCommonTraps OBJECT IDENTIFIER ::= { hwAtmTraps 1 }
    hwAtmAlarmTraps  OBJECT IDENTIFIER ::= { hwAtmTraps 2 }
    hwAtmAlarmTrapsPrefix OBJECT IDENTIFIER ::= { hwAtmAlarmTraps 0 } 
      
    hwAtmLOCDOccurAlarmTrap NOTIFICATION-TYPE
      OBJECTS {
              hwFrameIndex,
              hwSlotIndex,
              hwPortIndex
              } 
      STATUS current
      DESCRIPTION
             "This trap will send when loss of cell delimitation (LOCD) occurs at the ATM port."
      ::= { hwAtmAlarmTraps 0 1 }
      
    hwAtmLOPOccurAlarmTrap NOTIFICATION-TYPE
      OBJECTS {
              hwFrameIndex,
              hwSlotIndex,
              hwPortIndex
              } 
      STATUS current
      DESCRIPTION
             "This trap will send when loss of pointer (LOP) occurs at the SDH layer of the ATM port."
      ::= { hwAtmAlarmTraps 0 2 }
        
    hwAtmPortReceivePathAlarmTrap NOTIFICATION-TYPE
        OBJECTS {
                hwFrameIndex,
                hwSlotIndex,
                hwPortIndex
                } 
        STATUS current
        DESCRIPTION
               "This trap will send when the ATM port receives the path alarm indication signals from the far end."
        ::= { hwAtmAlarmTraps 0 3 }
        
    hwAtmReceivePathRemoteDefectAlarmTrap NOTIFICATION-TYPE
        OBJECTS {
                hwFrameIndex,
                hwSlotIndex,
                hwPortIndex
                } 
        STATUS current
        DESCRIPTION
               "This trap will send when the ATM port receives the path remote defect indication signals from the far end."
        ::= { hwAtmAlarmTraps 0 4 }
        
    hwAtmOOFOccurAlarmTrap NOTIFICATION-TYPE
        OBJECTS {
                hwFrameIndex,
                hwSlotIndex,
                hwPortIndex
                } 
        STATUS current
        DESCRIPTION
               "This trap will send when out of frame(OOF) occurs at the SDH layer of the ATM port."
        ::= { hwAtmAlarmTraps 0 5 }
        
    hwAtmLossReferenceClockAlarmTrap NOTIFICATION-TYPE
        OBJECTS {
                hwFrameIndex,
                hwSlotIndex,
                hwPortIndex
                } 
        STATUS current
        DESCRIPTION
               "This trap will send when the loss of receiving reference clock occurs at the ATM port."
        ::= { hwAtmAlarmTraps 0 6 }
        
                
    hwAtmLOCDRecoverAlarmTrap NOTIFICATION-TYPE
        OBJECTS {
                hwFrameIndex,
                hwSlotIndex,
                hwPortIndex
                } 
        STATUS current
        DESCRIPTION
               "This trap will send when loss of cell delimitation (LOCD) recovery."
        ::= { hwAtmAlarmTraps 0 7 }
        
    hwAtmLOPRecoverAlarmTrap NOTIFICATION-TYPE
        OBJECTS {
                hwFrameIndex,
                hwSlotIndex,
                hwPortIndex
                } 
        STATUS current
        DESCRIPTION
               "This trap will send when loss of pointer (LOP) recovery."
        ::= { hwAtmAlarmTraps 0 8 }
        
    hwAtmPAISRecoverAlarmTrap NOTIFICATION-TYPE
        OBJECTS {
                hwFrameIndex,
                hwSlotIndex,
                hwPortIndex
                } 
        STATUS current
        DESCRIPTION
               "This trap will send when path alarm indication signal(PAIS) recovery."
        ::= { hwAtmAlarmTraps 0 9 }
        
    hwAtmPRDIRecoverAlarmTrap NOTIFICATION-TYPE
        OBJECTS {
                hwFrameIndex,
                hwSlotIndex,
                hwPortIndex
                } 
        STATUS current
        DESCRIPTION
               "This trap will send when path remote defect indication(PRDI) recovery ."
        ::= { hwAtmAlarmTraps 0 10 }
        
    hwAtmOOFRecoverAlarmTrap NOTIFICATION-TYPE
        OBJECTS {
                hwFrameIndex,
                hwSlotIndex,
                hwPortIndex
                } 
        STATUS current
        DESCRIPTION
               "This trap will send when out of frame (OOF) recovery."
        ::= { hwAtmAlarmTraps 0 11 }
        
    hwAtmReferenceColckRecoverAlarmTrap NOTIFICATION-TYPE
        OBJECTS {
                hwFrameIndex,
                hwSlotIndex,
                hwPortIndex
                } 
        STATUS current
        DESCRIPTION
               "This trap will send when loss of receiving reference clock recovery at the ATM port."
        ::= { hwAtmAlarmTraps 0 12 }          
                
    hwAtmLicenseInsufficientAlarmTrap NOTIFICATION-TYPE
        OBJECTS {
                hwFrameIndex,
                hwSlotIndex,
                hwPortIndex
                } 
        STATUS current
        DESCRIPTION
               "This trap will send when the licenses are insufficient, so some ports or all the ports on the AIUG board are automatically deactivated."
        ::= { hwAtmAlarmTraps 0 13 }
END
