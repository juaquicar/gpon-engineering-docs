--  ============================================================================
-- Copyright (C) 2016 by  HUAWEI TECHNOLOGIES. All rights reserved.
-- Description: This MIB is used for defining clock management
--              MIB objects.
-- Reference:
-- Version: V1.48                                          
-- =============================================================================

        HUAWEI-CLK-MIB DEFINITIONS ::= BEGIN

                IMPORTS
                        huaweiUtility
                                FROM HUAWEI-MIB
                        IpAddress, Integer32, OBJECT-TYPE, MODULE-IDENTITY,NOTIFICATION-TYPE
                                FROM SNMPv2-SMI
                        RowStatus, TruthValue,DisplayString, MacAddress
                                FROM SNMPv2-TC
                        ifIndex
                                FROM IF-MIB
                        hwFrameIndex,hwSlotIndex,hwSubslotIndex,hwPortIndex,hwConfigChangeIP
                                FROM HUAWEI-DEVICE-MIB;

             hwClk MODULE-IDENTITY
	             LAST-UPDATED "201602160000Z"
                     ORGANIZATION "Huawei Technologies Co.,Ltd."
                     CONTACT-INFO
                                  "Huawei Industrial Base
                                   Bantian, Longgang
                                   Shenzhen 518129
                                   People's Republic of China
                                   Website: http://www.huawei.com
                                   Email: support@huawei.com
                                   "
                        DESCRIPTION
                          "This MIB is used for defining clock management MIB objects."
       
        --  Revision history  
        REVISION     "201602160000Z" 
        DESCRIPTION  "V1.48, Added and modified the following nodes to comply with ITU-T G.8275.1.
             Add: 
                     hwPtpLocalSourceLocalPriority
                     hwPtpLocalSourcePriority2
                     hw1588ClkPtpPortNotSlave
                     hw1588ClkPtpPortLocalPriority
                     hwPtpBitsPortLocalPriority
                     hwPtpBitsOffsetScaledLogVariance
             Modify:
                     hw1588ClkType
                     hwPtpDomain
                     hwPtpBMCEnable
                     hw1588ClkPtpPortAnnounceTimeout
                     hw1588ClkPtpPortMacDestinationMac
                     hw1588ClkPtpPortDelayMechanism
                     hw1588ClkPtpPortUdpDestinationMac
                     hw1588ClkPtpPortUdpEgressSourceIp
                     hw1588ClkPtpPortUdpEgressDestinationIp
                     hw1588ClkPtpPortUdpVlanPRI
                     hw1588ClkPtpPortMacVlanPRI
                     hw1588ClkPtpPortUdpEgressDscp
                     hw1588ClkPtpPortUdpVlan
                     hw1588ClkPtpPortMacVlan
                     hw1588ClkPtpPortAnnounceSendTimeInterval
                     hw1588ClkPtpPortSyncSendTimeInterval
                     hw1588ClkPtpPortReqSendTimeInterval 
                     hwPtpBitsClockAccuracy
                     hwPtpBitsClockClass
                     hwPtpBitsPriority1
                     hw1588ClkPtpPortLineWarpValue
                     "
	
        REVISION     "201511110000Z" 
        DESCRIPTION  "V1.47, Add hwClkFreqDeviation of HwClockInManageEntry."
					  
        REVISION     "201510280000Z" 
        DESCRIPTION  "V1.46, Add hwClkOutExternalClosedTrap of hwClkAlarmTrapsPrefix.
		              Add hwClkOutExternalOpenedTrap of hwClkAlarmTrapsPrefix.
					  Add hwExtClkOutputState for external clock output state." 
         
        REVISION     "201504150000Z" 
        DESCRIPTION  "V1.45, Correct the description of node hwClkOutType and hwClkOutTypeTrapSn." 
                   
        REVISION     "201412160000Z" 
        DESCRIPTION  "V1.44, Correct the node hwClkRowStatus from read-write to read-create."   
                      
        REVISION     "201409120000Z" 
        DESCRIPTION  "V1.43, Add hwClkQlFailTrap of hwClkAlarmTrapsPrefix.
                      Add hwClkQlRestoreTrap of hwClkAlarmTrapsPrefix."                          
						  
       
        REVISION     "201408180000Z" 
        DESCRIPTION  "V1.42, Modify the value range of the node.
                      hw1588ClkPtpPortUdpVlanPRI
                      hw1588ClkPtpPortMacVlanPRI
                      hw1588ClkPtpPortUdpEgressDscp
                      hw1588ClkPtpPortUdpVlan
                      hw1588ClkPtpPortMacVlan
                      hwPtpPortRingFiberLengthChangeValue."
                      
        REVISION     "201406230000Z" 
        DESCRIPTION  "V1.41, Modify the following not normative nodes to satisfy for the new OMSYS tool.
                      hwClock
                      hwClkInIndex
                      hwExtClkOutputMode
                      hw1588ClkInIndex
                      hwPtpBitsClockAccuracy
                      hw1588ClkPtpPortDelayMechanism
                      hw1588ClkPtpPortClockStep
                      hw1588ACRNegotiateState
                      hw1588ACRNegoMode
                      hw1588ACRServerSsm."   
        
        REVISION     "201312100000Z" 
        DESCRIPTION  "V1.40, Modify node hw1588ClkPtpPortUdpVlan and hw1588ClkPtpPortMacVlan 's sizelist."                         

       
        REVISION     "201309030000Z"
        DESCRIPTION  "V1.39, Add hw1588ACRServerTable of 1588ACR;
                      Add hw1588ACRDfx and hw1588ACRServerEntry of 1588ACR;
                      Add the following leaf nodes on hw1588ACRManage: hw1588ACRGlbEnable,
                                                                       hw1588ACRDeviceType,
                                                                       hw1588ACRVpnInstance,
                                                                       hw1588ACRAnnounceInterval,
                                                                       hw1588ACRSyncInterval,
                                                                       hw1588ACRDelayRespInterval,
                                                                       hw1588ACRAnnounceDuration,
                                                                       hw1588ACRSyncDuration,
                                                                       hw1588ACRDelayRespDuration,
                                                                       hw1588ACRNegoMode,
                                                                       hw1588ACRNegoEnable,
                                                                       hw1588ACRTraceSourceId
                     "

       
        REVISION     "201308080000Z"
        DESCRIPTION  "V1.38, Added pvx2m for getting/setting clock source PVX-2M.
                     "

       
        REVISION     "201307310000Z"
        DESCRIPTION  "V1.37, Add obsolete tags for those abandoned nodes.
                     "

       

        REVISION     "201305300000Z"
        DESCRIPTION  "V1.36, Modify some mibs which aren't true according to the simpletester.
                     "

        REVISION     "201303180000Z"
        DESCRIPTION  "V1.35, Add hwPtpParentClockID for ptp parent clockID.
                     add hwPtpParentPortNumber for ptp parent portnumber.
                     add hw1588ClkInSelectStatus to indicate whether the time source is selected.
                     modify the parameter of hwClkGmcclockIdChangeTrap.
                     modify the parameter of hwClkTimeSourcePortIdentityTrap.
                     "

                REVISION     "201211060000Z"
                DESCRIPTION  "V1.34, Add hwPtpBitsClockAccuracy for clock accuracy.
                     add hwPtpBitsClockClass for clock class.
                     add hwPtpBitsPriority1 for clock priority 1.
                     add hwPtpBitsPriority2 for clock priority 2.
                     add hwPtpBitsTimeSource for time source.
                     add hwBits1ppsDelayDirection and hwBits1ppsDelayValue for clock warp.
                     add hwPtpDomain for PTP domain.
                     add hwPtpBMCEnable for PTP BMC switch.
                     add hwPtpLockState for PTP lock state.
                     add hwPtpFreqLockStatus for PTP frequency lock state.
                     add hwPtpTimeScale for the time scale of PTP.
                     add hwPtpFrequencyTraceable for PTP Frequency Traceable.
                     add hwPtpTimeTraceable for PTP Time Traceable.
                     add hwPtpGMClockID for Grand Master Clock ID.
                     add hwPtpGrandMasterClockPriority1 for Grand Master Clock Priority1.
                     add hwPtpGrandMasterClockPriority2 for Grand Master Clock Priority2.
                     add hwPtpGrandMasterClockAccuracy for Grand Master Clock Accuracy.
                     add hwPtpGrandMasterClockClass for Grand Master Clock Class.
                     add hwPtpGrandMasterClockTimeSource for PTP GrandMaster clock timesource attribute.
                     add hwPtpPhyPhaseSubCur for PTP physics phase current warp.
                     add hwPtpPhyPhaseSubMin for PTP physics phase min warp.
                     add hwPtpPhyPhaseSubMax for PTP physics phase max warp.
                     add hwPtpPhyPhaseSubMean for PTP physics phase mean warp.
                     add hwPtpTimeSyncOffsetCur for PTP current time offset.
                     add hwPtpTimeSyncOffsetMin for PTP min time offset.
                     add hwPtpTimeSyncOffsetMax for PTP max time offset.
                     add hwPtpTimeSyncOffsetMean for PTP average time offset.
                     add hwPtpTimeMeanpathdelayCur for PTP current path delay.
                     add hwPtpTimeMeanpathdelayMin for PTP min path delay.
                     add hwPtpTimeMeanpathdelayMax for PTP max path delay.
                     add hwPtpTimeMeanpathdelayMean for PTP average path delay.
                     add hwPtpDlyMeasureEnable for ptp asymmetry measure switch.
                     add hw1588ClkPtpPortDelayMechanism for delay mechanism.
                     add hw1588ClkPtpPortMacDestinationMac for PTP port MAC egress destination MAC address.
                     add hw1588ClkPtpPortUdpDestinationMac for PTP port UDP egress destination MAC address.
                     add hw1588ClkPtpPortUdpEgressSourceIp for PTP port UDP egress source IP address.
                     add hw1588ClkPtpPortUdpEgressDestinationIp for PTP port UDP egress destination IP address.
                     add hw1588ClkPtpPortUdpVlanPRI for PTP port UDP egress packet priority.
                     add hw1588ClkPtpPortMacVlanPRI for PTP port Mac egress packet priority.
                     add hw1588ClkPtpPortUdpEgressDscp for PTP port UDP egress dscp value.
                     add hw1588ClkPtpPortClockStep for clock step mode.
                     add hw1588ClkPtpPortUdpVlan for PTP port UDP egress vlan ID.
                     add hw1588ClkPtpPortMacVlan for PTP port MAC egress vlan ID.
                     Modified the encoding rule of hwClkInPostion's value .
                     "

        REVISION    "201205200000Z"
        DESCRIPTION "V1.33,Added hwClkEsmcLoseTrap, hwClkEsmcRestoreTrap and hwClkQlChangeTrap."

                       REVISION    "201201050000Z"
                DESCRIPTION "V1.32,Modified hwExtClkOutputBitsType's enumerated value.
                             Modified hwClkInBitsImpedance's enumerated value.
                             Modified hwClkInBitsType's enumerated value."

                       REVISION    "201111220000Z"
                DESCRIPTION "V1.31, implemented DT requirements and changed the syntax and semantics of SIMPLETEST.
                             Modified hwSubslotIndex from hwSubSlotIndex for compiling problem.
                             Modified hwClkHoldoffTime's enumerated value.
                             Added hwQlInputLowerLimit"

                REVISION    "201010120000Z"
                DESCRIPTION "V1.30, add the objects of hwClkNoTraceTrap and hwClkNoTraceRecoversTrap for standard traps.
                            Added hwClkOutTypeTrapSn to hwClkNoTraceTrap and hwClkNoTraceRecoversTrap.
                            "

                REVISION    "201007200000Z"
                DESCRIPTION "V1.29, modified the objects of hwClkGmcclockIdChangeTrap and hwClkTimeSourcePortIdentityTrap for standard traps.
                            Added hw3rdClkOldSubBoardWorkMode to hwClkSubcardWorkmodeSwitchesTrap.
                            "

                REVISION    "201007030000Z"
                DESCRIPTION "V1.28, added hwExtClkOutputBitsType for getting/setting output signals of the GPIO board."

                REVISION    "201005060000Z"
                DESCRIPTION "V1.27, added hw1588ClkInWorkMode for getting/setting time source work mode.
                            Added enum ppsnmea(3) to hwBitsPortTimeWorkMode.
                            Modified pps(1) to ppsubx(1) in hwBitsPortTimeWorkMode.
                            Added hwClkLockState for getting clock source lock state.
                            Added hwPTPEnable for enabling current 1588v2 or 1588ACR function.
                            Added hw1588ClkDSCP for getting/setting clock source dscp.
                            Added hw1588ClkVlanPRI for getting/setting the clock source VLAN priority.
                            Added hw1588ACRReqSendTimeInterval for getting/setting the transmit interval of time source request packets.
                            Added hw1588ACRSourceIp for getting/setting time source IP address.
                            Added hw1588ACRDSCP for getting/setting time source dscp.
                            Added hw1588ACRVlan for getting/setting time source VLAN.
                            Added hw1588ACRVlanPRI for getting/setting time source VLAN priority.
                            "

                REVISION    "201004120000Z"
                DESCRIPTION "V1.26, modified the MIB for clearing simple testing errors and warnings and added hwQlOutputUpperLimit."

                REVISION    "201003240000Z"
                DESCRIPTION "V1.25, added hw1588ClkPtpPortMsgFormat, hw1588ClkPtpPortInfoMode, hw1588ClkPtpPortAnnounceSendTimeInterval,
                            hw1588ClkPtpPortSyncSendTimeInterval, hw1588ClkPtpPortReqSendTimeInterval, hw1588ClkPtpPortLineWarpMode,
                            hw1588ClkPtpPortLineWarpDirect, hw1588ClkPtpPortLineWarpValue, hw1588ClkPtpPortAnnounceTimeout, and
                            hw1588ClkPtpPortDomainNum for the 1588 clock.
                            "

                REVISION    "201002020000Z"
                DESCRIPTION "V1.24,Modified description."

                REVISION    "201001070000Z"
                DESCRIPTION "V1.23,Modified hwExtClkoutputThresholdSsmQl."

                REVISION    "200912010000Z"
                DESCRIPTION "V1.22,Modified hwClkInQL's enumerated value."

                REVISION    "200911170000Z"
                DESCRIPTION "V1.21,Added hwClkInQL, hwClkInFaultRecord, and hwClkInClearFaultRecord."

                REVISION    "200910160000Z"
                DESCRIPTION "V1.20,Added hwBitsPortManageTable."

                REVISION    "200906150000Z"
                DESCRIPTION "V1.19,Added hwACMClockIPTable."

                REVISION    "200906050000Z"
                DESCRIPTION "V1.18,Added hwClockTransManageTable."

                REVISION    "200906040000Z"
                DESCRIPTION "V1.17,Added pw(15) and copa(16) to hwClkInWorkMode."

                REVISION    "200906030000Z"
                DESCRIPTION "V1.16,Added 11 new columns to hwClock1588ManageTable."

                REVISION    "200902180000Z"
                DESCRIPTION "V1.15,Added bits_type_64K(3) to hwClkInBitsType and added bits_impedance_110ohm to hwClkInBitsImpedance."

                REVISION    "200812150000Z"
                DESCRIPTION "V1.14,Added hwClock1588ManageTable."

                REVISION    "200705120000Z"
                DESCRIPTION "V1.13,Added hwClkInBitsType."

                REVISION    "200704170000Z"
                DESCRIPTION "V1.12,Added hwClkInBitsImpedance."

                REVISION    "200611200000Z"
                DESCRIPTION "V1.11,Modified the MIB according to standard specification."

                REVISION    "200608100000Z"
                DESCRIPTION "V1.10,Added hwClkOutputPostion and hwClkOutPortEnable."

                REVISION    "200411010000Z"
                DESCRIPTION "V1.01,Added hwUASystemWorkMode and hw3rdClkSubBoardWorkMode."

                REVISION    "200305120000Z"
                DESCRIPTION "V1.00, Initial version."

                ::= { huaweiUtility 25 }




--
-- Node definitions
--

                -- 1.3.6.1.4.1.2011.6.25.1
		hwClkMibObjects OBJECT IDENTIFIER ::= { hwClk 1 }


                -- 1.3.6.1.4.1.2011.6.25.1.1
                hwClockInManageTable OBJECT-TYPE
                        SYNTAX SEQUENCE OF HwClockInManageEntry
                        MAX-ACCESS not-accessible
                        STATUS current
                        DESCRIPTION
                                "Clock Source Management Table.
                                This table is used to add or delete the clock source and query
                                the status of the clock source.
                                The index of this table is hwClkInIndex, which is the clock source ID.
                                "
                        ::= { hwClkMibObjects 1 }


                -- 1.3.6.1.4.1.2011.6.25.1.1.1
                hwClockInManageEntry OBJECT-TYPE
                        SYNTAX HwClockInManageEntry
                        MAX-ACCESS not-accessible
                        STATUS current
                        DESCRIPTION
                                "Clock Source Management Table.
                                This table is used to add or delete the clock source and query
                                the status of the clock source.
                                The index of this entry is hwClkInIndex, which is the clock source ID.
                                "
                        INDEX { hwClkInIndex }
                        ::= { hwClockInManageTable 1 }


                HwClockInManageEntry ::=
                        SEQUENCE {
                                hwClkInIndex
                                        Integer32,
                                hwClkInPostion
                                        Integer32,
                                hwClkInWorkMode
                                        INTEGER,
                                hwClkInOperStatus
                                        INTEGER,
                                hwClkInRowStatus
                                        RowStatus,
                                hwClkInBitsImpedance
                                        INTEGER,
                                hwClkInBitsType
                                        INTEGER,
                                hwClkInQL
                                        INTEGER,
                                hwClkInFaultRecord
                                        INTEGER,
                                hwClkInClearFaultRecord
                                        INTEGER,
                                hwClkLockState
                                        INTEGER,
	          hwClkFreqDeviation
	                  Integer32
                                 }

                -- 1.3.6.1.4.1.2011.6.25.1.1.1.1
                hwClkInIndex OBJECT-TYPE
                        SYNTAX Integer32 (0..9 | 255)
			MAX-ACCESS accessible-for-notify
                        STATUS current
                        DESCRIPTION
                                "Clock source index: ranging from 0 to 9.  The value 255 indicates the local
                                clock source.
                                Range: 0-9 | 255
                                "
                        ::= { hwClockInManageEntry 1 }


                -- 1.3.6.1.4.1.2011.6.25.1.1.1.2
                hwClkInPostion OBJECT-TYPE
                        SYNTAX Integer32
                        MAX-ACCESS read-create
                        STATUS current
                        DESCRIPTION
                                "The ifIndex of physical position of clock source. If the clock source
                                isn't a sysline clock, the value will be 0xFFFFFFFFFFFFFF.
                                The first byte indicates the NO. of CESoP index.
                                The second byte indicates the NO. of frame,
                                the third byte indicates the NO. of slot and
                                the lowest byte indicates the port ID.
                                The following shows how to use parameter during the get or set operation:
                                0x 01, 00,00,00  Cesop ID;     0~1
                                0x 02, 00,00,00  System clock as an external clock
                                0x 03, 00,00,00  1588 clock as an system clock
                                0x 00, FF,00,00  Frame ID;     0~255
                                0x 00, 00,FF,00  Slot  ID;     0~255
                                0x 00, 00,00,FF  Port  ID;     0~255
                                "
                        ::= { hwClockInManageEntry 2 }


                -- 1.3.6.1.4.1.2011.6.25.1.1.1.3
                hwClkInWorkMode OBJECT-TYPE
                        SYNTAX INTEGER
                                {
                                none(1),
                                sysLine(2),
                                cesLine(3),
                                cesSrts(4),
                                e1Bits0(5),
                                e1Bits1(6),
                                f2mhzBits0(7),
                                f2mhzBits1(8),
                                msuSdh(9),
                                msuTdm(10),
                                localSurge(11),
                                xpm8k(12),
                                gPON(13),
                                pkt1588(14),
                                pw(15),
                                copa(16),
                                adaptClock(17),
                                aCMClock(18),
                                t1Bits0(19),
                                t1Bits1(20),
                                system(21),
                                acr1588(22),
                                syncEth(23),
                                pvx2m(24)
                                }
                        MAX-ACCESS read-create
                        STATUS current
                        DESCRIPTION
                                "Clock source type.
                                Includes the line clock source,  BITS clock source, and local surge source.
                                If it is line clock source of a CES port, the clock source type may be CES line or CES SRTS clock source.
                                If it is BITS clock source, the clock source type may be 2 MHZ or EL clock source of BITS0, or 2 MHZ or EL clock source of BITS1.
                                If the value is 1, it indicates that a clock source is not configured.
                                Options:
                                1.none(1)                       - indicates that clock source not configured
                                2.sysLine(2)                    - indicates that line clock source that needs to specify frame/slot/port
                                3.cesLine(3)                    - indicates that line_clk of a CES clock source
                                4.cesSrts(4)                    - indicates that srts_clk of a CES clock source
                                5.e1Bits0(5)                    - indicates that EL type of a BITS0 clock source
                                6.e1Bits1(6)                    - indicates that EL type of a BITS1 clock source
                                7.f2mhzBits0(7)                 - indicates that 2MHZ type of a BITS0 clock source
                                8.f2mhzBits1(8)                 - indicates that 2MHZ type of a BITS1 clock source
                                9.msuSdh(9)                     - indicates that sdh_clk of an MSU clock source
                                10.msuTdm(10)                   - indicates that tdm_clk of an MSU clock source
                                11.localSurge(11)               - indicates that local surge clock
                                12.xpm8k(12)                    - indicates that xpm-8k type of a xpm-8k clock source
                                13.gPON(13)                     - indicates that 2MHZ type of a clock source at H601GP1A board
                                14.pkt1588(14)                  - indicates that frequency synchronization from 1588
                                15.pw(15)                       - indicates that Pseudo-Wire clock source
                                16.copa(16)                     - indicates that EL clock source of H601COPA board
                                17.adaptClock(17)               - indicates that clock adapt from CESoP
                                18.aCMClock(18)                 - indicates that ACM clock
                                19.t1Bits0(19)                  - indicates that TL type of a BITS0 clock source
                                20.t1Bits1(20)                  - indicates that TL type of a BITS1 clock source
                                21.system(21)                   - indicates that system clock source
                                22.acr1588(22)                  - indicates that 1588ACR clock source
                                23.syncEth(23)                  - indicates that syncEth clock source
                                24.pvx2m(24)                    - indicates that PVX-2M clock source
                                "
                        ::= { hwClockInManageEntry 3 }


                -- 1.3.6.1.4.1.2011.6.25.1.1.1.4
                hwClkInOperStatus OBJECT-TYPE
                        SYNTAX INTEGER
                                {
                                none(1),
                                normal(2),
                                failure(3),
                                failureLoss(4),
                                failureEFD(5)
                                }
                        MAX-ACCESS read-only
                        STATUS current
                        DESCRIPTION
                                "Clock source state.
                                Options:
                                1.none(1)        - indicates that the clock source index isn't configured
                                2.normal(2)      - indicates that the state of the clock source is active
                                3.failure(3)     - indicates that the state of the clock source fails and this leaf is not used on the OLT
                                4.failureLoss(4) - indicates that the clock source fails due to signal loss
                                5.failureEFD(5)  - indicates that the clock source fails due to frequency offset
                                "
                        ::= { hwClockInManageEntry 4 }


                -- 1.3.6.1.4.1.2011.6.25.1.1.1.5
                hwClkInRowStatus OBJECT-TYPE
                        SYNTAX RowStatus
                        MAX-ACCESS read-create
                        STATUS current
                        DESCRIPTION
                                "Clock Source operation:
                                A user can add a clock source or clear a clock source.
                                After a user adds a clock source,the clock works in trace mode.
                                After a user clears a clock source, the clock works in srystal mode.
                                To set the position(frame,slot,port) and oper(4), these two operations
                                must be set together.
                                Oper(6) can be set by itself. To set a BITS clock source,
                                the frame,slot,port parameters are useless.
                                Oper(6) is used to clear a clock source.
                                "
                        ::= { hwClockInManageEntry 5 }


                -- 1.3.6.1.4.1.2011.6.25.1.1.1.6
                hwClkInBitsImpedance OBJECT-TYPE
                        SYNTAX INTEGER
                                {
                                bitsImpedance75ohm(1),
                                bitsImpedance120ohm(2),
                                bitsImpedance110ohm(3),
                                bitsImpedance100ohm(4),
                                bitsImpedanceNone(255)
                                }
                        MAX-ACCESS read-create
                        STATUS current
                        DESCRIPTION
                                "BITS clock impedance type.The impedance value must be set when the clock source is a bits clock.
                                Options:
                                1. bitsImpedance75ohm(1)        - indicates that the impedance of this BITS clock source is 75 ohm
                                2. bitsImpedance120ohm(2)        - indicates that  the impedance of this BITS clock source is 120 ohm
                                3. bitsImpedance110ohm(3)        - indicates that  the impedance of this BITS clock source is 110 ohm
                                4. bitsImpedance100ohm(4)        - indicates that  the impedance of this BITS clock source is 100 ohm
                                5. bitsImpedanceNone(255)        - indicates that this clock source is not a BITS clock
                                "
                        ::= { hwClockInManageEntry 6 }


                -- 1.3.6.1.4.1.2011.6.25.1.1.1.7
                hwClkInBitsType OBJECT-TYPE
                        SYNTAX INTEGER
                                {
                                bitsType2MHz(1),
                                bitsType2Mbps(2),
                                bitsType64K(3),
                                bitsType1544bps(4),
                                bitsTypeNone(255)
                                }
                        MAX-ACCESS read-create
                        STATUS current
                        DESCRIPTION
                                "BITS clock type:
                                Options:
                                1.bitsType2MHz(1)       -  indicates that the BITS clock type is 2MHz
                                2.bitsType2Mbps(2)      -  indicates that the BITS clock type is 2bps
                                3.bitsType64K(3)        -  indicates that the BITS clock type is 64K
                                4.bitsType1544bps(4)  -  indicates that the BITS clock type is bitsType1.544Mbps
                                5.bitsTypeNone(255) -  indicates that  the clock source is not a BITS clock
                                The BITS clock type must be set when the clock source is a BITS clock.
                                "
                        ::= { hwClockInManageEntry 7 }


                -- 1.3.6.1.4.1.2011.6.25.1.1.1.8
                hwClkInQL OBJECT-TYPE
                        SYNTAX INTEGER
                                {
                                qlPRC(2),
                                qlSsuA(4),
                                qlSsuB(8),
                                qlSEC(11),
                                qlDNU(15),
                                qlCLEAR(255)
                                }
                        MAX-ACCESS read-create
                        STATUS current
                        DESCRIPTION
                                "Clock source quality level:
                                Options:
                                1. qlPRC(2)     -  indicates that primary reference clock
                                2. qlSsuA(4)    -  indicates that the clock signal comes from class I or class
                                                   V sub-clock prescribed on G.812 protocol
                                3. qlSsuB(8)    -  indicates that the clock signal comes from class VI sub-clock
                                                   prescribed on G.812 protocol
                                4. qlSEC(11)    -  indicates that the clock signal comes from SEC(SDH Equipment
                                                   Clock) prescribed on G.813 protocol
                                5. qlDNU(15)    -  indicates that the clock signal can't be used for synchronization
                                6. qlCLEAR(255) -  indicates that it is a wrong clock quality level
                                "
                        ::= { hwClockInManageEntry 8 }


                -- 1.3.6.1.4.1.2011.6.25.1.1.1.9
                hwClkInFaultRecord OBJECT-TYPE
                        SYNTAX INTEGER
                                {
                                noFaultRecord(1),
                                faultRecord(2)
                                }
                        MAX-ACCESS read-only
                        STATUS current
                        DESCRIPTION
                                "Clock source fault record.
                                Options:
                                1.noFaultRecord(1)  -  indicates that there is no fault record
                                2.faultRecord(2)    -  indicates that the clock source had a fault record
                                "
                        ::= { hwClockInManageEntry 9 }


                -- 1.3.6.1.4.1.2011.6.25.1.1.1.10
                hwClkInClearFaultRecord OBJECT-TYPE
                        SYNTAX INTEGER { clearFaultRecord(1) }
                        MAX-ACCESS read-create
                        STATUS current
                        DESCRIPTION
                                "Clear fault record of one clock source.
                                Options:
                                1.clearFaultRecord(1)  -Clears fault records
                                "
                        ::= { hwClockInManageEntry 10 }


                -- 1.3.6.1.4.1.2011.6.25.1.1.1.11
                hwClkLockState OBJECT-TYPE
                        SYNTAX INTEGER
                                {
                                locked(1),
                                unlocked(2)
                                }
                        MAX-ACCESS read-only
                        STATUS current
                        DESCRIPTION
                                "Clock lock state.
                                Options:
                                1.locked(1)   - indicates that the clock is locked
                                2.unlocked(2) - indicates that the clock is unlocked
                                "
                        ::= { hwClockInManageEntry 11 }
					
                -- 1.3.6.1.4.1.2011.6.25.1.1.1.12
                hwClkFreqDeviation OBJECT-TYPE
                        SYNTAX Integer32
	   MAX-ACCESS read-only
	   STATUS current
	   DESCRIPTION
                                "Clock source freq-deviation-value
                                The value is ten times of actual frequency deviation value
	           Unit: 0.1ppm
	           The invalid value is 0x7fffffff
                                "                        
                       ::= { hwClockInManageEntry 12 }


                -- 1.3.6.1.4.1.2011.6.25.1.2
                hwClockOutManageTable OBJECT-TYPE
                        SYNTAX SEQUENCE OF HwClockOutManageEntry
                        MAX-ACCESS not-accessible
                        STATUS current
                        DESCRIPTION
                                "Clock Out Management Table.
                                This table is used to configure and query the priority of the clock source,
                                and query the index of the currently-output clock source, and the working mode (the output mode)
                                of the current clock.The indexes of this table are hwClkInIndex and hwClkOutIndex.
                                hwClkInIndex comes from hwClockInManageTable and is the index of the input clock source.
                                hwClkOutIndex is the type of the output clock source.
                                The output clock source can be of the SDH, TDM, 8K, or 19M type.
                                "
                        ::= { hwClkMibObjects 2 }


                -- 1.3.6.1.4.1.2011.6.25.1.2.1
                hwClockOutManageEntry OBJECT-TYPE
                        SYNTAX HwClockOutManageEntry
                        MAX-ACCESS not-accessible
                        STATUS current
                        DESCRIPTION
                                "Clock Out Management Table.
                                This table is used to configure and query the priority of the clock source,
                                and query the index of the currently-output clock source, and the working mode (the output mode)
                                of the current clock.The indexes of this entry are hwClkInIndex and hwClkOutIndex.
                                hwClkInIndex comes from hwClockInManageTable and is the index of the input clock source.
                                hwClkOutIndex is the type of the output clock source.
                                The output clock source can be of the SDH, TDM, 8K, or 19M type.
                                "
                        INDEX { hwClkInIndex, hwClkOutIndex }
                        ::= { hwClockOutManageTable 1 }


                HwClockOutManageEntry ::=
                        SEQUENCE {
                                hwClkOutIndex
                                        Integer32,
                                hwClkOutType
                                        INTEGER,
                                hwClkOutPriority
                                        Integer32,
                                hwClkOutWorkMode
                                        INTEGER,
                                hwClkOutOperStatus
                                        TruthValue
                         }

                -- 1.3.6.1.4.1.2011.6.25.1.2.1.1
                hwClkOutIndex OBJECT-TYPE
                        SYNTAX Integer32 (1..7)
                        MAX-ACCESS not-accessible
                        STATUS current
                        DESCRIPTION
                                "Index of clock out table. Its meaning is the same as hwClkOutType.
                                The clock out index must be 8k in UA system and must be SDH or
                                TDM in MD/MA system during the setting of priority for a clock source.
                                Range: 1 - 7
                                "
                        ::= { hwClockOutManageEntry 1 }


                -- 1.3.6.1.4.1.2011.6.25.1.2.1.2
                hwClkOutType OBJECT-TYPE
                        SYNTAX INTEGER
                                {
                                sdh(1),
                                tdm(2),
                                system(3),
                                clk19M(4),
                                systemObsolete(5),
                                external(6),
                                external1(7)
                                }
                        MAX-ACCESS read-only
                        STATUS current
                        DESCRIPTION
                                "Clock out type.
                                Currently, there are seven types: SDH, TDM, system, 19 MHzm, systemObsolete, external and external1.
                                Options:
                                1.sdh(1)                -   indicates that output clock type is SDH
                                2.tdm(2)                -   indicates that output clock type is TDM
                                3.system(3)             -   indicates that output clock type is system
                                4.clk19M(4)             -   indicates that output clock type is clk19M
                                5.systemObsolete(5)     -   indicates that output clock type is systemObsolete
                                6.external(6)           -   indicates that output clock type is external
                                7.external1(7)          -   indicates that output clock type is external1
                                "
                        ::= { hwClockOutManageEntry 2 }


                -- 1.3.6.1.4.1.2011.6.25.1.2.1.3
                hwClkOutPriority OBJECT-TYPE
                        SYNTAX Integer32 (0..9 | 255)
                        MAX-ACCESS read-write
                        STATUS current
                        DESCRIPTION
                                "Clock source priority.
                                The priority ranges from 0 to 9 in a descending order. If the value is 255 in the get operation,
                                it indicates that the priority of the clock source isn't configured.
                                "
                        DEFVAL { 255 }
                        ::= { hwClockOutManageEntry 3 }


                -- 1.3.6.1.4.1.2011.6.25.1.2.1.4
                hwClkOutWorkMode OBJECT-TYPE
                        SYNTAX INTEGER
                                {
                                trace(1),
                                surge(2),
                                keep(3),
                                snap(4),
                                thirdsurge(5)
                                }
                        MAX-ACCESS read-only
                        STATUS current
                        DESCRIPTION
                                "Clock out working mode.
                                Options:
                                1.trace(1)       - indicates that the clock is working in tracing mode
                                2.surge(2)       - indicates that the clock is working in surge mode
                                3.keep(3)        - indicates that the clock is working in keeping mode
                                4.snap(4)        - indicates that the clock is working in snapping mode
                                5.thirdsurge(5)  - indicates that the clock is working in thirdsurge mode
                                "
                        ::= { hwClockOutManageEntry 4 }


                -- 1.3.6.1.4.1.2011.6.25.1.2.1.5
                hwClkOutOperStatus OBJECT-TYPE
                        SYNTAX TruthValue
                        MAX-ACCESS read-only
                        STATUS current
                        DESCRIPTION
                                "Clock source Out state. It indicates whether the clock source is
                                the output clock of the system: 1 indicates yes, and 2 indicates no.
                                       Options:
                                       1.yes(1) - indicates that the clock source is the output clock
                                       2.no(2)  - indicates that the clock source isn't the output clock
                                "
                        ::= { hwClockOutManageEntry 5 }


                -- 1.3.6.1.4.1.2011.6.25.1.3
                hwSystemClockManagePara OBJECT IDENTIFIER ::= { hwClkMibObjects 3 }


                -- 1.3.6.1.4.1.2011.6.25.1.3.1
                hwUASystemWorkMode OBJECT-TYPE
                        SYNTAX INTEGER
                                {
                                olt(1),
                                onu(2)
                                }
                        MAX-ACCESS read-write
                        STATUS current
                        DESCRIPTION
                                "UA work mode.
                                Options:
                                1.olt(1) - indicates that the UA system works as an OLT in VPRING
                                2.onu(2) - indicates that the UA system works as an ONU in VPRING
                                "
                        ::= { hwSystemClockManagePara 1 }


                -- 1.3.6.1.4.1.2011.6.25.1.3.2
                hw3rdClkSubBoardWorkMode OBJECT-TYPE
                        SYNTAX INTEGER
                                {
                                trace(1),
                                keep(2),
                                thirdsurge(3),
                                snap(4),
                                no3rdclksubboard(255)
                                }
                        MAX-ACCESS read-only
                        STATUS current
                        DESCRIPTION
                                "Working mode of 3rd sub-board clock.
                                Options:
                                1. trace(1)              - indicates that the clock is working in tracing mode
                                2. keep(2)               - indicates that the clock is working in keeping mode
                                3. thirdsurge(3)         - indicates that the clock is working in 3rd subboard crystal
                                4. snap(4)               - indicates clock is working in snap mode
                                5. no3rdclksubboard(255) - indicates that there is no 3rd subboard
                                "
                        ::= { hwSystemClockManagePara 2 }


                -- 1.3.6.1.4.1.2011.6.25.1.3.3
                hwSystemClockMode OBJECT-TYPE
                        SYNTAX INTEGER
                                {
                                clockClksubboard(1),
                                clockLocalboard(2)
                                }
                        MAX-ACCESS read-only
                        STATUS current
                        DESCRIPTION
                                "System clock mode.
                                Options:
                                1. clockClksubboard(1) - indicates the clock-subboard supply output clock
                                2. clockLocalboard(2)  - indicates the local-board supply output clock
                                "
                        ::= { hwSystemClockManagePara 3 }


                -- 1.3.6.1.4.1.2011.6.25.1.3.4
                hw3rdClkSubBoardInputStatus OBJECT-TYPE
                        SYNTAX INTEGER
                                {
                                none(1),
                                normal(2),
                                fault(3),
                                no3rdclksubboard(255)
                                }
                        MAX-ACCESS read-only
                        STATUS current
                        DESCRIPTION
                                "Clock-subboard clock input status.
                                Options:
                                1.none(1)               - indicates that the clock-subboard has no clock-signal input
                                2.normal(2)             - indicates that the clock-signal input status of the clock-subboard is normal
                                3.fault(3)              - indicates that the clock-signal input status of the clock-subboard is faulty
                                4.no3rdclksubboard(255) - indicates that there is no 3rd subboard
                                "
                        ::= { hwSystemClockManagePara 4 }


                -- 1.3.6.1.4.1.2011.6.25.1.3.5
                hw3rdClkSubBoardOutputStatus OBJECT-TYPE
                        SYNTAX INTEGER
                                {
                                normal(1),
                                fault(2),
                                no3rdclksubboard(255)
                                }
                        MAX-ACCESS read-only
                        STATUS current
                        DESCRIPTION
                                "Clock-subboard clock output status.
                                Options:
                                1.normal(1)             - indicates that the clock-subboard output status is normal
                                2.fault(2)              - indicates thaclock-subboard output status is faulty
                                3.no3rdclksubboard(255)        - indicates that there is no 3rd subboard
                                "
                        ::= { hwSystemClockManagePara 5 }


                -- 1.3.6.1.4.1.2011.6.25.1.3.6
                hwClockSelectionMode OBJECT-TYPE
                        SYNTAX INTEGER
                                {
                                qlDisable(1),
                                qlEnable(2)
                                }
                        MAX-ACCESS read-write
                        STATUS current
                        DESCRIPTION
                                "Clock selection mode.
                                Options:
                                1.qlDisable(1) - indicates that a clock source is selected based on its priority
                                2.qlEnable(2)  - indicates that a clock source is selected based on its quality
                                "
                        ::= { hwSystemClockManagePara 6 }


                -- 1.3.6.1.4.1.2011.6.25.1.3.8
                hwClkRevertiveMode OBJECT-TYPE
                        SYNTAX INTEGER
                                {
                                revertive(1),
                                nonRevertive(2)
                                }
                        MAX-ACCESS read-write
                        STATUS current
                        DESCRIPTION
                                "Clock revertive mode.
                                Options:
                                1.revertive(1)   - Though a clock source had fault record,
                                                   it still can be selected as the system clock
                                2.nonRevertive(2)- If one clock source had fault record, it can't
                                                   be selected as system clock
                                "
                        ::= { hwSystemClockManagePara 8 }


                -- 1.3.6.1.4.1.2011.6.25.1.3.9
                hw1588ClkType OBJECT-TYPE
                        SYNTAX INTEGER
                                {
                                oc(1),
                                bc(2),
                                tc(3),
                                tcoc(4),
                                tcbc(5),
                                tbc(6),
                                invalid(255)
                                }
                        MAX-ACCESS read-write
                        STATUS current
                        DESCRIPTION
                                "The 1588 clock type of device.
                                Options:
                                1. oc(1)        -  indicates that 1588 clock type is Ordinary Clock
                                2. bc(2)        -  indicates that 1588 clock type is Boundary Clock
                                3. tc(3)        -  indicates that 1588 clock type is Transparent Clock
                                4. tcoc(4)      -  indicates that 1588 clock type is combination of
                                                   transparent clock and ordinary clock
                                5. tcbc(5)      -  indicates that 1588 clock type is combination of
                                                   transparent clock and boundary Clock
                                6. tbc(6)       -  indicates that 1588 clock type is Telecommunication Boundary Clock 
                                7. invalid(255) -  indicates that the 1588 clock type is not available
                                "
                        ::= { hwSystemClockManagePara 9 }


                -- 1.3.6.1.4.1.2011.6.25.1.3.10
                hw1588ClkPEmode OBJECT-TYPE
                        SYNTAX INTEGER
                                {
                                p2p(1),
                                e2e(2),
                                invalid(255)
                                }
                        MAX-ACCESS read-write
                        STATUS obsolete
                        DESCRIPTION
                                "The 1588 clock PE-mode of device.
                                Options:
                                1. p2p(1)       -   indicates that the 1588 clock works in P2P mode
                                2. e2e(2)       -   indicates that the 1588 clock works at E2E mode
                                3. invalid(255) -   indicates that the 1588 clock PE-mode is not available
                                "
                        ::= { hwSystemClockManagePara 10 }


                -- 1.3.6.1.4.1.2011.6.25.1.3.11
                hw1588ClkID OBJECT-TYPE
                        SYNTAX OCTET STRING (SIZE (16))
                        MAX-ACCESS read-write
                        STATUS current
                        DESCRIPTION
                                "The 1588 clock identity of device.
                                The first 4 bytes must be 0x259e40 for an OLT.
                                The first 4 bytes must be 0x259e41 for a MxU."
                        ::= { hwSystemClockManagePara 11 }


                -- 1.3.6.1.4.1.2011.6.25.1.3.12
                hwExtClkoutputThresholdSsmQl OBJECT-TYPE
                        SYNTAX INTEGER
                                {
                                qlPRC(2),
                                qlSsuA(4),
                                qlSsuB(8),
                                qlSEC(11),
                                qlDNU(15)
                                }
                        MAX-ACCESS read-write
                        STATUS current
                        DESCRIPTION
                                "Clock source quality level.
                                Options:
                                1. qlPRC(2)   - primary reference clock
                                2. qlSsuA(4)  - indicates that the clock signal comes from class I or class V
                                                sub-clock stipulated in G.812 protocol
                                3. qlSsuB(8)  - indicates that the clock signal comes from class VI sub-clock
                                                stipulated in G.812 protocol
                                4. qlSEC(11)  - indicates that The clock signal comes from SEC(SDH Equipment Clock)
                                                stipulated in G.813 protocol
                                5. qlDNU(15)  - indicates that the clock signal can't be used for synchronization
                                "
                        ::= { hwSystemClockManagePara 12 }


                -- 1.3.6.1.4.1.2011.6.25.1.3.13
                hwExtClkOutputMode OBJECT-TYPE
                        SYNTAX INTEGER
                                {
				fixTrace(1),
				autoTrace(2),
				noTrace(3)
                                }
                        MAX-ACCESS read-write
                        STATUS current
                        DESCRIPTION
                                "The mode of external clock output.
                                Options:
				1.fixTrace(1) 		-Output system clock
				2.autoTrace(2)		-indicates that external clock output automatically
				3.noTrace(3)  		-indicates that that the external clock output is closed
                                "
                        ::= { hwSystemClockManagePara 13 }


                -- 1.3.6.1.4.1.2011.6.25.1.3.14
                hwClkWaitRestoreTime OBJECT-TYPE
                        SYNTAX Integer32 (0..12)
                        MAX-ACCESS read-write
                        STATUS current
                        DESCRIPTION
                                "If the clock state changes from failed to normal, wait
                                the specified time to join clock source selection.
                                Defined in G.781: wait restore time.
                                Unit:minute
                                Default value: 5 minutes
                                Range: 0 - 12
                                "
                        ::= { hwSystemClockManagePara 14 }


                -- 1.3.6.1.4.1.2011.6.25.1.3.15
                hwClkHoldoffTime OBJECT-TYPE
                        SYNTAX Integer32 (0..1)
                        MAX-ACCESS read-write
                        STATUS current
                        DESCRIPTION
                                "If the clock state changes from normal to failed, wait the specified time to mark the failed state.
                                Unit:second.
                                Default value: 0 second
                                Range: 0 - 1
                                0 - 0 second
                                1 - 1 second
                                "
                        ::= { hwSystemClockManagePara 15 }


                -- 1.3.6.1.4.1.2011.6.25.1.3.16
                hwQlOutputUpperLimit OBJECT-TYPE
                        SYNTAX INTEGER
                                {
                                qlPRC(2),
                                qlSsuA(4),
                                qlSsuB(8),
                                qlSEC(11),
                                qlDNU(15)
                                }
                        MAX-ACCESS read-write
                        STATUS current
                        DESCRIPTION
                                "System output clock signal with a lower quality than the limited value.
                                Options:
                                1.qlPRC(2)  - indicates that the quality of the system output clock signal is lower than qlPRC
                                2.qlSsuA(4) - indicates that the quality of the system output clock signal is lower than qlSsuA
                                3.qlSsuB(8) - indicates that the quality of the system output clock signal is lower than qlSsuB
                                4.qlSEC(11) - indicates that the quality of the system output clock signal is lower than qlSEC
                                5.qlDNU(15) - indicates that the quality of the system output clock signal is lower than qlDNU
                                "
                        ::= { hwSystemClockManagePara 16 }


                -- 1.3.6.1.4.1.2011.6.25.1.3.17
                hwPTPEnable OBJECT-TYPE
                        SYNTAX INTEGER
                                {
                                enable(1),
                                disable(2)
                                }
                        MAX-ACCESS read-write
                        STATUS current
                        DESCRIPTION
                                "Enable or disable the 1588 function.
                                Options:
                                1.enable(1)   - Enable the 1588 function
                                2.disable(2)  - Disable the 1588 function
                                Default: disable(2)
                                "
                        ::= { hwSystemClockManagePara 17 }


                -- 1.3.6.1.4.1.2011.6.25.1.3.18
                hwExtClkOutputBitsType OBJECT-TYPE
                        SYNTAX INTEGER
                                {
                                bitsType2MHz(1),
                                bitsType2Mbps(2),
				bitsType1544bps(3),
				bitsType1ppsInput(4),
				bitsType1ppsOutput(5)
                                }
                        MAX-ACCESS read-write
                        STATUS current
                        DESCRIPTION
                                "Get or set output signal of GPIO board. Default to bitsType2Mbps(2).
                                Options:
                                1. bitsType2MHz (1)        - indicates that the output signal of the GPIO board is bitsType2MHz
                                2. bitsType2Mbps(2)        - indicates that the output signal of the GPIO board is bitsType2Mbps
                                3. bitsType1544bps(3)        - indicates that the output signal of the GPIO board is bitsType1.544Mbps
				4. bitsType1ppsInput(4)         - indicates that the input signal of the GPIO board is bitsType1ppsInput
				5. bitsType1ppsOutput(5)        - indicates that the output signal of the GPIO board is bitsType1ppsOutput  
                                "
                        ::= { hwSystemClockManagePara 18 }


                -- 1.3.6.1.4.1.2011.6.25.1.3.19
                hwQlInputLowerLimit OBJECT-TYPE
                        SYNTAX INTEGER
                                {
                                qlPRC(2),
                                qlSsuA(4),
                                qlSsuB(8),
                                qlSEC(11)
                                }
                        MAX-ACCESS read-write
                        STATUS current
                        DESCRIPTION
                                "Clock source quality level:
                                Options:
                                1. qlPRC(2)     -  indicates that primary reference clock
                                2. qlSsuA(4)    -  indicates that the clock signal comes from class I or class
                                                   V sub-clock prescribed on G.812 protocol
                                3. qlSsuB(8)    -  indicates that the clock signal comes from class VI sub-clock
                                                   prescribed on G.812 protocol
                                4. qlSEC(11)    -  indicates that the clock signal comes from SEC(SDH Equipment
                                                   Clock) prescribed on G.813 protocol
                                "
                        ::= { hwSystemClockManagePara 19 }


                -- 1.3.6.1.4.1.2011.6.25.1.3.20
                hwPtpDomain OBJECT-TYPE
                        SYNTAX Integer32 (0..255)
                        MAX-ACCESS read-write
                        STATUS current
                        DESCRIPTION
                                "PTP domain value.
                                BC:	
                                    Range: 0-255
                                    Default: 0
                                T-BC:
                                    Range: 24-43
                                    Default: 24
                                "
                        ::= { hwSystemClockManagePara 20 }


                -- 1.3.6.1.4.1.2011.6.25.1.3.21
                hwPtpBMCEnable OBJECT-TYPE
                        SYNTAX INTEGER
                                {
                                enable(1),
                                disable(2)
                                }
                        MAX-ACCESS read-write
                        STATUS current
                        DESCRIPTION
                                "PTP BMC switch.
                                BC: 
                                    Options:
                                    1. enable(1)  - indicates that ptp BMC is enabled
                                    2. disable(2) - indicates that ptp BMC is disabled
                                    Default: disable(2)
				
                                T-BC:
                                    enable(1) - indicates that ptp BMC is enabled					
                                "
                        ::= { hwSystemClockManagePara 21 }


                -- 1.3.6.1.4.1.2011.6.25.1.3.22
                hwPtpLockState OBJECT-TYPE
                        SYNTAX INTEGER
                                {
                                locked(1),
                                unlocked(2)
                                }
                        MAX-ACCESS read-only
                        STATUS current
                        DESCRIPTION
                                "PTP lock state.
                                Options:
                                1. locked(1)   -  indicates that the clock is locked
                                2. unlocked(2) -  indicates that the clock is unlocked
                                "
                        ::= { hwSystemClockManagePara 22 }


                -- 1.3.6.1.4.1.2011.6.25.1.3.23
                hwPtpFreqLockStatus OBJECT-TYPE
                        SYNTAX INTEGER
                                {
                                locked(1),
                                unlocked(2)
                                }
                        MAX-ACCESS read-only
                        STATUS current
                        DESCRIPTION
                                "PTP frequency lock state.
                                Options:
                                1. locked(1)   -  indicates that the frequency is locked
                                2. unlocked(2) -  indicates that the frequency is unlocked
                                "
                        ::= { hwSystemClockManagePara 23 }


                -- 1.3.6.1.4.1.2011.6.25.1.3.24
                hwPtpTimeScale OBJECT-TYPE
                        SYNTAX INTEGER
                                {
                                ptp(1),
                                arb(2)
                                }
                        MAX-ACCESS read-only
                        STATUS current
                        DESCRIPTION
                                "The time scale of the grandmaster clock.
                                "
                        ::= { hwSystemClockManagePara 24 }


                -- 1.3.6.1.4.1.2011.6.25.1.3.25
                hwPtpFrequencyTraceable OBJECT-TYPE
                        SYNTAX TruthValue
                        MAX-ACCESS read-only
                        STATUS current
                        DESCRIPTION
                                "The value is true if the frequency determinning the timescale is traceable to a primary reference, otherwise the value is false.
                                "
                        ::= { hwSystemClockManagePara 25 }


                -- 1.3.6.1.4.1.2011.6.25.1.3.26
                hwPtpTimeTraceable OBJECT-TYPE
                        SYNTAX TruthValue
                        MAX-ACCESS read-only
                        STATUS current
                        DESCRIPTION
                                "The value is ture if the time is traceable to a primary reference. otherwise the value is false.
                                "
                        ::= { hwSystemClockManagePara 26 }


                -- 1.3.6.1.4.1.2011.6.25.1.3.27
                hwPtpGMClockID OBJECT-TYPE
                        SYNTAX OCTET STRING (SIZE (16))
                        MAX-ACCESS read-only
                        STATUS current
                        DESCRIPTION
                                "Grand master clock ID.
                                "
                        ::= { hwSystemClockManagePara 27 }


                -- 1.3.6.1.4.1.2011.6.25.1.3.28
                hwPtpGrandMasterClockPriority1 OBJECT-TYPE
                        SYNTAX Integer32 (0..255)
                        MAX-ACCESS read-only
                        STATUS current
                        DESCRIPTION
                                "Grand master clock priority1.
                                "
                        ::= { hwSystemClockManagePara 28 }


                -- 1.3.6.1.4.1.2011.6.25.1.3.29
                hwPtpGrandMasterClockPriority2 OBJECT-TYPE
                        SYNTAX Integer32 (0..255)
                        MAX-ACCESS read-only
                        STATUS current
                        DESCRIPTION
                                "Grand master clock priority2.
                                "
                        ::= { hwSystemClockManagePara 29 }


                -- 1.3.6.1.4.1.2011.6.25.1.3.30
                hwPtpGrandMasterClockAccuracy OBJECT-TYPE
                        SYNTAX Integer32 (0..255)
                        MAX-ACCESS read-only
                        STATUS current
                        DESCRIPTION
                                "Grand master clock accuracy.
                                "
                        ::= { hwSystemClockManagePara 30 }


                -- 1.3.6.1.4.1.2011.6.25.1.3.31
                hwPtpGrandMasterClockClass OBJECT-TYPE
                        SYNTAX Integer32 (0..255)
                        MAX-ACCESS read-only
                        STATUS current
                        DESCRIPTION
                                "Grand master clock class.
                                "
                        ::= { hwSystemClockManagePara 31 }


                -- 1.3.6.1.4.1.2011.6.25.1.3.32
                hwPtpGrandMasterClockTimeSource OBJECT-TYPE
                        SYNTAX INTEGER
                                {
                                atomicclock(16),
                                gps(32),
                                terrestrialradio(48),
                                ptp(64),
                                ntp(80),
                                handset(96),
                                other(144),
                                internaloscillator(160)
                                }
                        MAX-ACCESS read-only
                        STATUS current
                        DESCRIPTION
                                "Indicates the source of time used by the grandmaster clock.
                                "
                        ::= { hwSystemClockManagePara 32 }


                -- 1.3.6.1.4.1.2011.6.25.1.3.33
                hwPtpPhyPhaseSubCur OBJECT-TYPE
                        SYNTAX Integer32
                        MAX-ACCESS read-only
                        STATUS current
                        DESCRIPTION
                                "PTP physics phase current warp.
                                "
                        ::= { hwSystemClockManagePara 33 }


                -- 1.3.6.1.4.1.2011.6.25.1.3.34
                hwPtpPhyPhaseSubMin OBJECT-TYPE
                        SYNTAX Integer32
                        MAX-ACCESS read-only
                        STATUS current
                        DESCRIPTION
                                "PTP physics phase min warp.
                                "
                        ::= { hwSystemClockManagePara 34 }


                -- 1.3.6.1.4.1.2011.6.25.1.3.35
                hwPtpPhyPhaseSubMax OBJECT-TYPE
                        SYNTAX Integer32
                        MAX-ACCESS read-only
                        STATUS current
                        DESCRIPTION
                                "PTP physics phase max warp.
                                "
                        ::= { hwSystemClockManagePara 35 }


                -- 1.3.6.1.4.1.2011.6.25.1.3.36
                hwPtpPhyPhaseSubMean OBJECT-TYPE
                        SYNTAX Integer32
                        MAX-ACCESS read-only
                        STATUS current
                        DESCRIPTION
                                "PTP physics phase mean warp.
                                "
                        ::= { hwSystemClockManagePara 36 }


                -- 1.3.6.1.4.1.2011.6.25.1.3.37
                hwPtpTimeSyncOffsetCur OBJECT-TYPE
                        SYNTAX Integer32
                        MAX-ACCESS read-only
                        STATUS current
                        DESCRIPTION
                                "PTP current time offset.
                                "
                        ::= { hwSystemClockManagePara 37 }


                -- 1.3.6.1.4.1.2011.6.25.1.3.38
                hwPtpTimeSyncOffsetMin OBJECT-TYPE
                        SYNTAX Integer32
                        MAX-ACCESS read-only
                        STATUS current
                        DESCRIPTION
                                "PTP min time offset.
                                "
                        ::= { hwSystemClockManagePara 38 }


                -- 1.3.6.1.4.1.2011.6.25.1.3.39
                hwPtpTimeSyncOffsetMax OBJECT-TYPE
                        SYNTAX Integer32
                        MAX-ACCESS read-only
                        STATUS current
                        DESCRIPTION
                                "PTP max time offset.
                                "
                        ::= { hwSystemClockManagePara 39 }


                -- 1.3.6.1.4.1.2011.6.25.1.3.40
                hwPtpTimeSyncOffsetMean OBJECT-TYPE
                        SYNTAX Integer32
                        MAX-ACCESS read-only
                        STATUS current
                        DESCRIPTION
                                "PTP average time offset.
                                "
                        ::= { hwSystemClockManagePara 40 }


                -- 1.3.6.1.4.1.2011.6.25.1.3.41
                hwPtpTimeMeanpathdelayCur OBJECT-TYPE
                        SYNTAX Integer32
                        MAX-ACCESS read-only
                        STATUS current
                        DESCRIPTION
                                "PTP current path delay.
                                "
                        ::= { hwSystemClockManagePara 41 }


                -- 1.3.6.1.4.1.2011.6.25.1.3.42
                hwPtpTimeMeanpathdelayMin OBJECT-TYPE
                        SYNTAX Integer32
                        MAX-ACCESS read-only
                        STATUS current
                        DESCRIPTION
                                "PTP min path delay.
                                "
                        ::= { hwSystemClockManagePara 42 }


                -- 1.3.6.1.4.1.2011.6.25.1.3.43
                hwPtpTimeMeanpathdelayMax OBJECT-TYPE
                        SYNTAX Integer32
                        MAX-ACCESS read-only
                        STATUS current
                        DESCRIPTION
                                "PTP max path delay.
                                "
                        ::= { hwSystemClockManagePara 43 }


                -- 1.3.6.1.4.1.2011.6.25.1.3.44
                hwPtpTimeMeanpathdelayMean OBJECT-TYPE
                        SYNTAX Integer32
                        MAX-ACCESS read-only
                        STATUS current
                        DESCRIPTION
                                "PTP average path delay.
                                "
                        ::= { hwSystemClockManagePara 44 }


                -- 1.3.6.1.4.1.2011.6.25.1.3.45
                hwPtpDlyMeasureEnable OBJECT-TYPE
                        SYNTAX INTEGER
                                {
                                enable(1),
                                disable(2)
                                }
                        MAX-ACCESS read-write
                        STATUS current
                        DESCRIPTION
                                "PTP asymmetry measure switch.
                                Options:
                                1. enable(1)  - indicates that ptp asymmetry measure is enabled
                                2. disable(2) - indicates that ptp asymmetry measure is disabled
                                "
                        ::= { hwSystemClockManagePara 45 }


                -- 1.3.6.1.4.1.2011.6.25.1.3.46
                hwPtpParentClockID OBJECT-TYPE
                        SYNTAX OCTET STRING (SIZE (16))
                        MAX-ACCESS read-only
                        STATUS current
                        DESCRIPTION
                                "PTP parent clockID.
                                "
                        ::= { hwSystemClockManagePara 46 }


                -- 1.3.6.1.4.1.2011.6.25.1.3.47
                hwPtpParentPortNumber OBJECT-TYPE
                        SYNTAX Integer32
                        MAX-ACCESS read-only
                        STATUS current
                        DESCRIPTION
                                "PTP parent portnumber."
                        ::= { hwSystemClockManagePara 47 }

                -- 1.3.6.1.4.1.2011.6.25.1.3.48
                hwExtClkOutputState OBJECT-TYPE
                        SYNTAX INTEGER
                            {
                            on(1),
                            off(2)
                            }
                        MAX-ACCESS read-only
                        STATUS current
                        DESCRIPTION
                                "External clock output state.
                                Options:
                                1. on(1) - indicates that the output of external clock is opened 
                                2. off(2) - indicates that the output of external clock is closed
                                "
                        ::= { hwSystemClockManagePara 48 }

                -- 1.3.6.1.4.1.2011.6.25.1.3.49
                hwPtpLocalSourceLocalPriority OBJECT-TYPE
                        SYNTAX Integer32
                        MAX-ACCESS read-write
                        STATUS current
                        DESCRIPTION
                                "In T-BC mode, the local priority is configured to calculate the optimum master clock. 
                                The smaller the value, the higher the priority. 
                                Range: 1-255
                                Default: 128
								
                                This attribute is invalid in BC mode.
                                "
                        ::= { hwSystemClockManagePara 49 }
						
                -- 1.3.6.1.4.1.2011.6.25.1.3.50
                hwPtpLocalSourcePriority2 OBJECT-TYPE
                        SYNTAX Integer32
                        MAX-ACCESS read-write
                        STATUS current
                        DESCRIPTION
                                "In T-BC mode, the priority2 is configured to calculate the optimum master clock. 
                                The smaller the value, the higher the priority. 
                                This attribute is invalid in BC mode.
                                Range: 0-255
                                Default: 128
                                "
                        ::= { hwSystemClockManagePara 50 }
				
                -- 1.3.6.1.4.1.2011.6.25.1.4
                hwClockOutPortManageTable OBJECT-TYPE
                        SYNTAX SEQUENCE OF HwClockOutPortManageEntry
                        MAX-ACCESS not-accessible
                        STATUS current
                        DESCRIPTION
                                "Clock output port management table.
                                This table is used to enable or disable the output
                                port and query the status of the output port. The index of this table is
                                hwClkOutputPostion, indicating the ifIndex of physical position of the clock source.
                                "
                        ::= { hwClkMibObjects 4 }


                -- 1.3.6.1.4.1.2011.6.25.1.4.1
                hwClockOutPortManageEntry OBJECT-TYPE
                        SYNTAX HwClockOutPortManageEntry
                        MAX-ACCESS not-accessible
                        STATUS current
                        DESCRIPTION
                                "Clock output port management table.
                                This table is used to enable or disable the output
                                port and query the status of the output port. The index of this entry is
                                hwClkOutputPostion, indicating the ifIndex of physical position of the clock source.
                                "
                        INDEX { hwClkOutputPostion }
                        ::= { hwClockOutPortManageTable 1 }


                HwClockOutPortManageEntry ::=
                        SEQUENCE {
                                hwClkOutputPostion
                                        Integer32,
                                hwClkOutPortEnable
                                        INTEGER,
                                hwSsmQlOutPortEnable
                                        INTEGER
                                 }

                -- 1.3.6.1.4.1.2011.6.25.1.4.1.1
                hwClkOutputPostion OBJECT-TYPE
                        SYNTAX Integer32
                        MAX-ACCESS read-create
                        STATUS current
                        DESCRIPTION
                                "The index of physical position of the clock source.
                                The highest byte is useless.
                                The second byte describes the frame ID.
                                The third byte describes the slot ID.
                                The lowest byte describes the port ID.
                                The following shows how to use parameter during the get or set operation:
                                0x 00, FF,00,00  Frame ID;     0~255
                                0x 00, 00,FF,00  Slot  ID;     0~255
                                0x 00, 00,00,FF  Port  ID;     0~255
                                "
                        ::= { hwClockOutPortManageEntry 1 }


                -- 1.3.6.1.4.1.2011.6.25.1.4.1.2
                hwClkOutPortEnable OBJECT-TYPE
                        SYNTAX INTEGER
                                {
                                enable(0),
                                disable(1)
                                }
                        MAX-ACCESS read-create
                        STATUS current
                        DESCRIPTION
                                "Clock output port switch.
                                Options:
                                1. enable(0)  - indicates that clock source output of this BITS port is enabled
                                2. disable(1) - indicates that clock source output of this BITS port is disabled
                                "
                        ::= { hwClockOutPortManageEntry 2 }


                -- 1.3.6.1.4.1.2011.6.25.1.4.1.3
                hwSsmQlOutPortEnable OBJECT-TYPE
                        SYNTAX INTEGER
                                {
                                enable(1),
                                disable(2)
                                }
                        MAX-ACCESS read-create
                        STATUS current
                        DESCRIPTION
                                "SSM QL output mode.
                                Options:
                                1.enable(1)  - indicates that SSM QL output of the port is enabled
                                2.disable(2) - indicates that SSM QL output of the port is disabled
                                "
                        ::= { hwClockOutPortManageEntry 3 }


                -- 1.3.6.1.4.1.2011.6.25.1.5
                hwClock1588ManageTable OBJECT-TYPE
                        SYNTAX SEQUENCE OF HwClock1588ManageEntry
                        MAX-ACCESS not-accessible
                        STATUS current
                        DESCRIPTION
                                "Clock 1588 source management table. This table is used to manage
                                the 1588 clock source.
                                The index of this table is hw1588ClkInIndex, which is the ID of the 1588 clock source.
                                "
                        ::= { hwClkMibObjects 5 }


                -- 1.3.6.1.4.1.2011.6.25.1.5.1
                hwClock1588ManageEntry OBJECT-TYPE
                        SYNTAX HwClock1588ManageEntry
                        MAX-ACCESS not-accessible
                        STATUS current
                        DESCRIPTION
                                "Clock 1588 source management table. This table is used to manage
                                the 1588 clock source.
                                The index of this entry is hw1588ClkInIndex, which is the ID of the 1588 clock source.
                                "
                        INDEX { hw1588ClkInIndex }
                        ::= { hwClock1588ManageTable 1 }


                HwClock1588ManageEntry ::=
                        SEQUENCE {
                                hw1588ClkInIndex
                                        Integer32,
                                hw1588ClkInPostion
                                        Integer32,
                                hw1588ClkPriority
                                        Integer32,
                                hw1588ClkInOperStatus
                                        INTEGER,
                                hw1588ClkInRowStatus
                                        RowStatus,
                                hw1588ClkReqSendTimeInterval
                                        Integer32,
                                hw1588ClkDomainNumber
                                        Integer32,
                                hw1588ClkPtpPEMode
                                        INTEGER,
                                hw1588ClkPtpMsgFormat
                                        INTEGER,
                                hw1588ClkPtpLineWarpMode
                                        INTEGER,
                                hw1588ClkPtpLineWarpDirect
                                        INTEGER,
                                hw1588ClkPtpLineWarpValue
                                        Integer32,
                                hw1588ClkPtpTimeSourceID
                                        OCTET STRING,
                                hw1588ClkPtpVlan
                                        Integer32,
                                hw1588ClkPtpInfoMode
                                        INTEGER,
                                hw1588ClkPtpAnnounceTimeout
                                        Integer32,
                                hw1588ClkGMClockID
                                        OCTET STRING,
                                hw1588ClkAnnounceSendTimeInterval
                                        Integer32,
                                hw1588ClkSyncSendTimeInterval
                                        Integer32,
                                hw1588ClkPtpLockState
                                        INTEGER,
                                hw1588ClkInWorkMode
                                        INTEGER,
                                hw1588ClkInSelectStatus
                                        INTEGER
                         }

                -- 1.3.6.1.4.1.2011.6.25.1.5.1.1
                hw1588ClkInIndex OBJECT-TYPE
                        SYNTAX Integer32 (0..9)
			MAX-ACCESS accessible-for-notify
                        STATUS current
                        DESCRIPTION
                                "Clock 1588 source index.
                                Range: 0-9"
                        ::= { hwClock1588ManageEntry 1 }


                -- 1.3.6.1.4.1.2011.6.25.1.5.1.2
                hw1588ClkInPostion OBJECT-TYPE
                        SYNTAX Integer32
                        MAX-ACCESS read-create
                        STATUS current
                        DESCRIPTION
                                "The index of physical position of clock 1588 source.
                                The highest byte is useless.
                                The second byte describes the frame ID.
                                The third byte describes the slot ID.
                                The lowest byte describes the port ID.
                                The following shows how to use parameters during the get or set operation:
				0x00,FF,00,00  Frame ID;     0-255
				0x00,00,FF,00  Slot  ID;     0-255
				0x00,00,00,FF  Port  ID;     0-255
				"
                        ::= { hwClock1588ManageEntry 2 }


                -- 1.3.6.1.4.1.2011.6.25.1.5.1.3
                hw1588ClkPriority OBJECT-TYPE
                        SYNTAX Integer32 (0..9 | 255)
                        MAX-ACCESS read-create
                        STATUS current
                        DESCRIPTION
                                "Clock 1588 source priority.
                                The priority ranges from 0 to 9 in a descending order.If the value is 255 in the get operation,
                                it indicates that the priority of the ptp source isn't configured.
                                "
                        ::= { hwClock1588ManageEntry 3 }


                -- 1.3.6.1.4.1.2011.6.25.1.5.1.4
                hw1588ClkInOperStatus OBJECT-TYPE
                        SYNTAX INTEGER
                                {
                                none(1),
                                normal(2),
                                failure(3)
                                }
                        MAX-ACCESS read-only
                        STATUS current
                        DESCRIPTION
                                "Clock 1588 source status:
                                Options:
                                1.none(1)   - indicates that the clock source index is not configured
                                2.normal(2) - indicates that the status of clock source is normal
                                3.failure(3)- indicates that the status of clock source is faulty
                                "
                        ::= { hwClock1588ManageEntry 4 }


                -- 1.3.6.1.4.1.2011.6.25.1.5.1.5
                hw1588ClkInRowStatus OBJECT-TYPE
                        SYNTAX RowStatus
                        MAX-ACCESS read-create
                        STATUS current
                        DESCRIPTION
                                "Clock 1588 source operation includes adding and deleting clock 1588 source.
                                If the value is set to 4, it indicates that a clock 1588 source is created.
                                If the value is set to 6, it indicates that an existing clock source is deleted.
                                "
                        ::= { hwClock1588ManageEntry 5 }


                -- 1.3.6.1.4.1.2011.6.25.1.5.1.6
                hw1588ClkReqSendTimeInterval OBJECT-TYPE
                        SYNTAX Integer32 (1..21)
                        MAX-ACCESS read-create
                        STATUS obsolete
                        DESCRIPTION
                                "1588 Req send time interval.
                                Options:
                                1.1/1024s( 1)  - indicates that the time interval is 1/1024s
                                2.1/512s( 2)   - indicates that the time interval is 1/512s
                                3.1/256s( 3)   - indicates that the time interval is 1/256s
                                4.1/128s( 4)   - indicates that the time interval is 1/128s
                                5.1/64s( 5)    - indicates that the time interval is 1/64s
                                6.1/32s( 6)    - indicates that the time interval is 1/32s
                                7.1/16s( 7)    - indicates that the time interval is 1/16s
                                8.1/8s( 8)     - indicates that the time interval is 1/8s
                                9.1/4s( 9)     - indicates that the time interval is 1/4s
                                10.1/2s(10)    - indicates that the time interval is 1/2s
                                11.1s(11)      - indicates that the time interval is 1s
                                12.2s(12)      - indicates that the time interval is 2s
                                13.4s(13)      - indicates that the time interval is 4s
                                14.8s(14)      - indicates that the time interval is 8s
                                15.16s(15)     - indicates that the time interval is 16s
                                16.32s(16)     - indicates that the time interval is 32s
                                17.64s(17)     - indicates that the time interval is 64s
                                18.128s(18)    - indicates that the time interval is 128s
                                19.256s(19)    - indicates that the time interval is 256s
                                20.512s(20)    - indicates that the time interval is 512s
                                21.1024s(21)   - indicates that the time interval is 1024s
                                "
                        ::= { hwClock1588ManageEntry 6 }


                -- 1.3.6.1.4.1.2011.6.25.1.5.1.7
                hw1588ClkDomainNumber OBJECT-TYPE
                        SYNTAX Integer32 (0..255)
                        MAX-ACCESS read-create
                        STATUS obsolete
                        DESCRIPTION
                                "1588 clock domain number:
                                Range: 0-255
                                Default: 0
                                "
                        ::= { hwClock1588ManageEntry 7 }


                -- 1.3.6.1.4.1.2011.6.25.1.5.1.8
                hw1588ClkPtpPEMode OBJECT-TYPE
                        SYNTAX INTEGER
                                {
                                p2p(1),
                                e2e(2)
                                }
                        MAX-ACCESS read-create
                        STATUS obsolete
                        DESCRIPTION
                                "PTP MODE,default value is e2e(2).
                                Options:
                                1. p2p(1) - indicates that the 1588 clock Ptp Pe Mode is p2p
                                2. e2e(2) - indicates that the 1588 clock Ptp Pe Mode is e2e
                                "
                        ::= { hwClock1588ManageEntry 8 }


                -- 1.3.6.1.4.1.2011.6.25.1.5.1.9
                hw1588ClkPtpMsgFormat OBJECT-TYPE
                        SYNTAX INTEGER
                                {
                                ptpeth(1),
                                ptpip(2)
                                }
                        MAX-ACCESS read-create
                        STATUS obsolete
                        DESCRIPTION
                                "PTP message encapsulation format,the default value is PTPETH(1).
                                Options:
                                1. ptpeth(1) - indicates that the PTP message is encapsulated into an Ethernet packet
                                2. ptpip(2)  - indicates that the PTP message is encapsulated into an IP packet
                                "
                        ::= { hwClock1588ManageEntry 9 }


                -- 1.3.6.1.4.1.2011.6.25.1.5.1.10
                hw1588ClkPtpLineWarpMode OBJECT-TYPE
                        SYNTAX INTEGER
                                {
                                length(1),
                                time(2)
                                }
                        MAX-ACCESS read-create
                        STATUS obsolete
                        DESCRIPTION
                                "PTP line warp mode, the default value is length(1).
                                Options:
                                1. length(1) - indicates that the warp is represented by length
                                2. time(2)   - indicates that the warp is represented by time
                                "
                        ::= { hwClock1588ManageEntry 10 }


                -- 1.3.6.1.4.1.2011.6.25.1.5.1.11
                hw1588ClkPtpLineWarpDirect OBJECT-TYPE
                        SYNTAX INTEGER
                                {
                                positive(1),
                                negative(2)
                                }
                        MAX-ACCESS read-create
                        STATUS obsolete
                        DESCRIPTION
                                "PTP line warp direct, the default value is positive(1).
                                Options:
                                1. positive(1)  - indicates that the warp is in the positive direction
                                2. negative(2)  - indicates that the warp is in the negative direction
                                "
                        ::= { hwClock1588ManageEntry 11 }


                -- 1.3.6.1.4.1.2011.6.25.1.5.1.12
                hw1588ClkPtpLineWarpValue OBJECT-TYPE
                        SYNTAX Integer32 (0..65529)
                        MAX-ACCESS read-create
                        STATUS obsolete
                        DESCRIPTION
                                "PTP Line Warp Value:
                                IF warp mode is length(1), the range is 0~14562m.
                                If warp mode is time(2), the range is 0~65529 ns.
                                "
                        ::= { hwClock1588ManageEntry 12 }


                -- 1.3.6.1.4.1.2011.6.25.1.5.1.13
                hw1588ClkPtpTimeSourceID OBJECT-TYPE
                        SYNTAX OCTET STRING (SIZE (20))
                        MAX-ACCESS read-create
                        STATUS obsolete
                        DESCRIPTION
                                "PTP source port ID:
                                It is 10 bytes in length and the default value is 0.
                                "
                        ::= { hwClock1588ManageEntry 13 }


                -- 1.3.6.1.4.1.2011.6.25.1.5.1.14
                hw1588ClkPtpVlan OBJECT-TYPE
                        SYNTAX Integer32 (0..4094)
                        MAX-ACCESS read-create
                        STATUS obsolete
                        DESCRIPTION
                                "PTP Vlan:
                                Range: 0-4094.
                                       Default: 1.
                                "
                        ::= { hwClock1588ManageEntry 14 }


                -- 1.3.6.1.4.1.2011.6.25.1.5.1.15
                hw1588ClkPtpInfoMode OBJECT-TYPE
                        SYNTAX INTEGER
                                {
                                muticast(1),
                                unicast(2)
                                }
                        MAX-ACCESS read-create
                        STATUS obsolete
                        DESCRIPTION
                                "PTP info mode,default value is multicast(1).
                                Options:
                                1. multicast(1)   - indicates that the PTP info mode is multicast.
                                2. unicast(2)         - indicates that the PTP info mode is unicast.
                                "
                        ::= { hwClock1588ManageEntry 15 }


                -- 1.3.6.1.4.1.2011.6.25.1.5.1.16
                hw1588ClkPtpAnnounceTimeout OBJECT-TYPE
                        SYNTAX Integer32 (2..1048576)
                        MAX-ACCESS read-create
                        STATUS obsolete
                        DESCRIPTION
                                "Announce timeout:
                                Range: 1-1048576 ms
                                Range: 1 - 1048576
                                       Default: 128 ms
                                "
                        ::= { hwClock1588ManageEntry 16 }


                -- 1.3.6.1.4.1.2011.6.25.1.5.1.17
                hw1588ClkGMClockID OBJECT-TYPE
                        SYNTAX OCTET STRING (SIZE (16))
                        MAX-ACCESS read-only
                        STATUS obsolete
                        DESCRIPTION
                                "Grandmaster clock ID."
                        ::= { hwClock1588ManageEntry 17 }


                -- 1.3.6.1.4.1.2011.6.25.1.5.1.18
                hw1588ClkAnnounceSendTimeInterval OBJECT-TYPE
                        SYNTAX Integer32 (1..21)
                        MAX-ACCESS read-create
                        STATUS obsolete
                        DESCRIPTION
                                "1588 announce send time interval,the default value is  1/8s(8).
                                Options:
                                1. 1/1024s(1)  - indicates that the time interval is 1/1024s
                                2. 1/512s (2)  - indicates that the time interval is 1/512s
                                3. 1/256s (3)  - indicates that the time interval is 1/256s
                                4. 1/128s (4)  - indicates that the time interval is 1/128s
                                5. 1/64s  (5)  - indicates that the time interval is 1/64s
                                6. 1/32s  (6)  - indicates that the time interval is 1/32s
                                7. 1/16s  (7)  - indicates that the time interval is 1/16s
                                8. 1/8s   (8)  - indicates that the time interval is 1/8s
                                9. 1/4s   (9)  - indicates that the time interval is 1/4s
                                10. 1/2s  (10) - indicates that the time interval is  1/2s
                                11. 1s    (11) - indicates that the time interval is  1s
                                12. 2s    (12) - indicates that the time interval is  2s
                                13. 4s    (13) - indicates that the time interval is  4s
                                14. 8s    (14) - indicates that the time interval is  8s
                                15. 16s   (15) - indicates that the time interval is  16s
                                16. 32s   (16) - indicates that the time interval is  32s
                                17. 64s   (17) - indicates that the time interval is  64s
                                18. 128s  (18) - indicates that the time interval is  128s
                                19. 256s  (19) - indicates that the time interval is  256s
                                20. 512s  (20) - indicates that the time interval is  512s
                                21. 1024s (21) - indicates that the time interval is  1024s
                                "
                        ::= { hwClock1588ManageEntry 18 }


                -- 1.3.6.1.4.1.2011.6.25.1.5.1.19
                hw1588ClkSyncSendTimeInterval OBJECT-TYPE
                        SYNTAX Integer32 (1..21)
                        MAX-ACCESS read-create
                        STATUS obsolete
                        DESCRIPTION
                                "1588 sync send time interval,the default value is 1/8s(8).
                                Options:
                                1. 1/1024s(1)  - indicates that the time interval is 1/1024s
                                2. 1/512s (2)  - indicates that the time interval is 1/512s
                                3. 1/256s (3)  - indicates that the time interval is 1/256s
                                4. 1/128s (4)  - indicates that the time interval is 1/128s
                                5. 1/64s  (5)  - indicates that the time interval is 1/64s
                                6. 1/32s  (6)  - indicates that the time interval is 1/32s
                                7. 1/16s  (7)  - indicates that the time interval is 1/16s
                                8. 1/8s   (8)  - indicates that the time interval is 1/8s
                                9. 1/4s   (9)  - indicates that the time interval is 1/4s
                                10. 1/2s  (10) - indicates that the time interval is  1/2s
                                11. 1s    (11) - indicates that the time interval is  1s
                                12. 2s    (12) - indicates that the time interval is  2s
                                13. 4s    (13) - indicates that the time interval is  4s
                                14. 8s    (14) - indicates that the time interval is  8s
                                15. 16s   (15) - indicates that the time interval is  16s
                                16. 32s   (16) - indicates that the time interval is  32s
                                17. 64s   (17) - indicates that the time interval is  64s
                                18. 128s  (18) - indicates that the time interval is  128s
                                19. 256s  (19) - indicates that the time interval is  256s
                                20. 512s  (20) - indicates that the time interval is  512s
                                21. 1024s (21) - indicates that the time interval is  1024s
                                "
                        ::= { hwClock1588ManageEntry 19 }


                -- 1.3.6.1.4.1.2011.6.25.1.5.1.20
                hw1588ClkPtpLockState OBJECT-TYPE
                        SYNTAX INTEGER
                                {
                                locked(1),
                                unlocked(2)
                                }
                        MAX-ACCESS read-only
                        STATUS current
                        DESCRIPTION
                                "1588 port lock state.
                                Options:
                                1. locked(1)   -  indicates that the clock is locked
                                2. unlocked(2) -  indicates that the clock is unlocked
                                "
                        ::= { hwClock1588ManageEntry 20 }


                -- 1.3.6.1.4.1.2011.6.25.1.5.1.21
                hw1588ClkInWorkMode OBJECT-TYPE
                        SYNTAX INTEGER
                                {
                                ptp(1),
                                bits(2)
                                }
                        MAX-ACCESS read-create
                        STATUS current
                        DESCRIPTION
                                "Time source type.
                                Options:
                                1. ptp(1)  - indicates that time source that need to specify frame/slot/port
                                2. bits(2) - indicates that time source of a BITS port
                                "
                        ::= { hwClock1588ManageEntry 21 }


                -- 1.3.6.1.4.1.2011.6.25.1.5.1.22
                hw1588ClkInSelectStatus OBJECT-TYPE
                        SYNTAX INTEGER
                                {
                                yes(1),
                                no(2)
                                }
                        MAX-ACCESS read-only
                        STATUS current
                        DESCRIPTION
                                "Time source select status.
                                Options:
                                1. yes(1)  - indicates that the time source is selected as the current time source.
                                2. no(2)   - indicates that the time source isn't selected as the current time source.
                                "
                        ::= { hwClock1588ManageEntry 22 }


                -- 1.3.6.1.4.1.2011.6.25.1.6
                hwClockTransManageTable OBJECT-TYPE
                        SYNTAX SEQUENCE OF HwClockTransManageEntry
                        MAX-ACCESS not-accessible
                        STATUS current
                        DESCRIPTION
                                "Clock transaction management table.
                                This table is used to configure and query the clock transmission.
                                The index of this table is hwClkTransID, which is also the ID of
                                the clock transmission.
                                "
                        ::= { hwClkMibObjects 6 }


                -- 1.3.6.1.4.1.2011.6.25.1.6.1
                hwClockTransManageEntry OBJECT-TYPE
                        SYNTAX HwClockTransManageEntry
                        MAX-ACCESS not-accessible
                        STATUS current
                        DESCRIPTION
                                "Clock transaction management table.
                                This table is used to configure and query the clock transmission.
                                The index of this entry is hwClkTransID, which is also the ID of
                                the clock transmission.
                                "
                        INDEX { hwClkTransID }
                        ::= { hwClockTransManageTable 1 }


                HwClockTransManageEntry ::=
                        SEQUENCE {
                                hwClkTransID
                                        Integer32,
                                hwClkLocalIP
                                        IpAddress,
                                hwClkVlanTag
                                        Integer32,
                                hwClkRemoteIP
                                        IpAddress,
                                hwClkRowStatus
                                        RowStatus
                         }

                -- 1.3.6.1.4.1.2011.6.25.1.6.1.1
                hwClkTransID OBJECT-TYPE
                        SYNTAX Integer32 (1..32)
                        MAX-ACCESS not-accessible
                        STATUS current
                        DESCRIPTION
                                "Clock transaction ID: The range is from 1 to 32.
                                Range: 1 - 32
                                "
                        ::= { hwClockTransManageEntry 1 }


                -- 1.3.6.1.4.1.2011.6.25.1.6.1.2
                hwClkLocalIP OBJECT-TYPE
                        SYNTAX IpAddress
                        MAX-ACCESS read-create
                        STATUS current
                        DESCRIPTION
                                "IP address of a local device"
                        ::= { hwClockTransManageEntry 2 }


                -- 1.3.6.1.4.1.2011.6.25.1.6.1.3
                hwClkVlanTag OBJECT-TYPE
                        SYNTAX Integer32 (0..4095)
                        MAX-ACCESS read-create
                        STATUS current
                        DESCRIPTION
                                "VLAN tag.
                                If the value is 0, it indicates that there is no VLAN tag in clock packages.
                                Range: 0 - 4095
                                "
                        ::= { hwClockTransManageEntry 3 }


                -- 1.3.6.1.4.1.2011.6.25.1.6.1.4
                hwClkRemoteIP OBJECT-TYPE
                        SYNTAX IpAddress
                        MAX-ACCESS read-create
                        STATUS current
                        DESCRIPTION
                                "IP address of remote device"
                        ::= { hwClockTransManageEntry 4 }


                -- 1.3.6.1.4.1.2011.6.25.1.6.1.5
                hwClkRowStatus OBJECT-TYPE
                        SYNTAX RowStatus
                        MAX-ACCESS read-create
                        STATUS current
                        DESCRIPTION
                                "Clock transaction operation. If the value is set to 4, it indicates that
                                a clock transmission configuration is added. If the value is set to 6,
                                it indicates that an existing clock transmission configuration is deleted.
                                "
                        ::= { hwClockTransManageEntry 5 }


                -- 1.3.6.1.4.1.2011.6.25.1.7
                hwClockTransIDNext OBJECT-TYPE
                        SYNTAX Integer32 (0..32)
                        MAX-ACCESS read-only
                        STATUS current
                        DESCRIPTION
                                " Clock transaction index that host returns.
                                If the value is 0, it indicates that there is no free index.
                                Range: 0 - 32
                                "
                        ::= { hwClkMibObjects 7 }


                -- 1.3.6.1.4.1.2011.6.25.1.8
                hwACMClockIPTable OBJECT-TYPE
                        SYNTAX SEQUENCE OF HwACMClockIPEntry
                        MAX-ACCESS not-accessible
                        STATUS current
                        DESCRIPTION
                                "Clock ACM source IP table.
                                The index of this table is ifIndex which comes from
                                ifTable. The method for using ifIndex is provided in ifIndex's mib description.
                                "
                        ::= { hwClkMibObjects 8 }


                -- 1.3.6.1.4.1.2011.6.25.1.8.1
                hwACMClockIPEntry OBJECT-TYPE
                        SYNTAX HwACMClockIPEntry
                        MAX-ACCESS not-accessible
                        STATUS current
                        DESCRIPTION
                                "Clock ACM source IP table.
                                The index of this entry is ifIndex which comes from
                                ifTable. The method for using ifIndex is provided in ifIndex's mib description.
                                "
                        INDEX { hwACMClockIPIndex }
                        ::= { hwACMClockIPTable 1 }


                HwACMClockIPEntry ::=
                        SEQUENCE {
                                hwACMClockIPIndex
                                        Integer32,
                                hwACMClockIP
                                        Integer32,
                                hwACMClkPostion
                                        Integer32,
                                hwACMClockIPRowStatus
                                        INTEGER
                         }

                -- 1.3.6.1.4.1.2011.6.25.1.8.1.1
                hwACMClockIPIndex OBJECT-TYPE
                        SYNTAX Integer32 (0..2147483647)
                        MAX-ACCESS read-write
                        STATUS current
                        DESCRIPTION
                                "Currently, it supports only ACM IP address but it can be extended in the future.
                                Range: 0 - 2147483647
                                "
                        ::= { hwACMClockIPEntry 1 }


                -- 1.3.6.1.4.1.2011.6.25.1.8.1.2
                hwACMClockIP OBJECT-TYPE
                        SYNTAX Integer32
                        MAX-ACCESS read-write
                        STATUS current
                        DESCRIPTION
                                " ACM cLOCK switch IP address at layer 3.
                                Range: 0.0.0.0-255.255.255.255
                                "
                        ::= { hwACMClockIPEntry 2 }


                -- 1.3.6.1.4.1.2011.6.25.1.8.1.3
                hwACMClkPostion OBJECT-TYPE
                        SYNTAX Integer32
                        MAX-ACCESS read-write
                        STATUS current
                        DESCRIPTION
                                "Physical position of clock source ACM IP address.
                                The highest byte is useless. The second byte describes the frame ID,
                                The third byte describes the slot ID.
                                The lowest byte is useless.
                                The following shows how to use parameter  during the get or set operation.
                                0x 0000, FFFF,0000,0000  Frame ID;     0-255
                                0x 0000, 0000,FFFF,0000  Slot  ID;     0-255.
                                "
                        ::= { hwACMClockIPEntry 3 }


                -- 1.3.6.1.4.1.2011.6.25.1.8.1.4
                hwACMClockIPRowStatus OBJECT-TYPE
                        SYNTAX INTEGER
                                {
                                createAndGo(4),
                                destroy(6)
                                }
                        MAX-ACCESS read-create
                        STATUS current
                        DESCRIPTION
                                "Rowstatus of the ACM clock IP address.
                                Options:
                                1. createAndGo(4) - Creates an ACM clock IP address
                                2. destroy(6)     - Destroys an ACM clock IP address.
                                "
                        ::= { hwACMClockIPEntry 4 }


                -- 1.3.6.1.4.1.2011.6.25.1.9
                hwBitsPortManageTable OBJECT-TYPE
                        SYNTAX SEQUENCE OF HwBitsPortManageEntry
                        MAX-ACCESS not-accessible
                        STATUS current
                        DESCRIPTION
                                "Time management table.
                                The index of this table is ifIndex which comes from
                                ifTable. The method for using ifIndex is provided in ifIndex's mib description.
                                "
                        ::= { hwClkMibObjects 9 }


                -- 1.3.6.1.4.1.2011.6.25.1.9.1
                hwBitsPortManageEntry OBJECT-TYPE
                        SYNTAX HwBitsPortManageEntry
                        MAX-ACCESS not-accessible
                        STATUS current
                        DESCRIPTION
                                "Time management table.
                                The index of this entry is ifIndex which comes from
                                ifTable. The method for using ifIndex is provided in ifIndex's mib description.
                                "
                        INDEX { ifIndex }
                        ::= { hwBitsPortManageTable 1 }


                HwBitsPortManageEntry ::=
                        SEQUENCE {
                                hwBitsPortClkWorkMode
                                        INTEGER,
                                hwBitsPortTimeWorkMode
                                        INTEGER,
                                hwBitsPortIOStatus
                                        INTEGER,
                                hwPtpBitsClockAccuracy
                                        Integer32,
                                hwPtpBitsClockClass
                                        Integer32,
                                hwPtpBitsPriority1
                                        Integer32,
                                hwPtpBitsPriority2
                                        Integer32,
                                hwPtpBitsTimeSource
                                        INTEGER,
                                hwBits1ppsDelayDirection
                                        INTEGER,
                                hwBits1ppsDelayValue
                                        Integer32,
                                hwPtpBitsPortLocalPriority
                                        Integer32,
                                hwPtpBitsOffsetScaledLogVariance
                                        Integer32
                         }

                -- 1.3.6.1.4.1.2011.6.25.1.9.1.1
                hwBitsPortClkWorkMode OBJECT-TYPE
                        SYNTAX INTEGER
                                {
                                e1(1),
                                t1(2),
                                f2mhz(3),
                                invalid(255)
                                }
                        MAX-ACCESS read-create
                        STATUS current
                        DESCRIPTION
                                "Port work mode of BITS clock.
                                Options:
                                1. e1(1)        - indicates that E1 type of clock input/output.
                                2. t1(2)        - indicates that T1 type of clock input/output
                                3. f2mhz(3)     - indicates that 2MHz type of clock input/output
                                4. invalid(255) - indicates that it is not configured
                                "
                        ::= { hwBitsPortManageEntry 1 }


                -- 1.3.6.1.4.1.2011.6.25.1.9.1.2
                hwBitsPortTimeWorkMode OBJECT-TYPE
                        SYNTAX INTEGER
                                {
                                ppsubx(1),
                                dcls(2),
                                invalid(255),
                                ppsnmea(3)
                                }
                        MAX-ACCESS read-create
                        STATUS current
                        DESCRIPTION
                                "Time work mode of Bits clock.
                                Options:
                                1.ppsubx(1)           - indicates that 1pps+ubx type of time input/output
                                2.dcls(2)             - indicates that DCLS type of time input/output
                                3.invalid(255)        - indicates that it is not configured
                                4.ppsnmea(3)          - indicates that 1pps+nmea type of time input/output
                                "
                        ::= { hwBitsPortManageEntry 2 }


                -- 1.3.6.1.4.1.2011.6.25.1.9.1.3
                hwBitsPortIOStatus OBJECT-TYPE
                        SYNTAX INTEGER
                                {
                                input(1),
                                output(2),
                                invalid(255)
                                }
                        MAX-ACCESS read-create
                        STATUS current
                        DESCRIPTION
                                "Time interface direction mode.
                                Options:
                                1.input(1)     - indicates that the mode of time interface is input
                                2.output(2)    - indicates that the mode of time interface source is output
                                3.invalid(255) - indicates that time input/output isn't configured
                                "
                        ::= { hwBitsPortManageEntry 3 }


                -- 1.3.6.1.4.1.2011.6.25.1.9.1.4
                hwPtpBitsClockAccuracy OBJECT-TYPE
                        SYNTAX Integer32 (0..255)
                        MAX-ACCESS read-create
                        STATUS current
                        DESCRIPTION
                                "The clockAccuracy characterizes a clock for the purpose of the best master clock (BMC) algorithm. The value of
                                this attribute shall be estimated by the clock to a precision consistent with the value of the selected enumeration.
                                BC: 
				Range: 0x0-0xFF
                                01 0x20     - indicates that the time is accurate to within 25 ns
                                02 0x21     - indicates that the time is accurate to within 100 ns
                                03 0x22     - indicates that the time is accurate to within 250 ns
				04 0x23     - indicates that the time is accurate to within 1 us
				05 0x24     - indicates that the time is accurate to within 2.5 us
				06 0x25     - indicates that the time is accurate to within 10 us
				07 0x26     - indicates that the time is accurate to within 25 us
				08 0x27     - indicates that the time is accurate to within 100 us
				09 0x28     - indicates that the time is accurate to within 250 us
                                10 0x29     - indicates that the time is accurate to within 1 ms
                                11 0x2A     - indicates that the time is accurate to within 2.5 ms
                                12 0x2B     - indicates that the time is accurate to within 10 ms
                                13 0x2C     - indicates that the time is accurate to within 25 ms
                                14 0x2D     - indicates that the time is accurate to within 100 ms
                                15 0x2E     - indicates that the time is accurate to within 250 ms
                                16 0x2F     - indicates that the time is accurate to within 1 s
                                17 0x30     - indicates that the time is accurate to within 10 s
                                18 0x31     - indicates that the time is accurate to >10 s
                                19 0x80-0xFD - indicates that for use by alternate PTP profiles

                                Default: 0x20
				
				T-BC:				
				Options:
				01 0xFE     - indicates that the time accuracy is unknown
				02 0x21     - indicates that the time is accurate to within 100 ns
				
				Default: 0xFE
                                "
                        ::= { hwBitsPortManageEntry 4 }


                -- 1.3.6.1.4.1.2011.6.25.1.9.1.5
                hwPtpBitsClockClass OBJECT-TYPE
                        SYNTAX Integer32 (0..255)
                        MAX-ACCESS read-create
                        STATUS current
                        DESCRIPTION
                                "The clockClass attribute of an ordinary or boundary clock denotes the traceability of the time or frequency
                                distributed by the grandmaster clock.
                                BC:
                                Range: 0-255

                                1.  6         - indicates that shall designate a clock that is synchronized to a primary reference time source. The timescale distributed shall
                                          be PTP. A clockClass 6 clock shall not be a slave to another clock in the domain
                                2.  7         - indicates that shall designate a clock that has previously been designated as clockClass 6 but that has lost the ability to
                                          synchronize to a primary reference time source and is in holdover mode and within holdover specifications. The timescale
                                          distributed shall be PTP. A clockClass 7 clock shall not be a slave to another clock in the domain
                                3.  13         - indicates that shall designate a clock that is synchronized to an application-specific source of time. The timescale
                                          distributed shall be ARB. A clockClass 13 clock shall not be a slave to another clock in the domain
                                4.  14         - indicates that shall designate a clock that has previously been designated as clockClass 13 but that has lost the ability to
                                          synchronize to an application-specific source of time and is in holdover mode and within holdover specifications.
                                          The timescale distributed shall be ARB. A clockClass 14 clock shall not be a slave to another clock in the domain
                                5.  52         - indicates that degradation alternative A for a clock of clockClass 7 that is not within holdover specification. A clock of
                                          clockClass 52 shall not be a slave to another clock in the domain
                                6.  58         - indicates that degradation alternative A for a clock of clockClass 14 that is not within holdover specification. A clock of
                                          clockClass 58 shall not be a slave to another clock in the domain
                                7.  187         - indicates that degradation alternative B for a clock of clockClass 7 that is not within holdover specification. A clock of
                                          clockClass 187 may be a slave to another clock in the domain
                                8.  193         - indicates that degradation alternative B for a clock of clockClass 14 that is not within holdover specification. A clock of
                                          clockClass 193 may be a slave to another clock in the domain
                                9.  248         - indicates that default. This clockClass shall be used if none of the other clockClass definitions apply
                                10. 255         - indicates that shall be the clockClass of a slave-only clock

                                Default: 6
								
                                T-BC:
                                Range: 0-255

                                1.  6           - T-GM connected to a PRTC in locked mode
                                2.  7           - T-GM in holdover, within holdover specification, traceable or non-traceable to Category 1 frequency source
                                3.  135         - T-BC in holdover, within holdover specification, traceable or non-traceable to Category 1 frequency source
                                4.  140         - T-GM in holdover, out of holdover specification, traceable to Category 1 frequency source
                                5.  150         - T-GM in holdover, out of holdover specification, traceable to Category 2 frequency source
                                6.  160         - T-GM in holdover, out of holdover specification, traceable to Category 3 frequency source
                                7.  165         - T-BC in holdover, out of holdover specification
                                8.  248         - T-GM or T-BC without time reference since start-up
                                9.  255         - Slave only OC(does not send Announce messages)

                                Default: 6
                                "
                        ::= { hwBitsPortManageEntry 5 }


                -- 1.3.6.1.4.1.2011.6.25.1.9.1.6
                hwPtpBitsPriority1 OBJECT-TYPE
                        SYNTAX Integer32 (0..255)
                        MAX-ACCESS read-create
                        STATUS current
                        DESCRIPTION
                                "The attribute priority1 is used in the execution of the best master clock algorithm. Lower values take precedence.
                                Range: 0-255
                                Default: 128
								
				This attribute is invalid in T-BC mode.
                                "
                        ::= { hwBitsPortManageEntry 6 }


                -- 1.3.6.1.4.1.2011.6.25.1.9.1.7
                hwPtpBitsPriority2 OBJECT-TYPE
                        SYNTAX Integer32 (0..255)
                        MAX-ACCESS read-create
                        STATUS current
                        DESCRIPTION
                                "The attribute priority2 is used in the execution of the best master clock algorithm. Lower values take precedence.
                                Range: 0-255
                                Default: 128
                                "
                        ::= { hwBitsPortManageEntry 7 }


                -- 1.3.6.1.4.1.2011.6.25.1.9.1.8
                hwPtpBitsTimeSource OBJECT-TYPE
                        SYNTAX INTEGER
                                {
                                atomicClock(16),
                                gPS(32),
                                terrestrialRadio(48),
                                ptp(64),
                                ntp(80),
                                handSet(96),
                                other(144),
                                internalOscillator(160)
                                }
                        MAX-ACCESS read-create
                        STATUS current
                        DESCRIPTION
                                "This attribute indicates the source of time used by the grandmaster clock.
                                Options:
                                1.atomicClock(16)        - indicates that any device, or device directly connected to such a device,
                                                           that is based on atomic resonance for frequency and that has been calibrated
                                                           against international standards for frequency and, if the PTP timescale is used.
                                2.gPS(32)                - indicates that any device synchronized to a satellite system that distribute time
                                                           and frequency tied to international standards
                                3.terrestrialRadio(48)   - indicates that any device synchronized via any of the radio distribution systems
                                                           that distribute time and frequency tied to international standards
                                4.ptp(64)                - indicates that any device synchronized to a PTP-based source of time external to the domain
                                5.ntp(80)                - indicates that any device synchronized via NTP or Simple Network Time Protocol (SNTP) to servers
                                                           that distribute time and frequency tied to international standards
                                6.handSet(96)            - indicates that used for any device whose time has been set by means of a human interface
                                                           based on observation of an international standards source of time to within the claimed clock accuracy
                                7.other(144)             - indicates that other source of time and/or frequency not covered by other values
                                8.internalOscillator(160)- indicates that any device whose frequency is not based on atomic resonance nor calibrated against international
                                                           standards for frequency, and whose time is based on a free-running oscillator with epoch determined in an
                                                           arbitrary or unknown manner

                                Default: gPS(32)
                                "
                        ::= { hwBitsPortManageEntry 8 }


                -- 1.3.6.1.4.1.2011.6.25.1.9.1.9
                hwBits1ppsDelayDirection OBJECT-TYPE
                        SYNTAX INTEGER
                                {
                                receive(1),
                                send(2)
                                }
                        MAX-ACCESS read-create
                        STATUS current
                        DESCRIPTION
                                "Delay mode of the time signal on the BITS port.
                                Options:
                                1.receive(1)           - indicates that delay mode is receive
                                2.send(2)             - indicates that delay mode is send
                                "
                        ::= { hwBitsPortManageEntry 9 }


                -- 1.3.6.1.4.1.2011.6.25.1.9.1.10
                hwBits1ppsDelayValue OBJECT-TYPE
                        SYNTAX Integer32 (0..200000)
                        MAX-ACCESS read-create
                        STATUS current
                        DESCRIPTION
                                "Adjusted delay of the time signal on the BITS port. In receive mode, it ranges from 0 to 200000.
                                In send mode, it ranges from 0 to 1600.
                                Unit:ns
                                Default: 0
                                "
                        ::= { hwBitsPortManageEntry 10 }

                -- 1.3.6.1.4.1.2011.6.25.1.9.1.11
                hwPtpBitsPortLocalPriority OBJECT-TYPE
                        SYNTAX Integer32 (1..255)
                        MAX-ACCESS read-create
                        STATUS current
                        DESCRIPTION
                                "In T-BC mode, the local priority of the BITS port is configured to calculate the optimum master clock. 
                                The smaller the value, the higher the priority. 
                                Range: 1-255
                                Default value: 128

                                This attribute is invalid in BC mode.								
                                "
                        ::= { hwBitsPortManageEntry 11 }
						
                -- 1.3.6.1.4.1.2011.6.25.1.9.1.12
                hwPtpBitsOffsetScaledLogVariance OBJECT-TYPE
                        SYNTAX Integer32 (0..65535)
                        MAX-ACCESS read-create
                        STATUS current
                        DESCRIPTION
                                "Indicates estimate of the variations of the local clock from a linear timescale. 
                                In T-BC mode, it can only be 0x4E5D (default) and 0xFFFF. 
                                
                                This attribute is invalid in BC mode. 
                                "
                        ::= { hwBitsPortManageEntry 12 }
				
                -- 1.3.6.1.4.1.2011.6.25.1.10
                hw1588ClkPtpPortManageTable OBJECT-TYPE
                        SYNTAX SEQUENCE OF Hw1588ClkPtpPortManageEntry
                        MAX-ACCESS not-accessible
                        STATUS current
                        DESCRIPTION
                                "1588 clock PTP port management table.
                                The index of this table is ifIndex which comes from ifTable.
                                The method for using ifIndex is provided in ifIndex's mib description.
                                "
                        ::= { hwClkMibObjects 10 }


                -- 1.3.6.1.4.1.2011.6.25.1.10.1
                hw1588ClkPtpPortManageEntry OBJECT-TYPE
                        SYNTAX Hw1588ClkPtpPortManageEntry
                        MAX-ACCESS not-accessible
                        STATUS current
                        DESCRIPTION
                                "1588 clock PTP port management table.
                                The index of this entry is ifIndex which comes from ifTable.
                                The method for using ifIndex is provided in ifIndex's mib description.
                                "
                        INDEX { ifIndex }
                        ::= { hw1588ClkPtpPortManageTable 1 }


                Hw1588ClkPtpPortManageEntry ::=
                        SEQUENCE {
                                hw1588ClkPtpPortState
                                        INTEGER,
                                hw1588ClkPtpPortEnable
                                        INTEGER,
                                hw1588ClkPtpPortVlan
                                        Integer32,
                                hw1588ClkPtpPortSourceIp
                                        IpAddress,
                                hw1588ClkPtpPortMsgFormat
                                        INTEGER,
                                hw1588ClkPtpPortInfoMode
                                        INTEGER,
                                hw1588ClkPtpPortAnnounceSendTimeInterval
                                        Integer32,
                                hw1588ClkPtpPortSyncSendTimeInterval
                                        Integer32,
                                hw1588ClkPtpPortReqSendTimeInterval
                                        Integer32,
                                hw1588ClkPtpPortLineWarpMode
                                        INTEGER,
                                hw1588ClkPtpPortLineWarpDirect
                                        INTEGER,
                                hw1588ClkPtpPortLineWarpValue
                                        Integer32,
                                hw1588ClkPtpPortAnnounceTimeout
                                        Integer32,
                                hw1588ClkPtpPortDomainNum
                                        Integer32,
                                hw1588ClkDSCP
                                        Integer32,
                                hw1588ClkVlanPRI
                                        Integer32,
                                hw1588ClkPtpPortDelayMechanism
                                        INTEGER,
                                hw1588ClkPtpPortMacDestinationMac
                                        MacAddress,
                                hw1588ClkPtpPortUdpDestinationMac
                                        MacAddress,
                                hw1588ClkPtpPortUdpEgressSourceIp
                                        IpAddress,
                                hw1588ClkPtpPortUdpEgressDestinationIp
                                        IpAddress,
                                hw1588ClkPtpPortUdpVlanPRI
                                        Integer32,
                                hw1588ClkPtpPortMacVlanPRI
                                        Integer32,
                                hw1588ClkPtpPortUdpEgressDscp
                                        Integer32,
                                hw1588ClkPtpPortClockStep
                                        INTEGER,
                                hw1588ClkPtpPortUdpVlan
                                        Integer32,
                                hw1588ClkPtpPortMacVlan
                                        Integer32,
                                hwPtpPortRingFiberLengthChangeValue
                                        Integer32,
                                hwPtpPortRingFiberLengthChangeValueFlag
                                        INTEGER,
                                hw1588ClkPtpPortNotSlave
                                        INTEGER,
                                hw1588ClkPtpPortLocalPriority
                                        Integer32
                        }

                -- 1.3.6.1.4.1.2011.6.25.1.10.1.1
                hw1588ClkPtpPortState OBJECT-TYPE
                        SYNTAX INTEGER
                                {
                                initializing(1),
                                faulty(2),
                                disabled(3),
                                listening(4),
                                premaster(5),
                                master(6),
                                passive(7),
                                uncalibrated(8),
                                slave(9),
                                invalid(255)
                                }
                        MAX-ACCESS read-only
                        STATUS current
                        DESCRIPTION
                                "1588 port status.
                                Options:
                                1.initializing(1)  - indicates that the state of 1588 clock PTP port is initializing
                                2.faulty(2)        - indicates that the state of 1588 clock PTP port is faulty
                                3.disabled(3)      - indicates that the state of 1588 clock PTP port is disabled
                                4.listening(4)     - indicates that the state of 1588 clock PTP port is listening
                                5.premaster(5)     - indicates that the state of 1588 clock PTP port is premaster
                                6.master(6)        - indicates that the state of 1588 clock PTP port is master
                                7.passive(7)       - indicates that the state of 1588 clock PTP port is passive
                                8.uncalibrated(8)  - indicates that the state of 1588 clock PTP port is uncalibrated
                                9.slave(9)         - indicates that the state of 1588 clock PTP port is slave
                                10.invalid(255)    - indicates that the state of 1588 clock PTP port is invalid
                                "
                        ::= { hw1588ClkPtpPortManageEntry 1 }


                -- 1.3.6.1.4.1.2011.6.25.1.10.1.2
                hw1588ClkPtpPortEnable OBJECT-TYPE
                        SYNTAX INTEGER
                                {
                                enable(1),
                                disable(2)
                                }
                        MAX-ACCESS read-write
                        STATUS current
                        DESCRIPTION
                                "Enable or disable the 1588 function of PTP port.
                                Options:
                                1. enable(1)   -Enable the 1588 function of this port
                                2. disable(2)  -Disable the 1588 function of this port
                                Default: disable(2)
                                "
                        ::= { hw1588ClkPtpPortManageEntry 2 }


                -- 1.3.6.1.4.1.2011.6.25.1.10.1.3
                hw1588ClkPtpPortVlan OBJECT-TYPE
                        SYNTAX Integer32 (0..4094)
                        MAX-ACCESS read-write
                        STATUS obsolete
                        DESCRIPTION
                                "PTP VLAN.
                                Range: 0 - 4094
                                "
                        ::= { hw1588ClkPtpPortManageEntry 3 }


                -- 1.3.6.1.4.1.2011.6.25.1.10.1.4
                hw1588ClkPtpPortSourceIp OBJECT-TYPE
                        SYNTAX IpAddress
                        MAX-ACCESS read-write
                        STATUS obsolete
                        DESCRIPTION
                                "PTP port source IP address"
                        ::= { hw1588ClkPtpPortManageEntry 4 }


                -- 1.3.6.1.4.1.2011.6.25.1.10.1.5
                hw1588ClkPtpPortMsgFormat OBJECT-TYPE
                        SYNTAX INTEGER
                                {
                                ptpeth(1),
                                ptpip(2)
                                }
                        MAX-ACCESS read-only
                        STATUS current
                        DESCRIPTION
                                "PTP message encapsulation format,the default value is PTPETH(1).
                                Options:
                                1. ptpeth(1) - indicates that the PTP message is encapsulated into an Ethernet packet
                                2. ptpip(2)  - indicates that the PTP message is encapsulated into an IP packet
                                "
                        ::= { hw1588ClkPtpPortManageEntry 5 }


                -- 1.3.6.1.4.1.2011.6.25.1.10.1.6
                hw1588ClkPtpPortInfoMode OBJECT-TYPE
                        SYNTAX INTEGER
                                {
                                multicast(1),
                                unicast(2)
                                }
                        MAX-ACCESS read-only
                        STATUS current
                        DESCRIPTION
                                "PTP info mode.
                                Default: multicast(1)
                                Options:
                                1. multicast(1) - indicates that the Info mode of the 1588 clock PTP port is multicast
                                2. unicast(2)  - indicates that the Info mode of the 1588 clock PTP port is unicast
                                "
                        ::= { hw1588ClkPtpPortManageEntry 6 }


                -- 1.3.6.1.4.1.2011.6.25.1.10.1.7
                hw1588ClkPtpPortAnnounceSendTimeInterval OBJECT-TYPE
                        SYNTAX Integer32 (6..14)
                        MAX-ACCESS read-create
                        STATUS current
                        DESCRIPTION
                                "Interval for sending announce packets.
                                BC:
                                Default: 1/8s(7)
                                Options:
                                    1. 1/16s  (6)  - indicates that the time interval is 1/16s
                                    2. 1/8s   (7)  - indicates that the time interval is 1/8s
                                    3. 1/4s   (8)  - indicates that the time interval is 1/4s
                                    4. 1/2s   (9)  - indicates that the time interval is 1/2s
                                    5. 1s     (10) - indicates that the time interval is 1s
                                    6. 2s     (11) - indicates that the time interval is 2s
                                    7. 4s     (12) - indicates that the time interval is 4s
                                    8. 8s     (13) - indicates that the time interval is 8s
                                    9. 16s    (14) - indicates that the time interval is 16s  
									
                                T-BC:
                                    1/8s   (7)  - indicates that the time interval is 1/8s
                                "
                        ::= { hw1588ClkPtpPortManageEntry 7 }


                -- 1.3.6.1.4.1.2011.6.25.1.10.1.8
                hw1588ClkPtpPortSyncSendTimeInterval OBJECT-TYPE
                        SYNTAX Integer32 (2..11)
                        MAX-ACCESS read-create
                        STATUS current
                        DESCRIPTION
                                "Interval for sending sync packets.
                                BC:
                                Default: 1/16s(6)
                                Options:
                                    1. 1/256s (2)  - indicates that the time interval is 1/256s
                                    2. 1/128s (3)  - indicates that the time interval is 1/128s
                                    3. 1/64s  (4)  - indicates that the time interval is 1/64s
                                    4. 1/32s  (5)  - indicates that the time interval is 1/32s
                                    5. 1/16s  (6)  - indicates that the time interval is 1/16s
                                    6. 1/8s   (7)  - indicates that the time interval is 1/8s
                                    7. 1/4s   (8)  - indicates that the time interval is 1/4s
                                    8. 1/2s   (9)  - indicates that the time interval is 1/24s
                                    9. 1s     (10) - indicates that the time interval is 1s
                                    10.2s     (11) - indicates that the time interval is 2s   
				
                                T-BC:					
                                    1/16s  (6)  - indicates that the time interval is 1/16s
                                "
                        ::= { hw1588ClkPtpPortManageEntry 8 }


                -- 1.3.6.1.4.1.2011.6.25.1.10.1.9
                hw1588ClkPtpPortReqSendTimeInterval OBJECT-TYPE
                        SYNTAX Integer32 (6..14)
                        MAX-ACCESS read-create
                        STATUS current
                        DESCRIPTION
                                "Interval for sending req packets.
                                BC:
                                Default: 1/8s(7)
	                            Options:
	                                1. 1/16s  (6)  - indicates that the time interval is 1/16s
	                                3. 1/8s   (7)  - indicates that the time interval is 1/8s
	                                3. 1/4s   (8)  - indicates that the time interval is 1/4s
	                                4. 1/2s   (9)  - indicates that the time interval is 1/2s
	                                5. 1s     (10) - indicates that the time interval is 1s
	                                6. 2s     (11) - indicates that the time interval is 2s
	                                7. 4s     (12) - indicates that the time interval is 4s
	                                8. 8s     (13) - indicates that the time interval is 8s
	                                9. 16s    (14) - indicates that the time interval is 16s    
	                            
                                T-BC:
                                    1/16s  (6)  - indicates that the time interval is 1/16s
                                "
                        ::= { hw1588ClkPtpPortManageEntry 9 }


                -- 1.3.6.1.4.1.2011.6.25.1.10.1.10
                hw1588ClkPtpPortLineWarpMode OBJECT-TYPE
                        SYNTAX INTEGER
                                {
                                length(1),
                                time(2)
                                }
                        MAX-ACCESS read-create
                        STATUS current
                        DESCRIPTION
                                "Type of the asymmetric transmission windage for optical
                                fibers, the default value is length(1).
                                Options:
                                1. length(1) - indicates that the warp is represented by length
                                2. time(2)   - indicates that the warp is represented by time
                                "
                        ::= { hw1588ClkPtpPortManageEntry 10 }


                -- 1.3.6.1.4.1.2011.6.25.1.10.1.11
                hw1588ClkPtpPortLineWarpDirect OBJECT-TYPE
                        SYNTAX INTEGER
                                {
                                positive(1),
                                negative(2)
                                }
                        MAX-ACCESS read-create
                        STATUS current
                        DESCRIPTION
                                "Fiber windage direction, the default value is positive(1).
                                Options:
                                1. positive(1) - indicates that the warp is in the positive direction
                                2. negative(2) - indicates that the warp is in the negative direction
                                "
                        ::= { hw1588ClkPtpPortManageEntry 11 }


                -- 1.3.6.1.4.1.2011.6.25.1.10.1.12
                hw1588ClkPtpPortLineWarpValue OBJECT-TYPE
                        SYNTAX Integer32 (0..65529)
                        MAX-ACCESS read-create
                        STATUS current
                        DESCRIPTION
                                "PTP line warp value.
                                If warp mode is length(1), the range is 0~14562m.
                                If warp mode is time(2)  the range is 0~65529 ns.
                                "
                        ::= { hw1588ClkPtpPortManageEntry 12 }


                -- 1.3.6.1.4.1.2011.6.25.1.10.1.13
                hw1588ClkPtpPortAnnounceTimeout OBJECT-TYPE
                        SYNTAX Integer32 (2..255)
                        MAX-ACCESS read-create
                        STATUS current
                        DESCRIPTION
                                "Announce timeout specifies that the interval for receiving announce packets on the port.
                                BC:	
                                    Range: 2 - 255
                                    Default value: 3
                                T-BC:
                                    Range: 3 - 255
                                    Default value: 3
                                "
                        ::= { hw1588ClkPtpPortManageEntry 13 }


                -- 1.3.6.1.4.1.2011.6.25.1.10.1.14
                hw1588ClkPtpPortDomainNum OBJECT-TYPE
                        SYNTAX Integer32 (0..255)
                        MAX-ACCESS read-create
                        STATUS obsolete
                        DESCRIPTION
                                "1588 clock domain number.
                                Range: 0-255
                                Default value: 0
                                "
                        ::= { hw1588ClkPtpPortManageEntry 14 }


                -- 1.3.6.1.4.1.2011.6.25.1.10.1.15
                hw1588ClkDSCP OBJECT-TYPE
                        SYNTAX Integer32 (0..63)
                        MAX-ACCESS read-create
                        STATUS obsolete
                        DESCRIPTION
                                "1588 clock DSCP:0-63."
                        ::= { hw1588ClkPtpPortManageEntry 15 }


                -- 1.3.6.1.4.1.2011.6.25.1.10.1.16
                hw1588ClkVlanPRI OBJECT-TYPE
                        SYNTAX Integer32 (0..7)
                        MAX-ACCESS read-create
                        STATUS obsolete
                        DESCRIPTION
                                "1588 clock Vlan priority:0-7."
                        ::= { hw1588ClkPtpPortManageEntry 16 }


                -- 1.3.6.1.4.1.2011.6.25.1.10.1.17
                hw1588ClkPtpPortDelayMechanism OBJECT-TYPE
                        SYNTAX INTEGER
                                {
                                delayMechanism(1),
                                pdelayMechanism(2)
                                }
                        MAX-ACCESS read-create
                        STATUS current
                        DESCRIPTION
                                "Delay measurement mechanism.
                                BC:
                                Options:
                                    1.delayMechanism(1)   - indicates that delay mechanism is delay-mechanism.
                                    2.pdelayMechanism(2)  - indicates that delay mechanism is pdelay-mechanism.
                                    Default: delayMechanism(1)
									
                                T-BC:
                                    delayMechanism(1)   - indicates that delay mechanism is delay-mechanism.
                                "
                        ::= { hw1588ClkPtpPortManageEntry 17 }


                -- 1.3.6.1.4.1.2011.6.25.1.10.1.18
                hw1588ClkPtpPortMacDestinationMac OBJECT-TYPE
                        SYNTAX MacAddress
                        MAX-ACCESS read-create
                        STATUS current
                        DESCRIPTION
                                "Destination MAC address of MAC-encapsulated packets.
                                BC:
                                    When the delay measurement mechanism is delay, the default destination MAC address is 011b-1900-0000.
                                    When the delay measurement mechanism is pdelay, the default destination MAC address is 0180-c200-000e.
                                T-BC:
                                    Supports only MAC-encapsulated packets and supports multicast MAC address configuration. 
                                    It can be 01-80-C2-00-00-0E and 01-1B-19-00-00-00 (default). 
                                "
                        ::= { hw1588ClkPtpPortManageEntry 18 }


                -- 1.3.6.1.4.1.2011.6.25.1.10.1.19
                hw1588ClkPtpPortUdpDestinationMac OBJECT-TYPE
                        SYNTAX MacAddress
                        MAX-ACCESS read-create
                        STATUS current
                        DESCRIPTION
                                "Destination MAC address of UDP-encapsulated packets.
                                When the delay measurement mechanism is delay, the default destination MAC address is 0100-5e00-0181.
                                When the delay measurement mechanism is pdelay, the default destination MAC address is 0100-5e00-006b.
                                
                                This attribute is invalid in T-BC mode.
                                "
                        ::= { hw1588ClkPtpPortManageEntry 19 }


                -- 1.3.6.1.4.1.2011.6.25.1.10.1.20
                hw1588ClkPtpPortUdpEgressSourceIp OBJECT-TYPE
                        SYNTAX IpAddress
                        MAX-ACCESS read-create
                        STATUS current
                        DESCRIPTION
                                "Source IP address of UDP-encapsulated packets.
                                Default:0.0.0.0
                                
                                This attribute is invalid in T-BC mode.
                                "
                        ::= { hw1588ClkPtpPortManageEntry 20 }


                -- 1.3.6.1.4.1.2011.6.25.1.10.1.21
                hw1588ClkPtpPortUdpEgressDestinationIp OBJECT-TYPE
                        SYNTAX IpAddress
                        MAX-ACCESS read-create
                        STATUS current
                        DESCRIPTION
                                "Destination IP address of UDP-encapsulated packets.
                                When the delay measurement mechanism is delay, the default destination IP address is 224.0.1.129.
                                When the delay measurement mechanism is pdelay, the default destination IP address is 224.0.0.107.
                                
                                This attribute is invalid in T-BC mode.
                                "
                        ::= { hw1588ClkPtpPortManageEntry 21 }


                -- 1.3.6.1.4.1.2011.6.25.1.10.1.22
                hw1588ClkPtpPortUdpVlanPRI OBJECT-TYPE
                        SYNTAX Integer32 ( -1 | 0..7)
                        MAX-ACCESS read-create
                        STATUS current
                        DESCRIPTION
                                "VLAN priority of UDP-encapsulated packets.
                                Default:7
                                Invalid(-1)
                                
                                This attribute is invalid in T-BC mode.
                                "
                        ::= { hw1588ClkPtpPortManageEntry 22 }


                -- 1.3.6.1.4.1.2011.6.25.1.10.1.23
                hw1588ClkPtpPortMacVlanPRI OBJECT-TYPE
                        SYNTAX Integer32 (-1 | 0..7)
                        MAX-ACCESS read-create
                        STATUS current
                        DESCRIPTION
                                "VLAN priority of MAC-encapsulated packets.
                                Default:7
                                Invalid(-1)
                                
                                This attribute is invalid in T-BC mode.
                                "
                        ::= { hw1588ClkPtpPortManageEntry 23 }


                -- 1.3.6.1.4.1.2011.6.25.1.10.1.24
                hw1588ClkPtpPortUdpEgressDscp OBJECT-TYPE
                        SYNTAX Integer32 (-1 | 0..63  )
                        MAX-ACCESS read-create
                        STATUS current
                        DESCRIPTION
                                "DSCP of UDP-encapsulated packets.
                                Default:56
                                Invalid(-1)
                                
                                This attribute is invalid in T-BC mode.
                                "
                        ::= { hw1588ClkPtpPortManageEntry 24 }


                -- 1.3.6.1.4.1.2011.6.25.1.10.1.25
                hw1588ClkPtpPortClockStep OBJECT-TYPE
                        SYNTAX INTEGER
                                {
                                oneStep(1),
                                twoStep(2)
                                }
                        MAX-ACCESS read-create
                        STATUS current
                        DESCRIPTION
                                "Clock step mode.
                                Options:
                                1.oneStep(1)   - indicates that clock step mode is one-step.
                                2.twoStep(2)   - indicates that clock step mode is two-step. 
                                Default: oneStep(1)       		        
                                "
                        ::= { hw1588ClkPtpPortManageEntry 25 }


                -- 1.3.6.1.4.1.2011.6.25.1.10.1.26
                hw1588ClkPtpPortUdpVlan OBJECT-TYPE
                        SYNTAX Integer32 ( -1 | 0 |1..4094)
                        MAX-ACCESS read-create
                        STATUS current
                        DESCRIPTION
                                "VLAN of UDP-encapsulated packets.
                                Default: untag(0)
                                Invalid(-1)
								
                                This attribute is invalid in T-BC mode.
                                "
                        ::= { hw1588ClkPtpPortManageEntry 26 }


                -- 1.3.6.1.4.1.2011.6.25.1.10.1.27
                hw1588ClkPtpPortMacVlan OBJECT-TYPE
                        SYNTAX Integer32 ( -1 | 0 | 1..4094)
                        MAX-ACCESS read-create
                        STATUS current
                        DESCRIPTION
                                "VLAN of MAC-encapsulated packets.
                                BC:
                                    Default: untag(0)
                                    Invalid(-1)
                                T-BC:
                                    Supports only untag(0). 
                                "
                        ::= { hw1588ClkPtpPortManageEntry 27 }


                -- 1.3.6.1.4.1.2011.6.25.1.10.1.28
                hwPtpPortRingFiberLengthChangeValue OBJECT-TYPE
                        SYNTAX Integer32 ( -1 | 0..65529 )
                        MAX-ACCESS read-only
                        STATUS current
                        DESCRIPTION
                                "The change (unit: ns) of the fiber length in a ring network detection. It may be a positive or negative value, which depends on the next node.
                                If the value is -1, the ring network detection function does not take effect.  "
                        ::= { hw1588ClkPtpPortManageEntry 28 }


                -- 1.3.6.1.4.1.2011.6.25.1.10.1.29
                hwPtpPortRingFiberLengthChangeValueFlag OBJECT-TYPE
                        SYNTAX INTEGER
                                {
                                invalid(-1),
                                negative(1),
                                positive(2)
                                }
                        MAX-ACCESS read-only
                        STATUS current
                        DESCRIPTION
                                "Flag of the change of the fiber length in a ring network detection.
                                Options:
                                1.invalid(-1)   - indicates that the the ring network detection function does not take effect.
                                2.negative(1)   - indicates that the change of the fiber length is a negative value.
                                3.positive(2)   - indicates that the change of the fiber length is a positive value.
                                "
                        ::= { hw1588ClkPtpPortManageEntry 29 }

                -- 1.3.6.1.4.1.2011.6.25.1.10.1.30
                hw1588ClkPtpPortNotSlave OBJECT-TYPE
                        SYNTAX INTEGER
                                {
                                enable(1), 
                                disable(2), 
                                invalid(255)
                                }
                        MAX-ACCESS read-create
                        STATUS current
                        DESCRIPTION
                                "In T-BC mode, this port cannot be the slave port when notSlave is enable; 
                                this port can be the slave port when notSlave is disable. 
                                By default, it is enable(1). 
								
                                This attribute is invalid in BC mode. 
                                "
                        ::= { hw1588ClkPtpPortManageEntry 30 }
				
                -- 1.3.6.1.4.1.2011.6.25.1.10.1.31
                hw1588ClkPtpPortLocalPriority OBJECT-TYPE
                        SYNTAX Integer32 (1..255)
                        MAX-ACCESS read-create
                        STATUS current
                        DESCRIPTION
                                "In T-BC mode, the local priority of the port is configured to calculate the optimum master clock. 
                                The smaller the value, the higher the priority. 
                                Range: 1-255
                                Default value: 128
								
                                This attribute is invalid in BC mode.
                                "
                        ::= { hw1588ClkPtpPortManageEntry 31 }	
				
                -- 1.3.6.1.4.1.2011.6.25.1.11
                hwClkTraps OBJECT IDENTIFIER ::= { hwClkMibObjects 11 }


                -- 1.3.6.1.4.1.2011.6.25.1.11.1
                hwClkTrapVbOids OBJECT IDENTIFIER ::= { hwClkTraps 1 }


                -- 1.3.6.1.4.1.2011.6.25.1.11.1.1
                hwClkGMClockIdChangeTrapSn OBJECT-TYPE
                        SYNTAX Integer32
                        MAX-ACCESS accessible-for-notify
                        STATUS current
                        DESCRIPTION
                                "SN of traps for reporting that the 1588 GM clock identity changes."
                        ::= { hwClkTrapVbOids 1 }


                -- 1.3.6.1.4.1.2011.6.25.1.11.1.2
                hwClkTimeSrcIdChangeTrapSn OBJECT-TYPE
                        SYNTAX Integer32
                        MAX-ACCESS accessible-for-notify
                        STATUS current
                        DESCRIPTION
                                "SN of traps for reporting that the 1588 time source port identity changes."
                        ::= { hwClkTrapVbOids 2 }


                -- 1.3.6.1.4.1.2011.6.25.1.11.1.3
                hw3rdClkOldSubBoardWorkMode OBJECT-TYPE
                        SYNTAX INTEGER
                                {
                                trace(1),
                                keep(2),
                                thirdsurge(3),
                                snap(4),
                                no3rdclksubboard(255)
                                }
                        MAX-ACCESS accessible-for-notify
                        STATUS current
                        DESCRIPTION
                                "The Out work mode of 3rd sub-board clock,the enumerative value is the same
                                with hw3rdClkSubBoardWorkMode.
                                Options:
                                1. trace(1)              - indicates that the clock is working in tracing mode
                                2. keep(2)               - indicates that the clock is working in keeping mode
                                3. thirdsurge(3)          - indicates that the clock is working in 3rd subboard crystal
                                4. snap(4)               - indicates clock is working in snap mode
                                5. no3rdclksubboard(255) - indicates that there is no 3rd subboard
                                "
                        ::= { hwClkTrapVbOids 3 }


                -- 1.3.6.1.4.1.2011.6.25.1.11.1.4
                hwClkOutTypeTrapSn OBJECT-TYPE
                        SYNTAX INTEGER
                                {
                                sdh(1),
                                tdm(2),
                                system(3),
                                clk19M(4),
                                systemObsolete(5),
                                external(6),
                                external1(7)
                                }
                        MAX-ACCESS accessible-for-notify
                        STATUS current
                        DESCRIPTION
                                "Clock out type.
                                Currently, there are seven types: SDH, TDM, system, 19 MHzm, systemObsolete, external and external1.
                                Options:
                                1.sdh(1)                -   indicates that output clock type is SDH
                                2.tdm(2)                -   indicates that output clock type is TDM
                                3.system(3)             -   indicates that output clock type is system
                                4.clk19M(4)             -   indicates that output clock type is clk19M
                                5.systemObsolete(5)     -   indicates that output clock type is systemObsolete
                                6.external(6)           -   indicates that output clock type is external
                                7.external1(7)          -   indicates that output clock type is external1
                                "
                        ::= { hwClkTrapVbOids 4 }


                -- 1.3.6.1.4.1.2011.6.25.1.11.2
                hwClkCommonTraps OBJECT IDENTIFIER ::= { hwClkTraps 2 }


                -- 1.3.6.1.4.1.2011.6.25.1.11.2.1
                hwClkCommonTrapsPrefix OBJECT IDENTIFIER ::= { hwClkCommonTraps 1 }


                -- 1.3.6.1.4.1.2011.6.25.1.11.2.1.1
                hwClkGmcclockIdChangeTrap NOTIFICATION-TYPE
                        OBJECTS { hwConfigChangeIP, hw1588ClkInIndex, hwPtpGMClockID }
                        STATUS current
                        DESCRIPTION
                                "This trap generates when the identity of the 1588 GM clock changes."
                        ::= { hwClkCommonTrapsPrefix 1 }


                -- 1.3.6.1.4.1.2011.6.25.1.11.2.1.2
                hwClkTimeSourcePortIdentityTrap NOTIFICATION-TYPE
                        OBJECTS { hwConfigChangeIP, hw1588ClkInIndex, hwPtpParentClockID, hwPtpParentPortNumber }
                        STATUS current
                        DESCRIPTION
                                "This trap generates when the identity of the 1588 time source port changes."
                        ::= { hwClkCommonTrapsPrefix 2 }


                -- 1.3.6.1.4.1.2011.6.25.1.11.3
                hwClkAlarmTraps OBJECT IDENTIFIER ::= { hwClkTraps 3 }


                -- 1.3.6.1.4.1.2011.6.25.1.11.3.0
                hwClkAlarmTrapsPrefix OBJECT IDENTIFIER ::= { hwClkAlarmTraps 0 }


                -- 1.3.6.1.4.1.2011.6.25.1.11.3.0.1
                hwClksystemclocksourceswitchesTrap NOTIFICATION-TYPE
                        OBJECTS { hwFrameIndex, hwSlotIndex, hwClkInIndex, hwClkInIndex }
                        STATUS current
                        DESCRIPTION
                                "This trap generates when the system clock source switches to a new one."
                        ::= { hwClkAlarmTrapsPrefix 1 }


                -- 1.3.6.1.4.1.2011.6.25.1.11.3.0.2
                hwClkExternalInputSignalLoseTrap NOTIFICATION-TYPE
                        OBJECTS { hwFrameIndex, hwSlotIndex, hwClkInIndex }
                        STATUS current
                        DESCRIPTION
                                "This trap generates when the input signal of the external clock source was lost."
                        ::= { hwClkAlarmTrapsPrefix 2 }


                -- 1.3.6.1.4.1.2011.6.25.1.11.3.0.3
                hwClkExternalInputSignalRecoversTrap NOTIFICATION-TYPE
                        OBJECTS { hwFrameIndex, hwSlotIndex, hwClkInIndex }
                        STATUS current
                        DESCRIPTION
                                "This trap generates when the input signal of the external clock source recovers."
                        ::= { hwClkAlarmTrapsPrefix 3 }


                -- 1.3.6.1.4.1.2011.6.25.1.11.3.0.4
                hwClk1588ClockSrcSwitchTrap NOTIFICATION-TYPE
                        OBJECTS { hwFrameIndex, hwSlotIndex, hwClkInIndex, hwClkInIndex }
                        STATUS current
                        DESCRIPTION
                                "This trap generates when the 1588 clock source switches to a new one."
                        ::= { hwClkAlarmTrapsPrefix 4 }


                -- 1.3.6.1.4.1.2011.6.25.1.11.3.0.5
                hwClk1588ClockSrcLostTrap NOTIFICATION-TYPE
                        OBJECTS { hwFrameIndex, hwSlotIndex, hwClkInIndex }
                        STATUS current
                        DESCRIPTION
                                "This trap generates when the 1588 clock source was lost."
                        ::= { hwClkAlarmTrapsPrefix 5 }


                -- 1.3.6.1.4.1.2011.6.25.1.11.3.0.6
                hwClk1588ClockSrcRecoversTrap NOTIFICATION-TYPE
                        OBJECTS { hwFrameIndex, hwSlotIndex, hwClkInIndex }
                        STATUS current
                        DESCRIPTION
                                "This trap generates when the 1588 clock source recovers."
                        ::= { hwClkAlarmTrapsPrefix 6 }


                -- 1.3.6.1.4.1.2011.6.25.1.11.3.0.7
                hwClkSubcardWorkmodeSwitchesTrap NOTIFICATION-TYPE
                        OBJECTS { hwFrameIndex, hwSlotIndex, hwSubslotIndex, hw3rdClkOldSubBoardWorkMode, hw3rdClkSubBoardWorkMode
                                 }
                        STATUS current
                        DESCRIPTION
                                "This trap generates when the working mode of the clock sub-board has changed."
                        ::= { hwClkAlarmTrapsPrefix 7 }


                -- 1.3.6.1.4.1.2011.6.25.1.11.3.0.8
                hwClkNoTraceTrap NOTIFICATION-TYPE
                        OBJECTS { hwClkOutTypeTrapSn }
                        STATUS current
                        DESCRIPTION
                                "This trap generates when the working mode of the clock sub-board has changed to non-tracing mode."
                        ::= { hwClkAlarmTrapsPrefix 8 }


                -- 1.3.6.1.4.1.2011.6.25.1.11.3.0.9
                hwClkNoTraceRecoversTrap NOTIFICATION-TYPE
                        OBJECTS { hwClkOutTypeTrapSn }
                        STATUS current
                        DESCRIPTION
                                "This trap generates when the working mode of the clock sub-board has changed to tracing mode."
                        ::= { hwClkAlarmTrapsPrefix 9 }


                -- 1.3.6.1.4.1.2011.6.25.1.11.3.0.10
                hwClkEsmcLoseTrap NOTIFICATION-TYPE
                        OBJECTS { hwFrameIndex, hwSlotIndex, hwClkInIndex }
                        STATUS current
                        DESCRIPTION
                                "This trap generates when ESMC is lost."
                        ::= { hwClkAlarmTrapsPrefix 10 }


                -- 1.3.6.1.4.1.2011.6.25.1.11.3.0.11
                hwClkEsmcRestoreTrap NOTIFICATION-TYPE
                        OBJECTS { hwFrameIndex, hwSlotIndex, hwClkInIndex }
                        STATUS current
                        DESCRIPTION
                                "This trap generates when loss of ESMC recovers."
                        ::= { hwClkAlarmTrapsPrefix 11 }


                -- 1.3.6.1.4.1.2011.6.25.1.11.3.0.12
                hwClkQlChangeTrap NOTIFICATION-TYPE
                        OBJECTS { hwFrameIndex, hwSlotIndex, hwClkInIndex, hwClkInQL, hwClkInQL,
                                hwClkInQL }
                        STATUS current
                        DESCRIPTION
                                "This trap generates when the input QL of clock source changes."
                        ::= { hwClkAlarmTrapsPrefix 12 }


                -- 1.3.6.1.4.1.2011.6.25.1.11.3.0.13
                hwClkPtpLockFailTrap NOTIFICATION-TYPE
                        OBJECTS { hw1588ClkInIndex }
                        STATUS current
                        DESCRIPTION
                                "This trap generates when the lock state of ptp fail."
                        ::= { hwClkAlarmTrapsPrefix 13 }


                -- 1.3.6.1.4.1.2011.6.25.1.11.3.0.14
                hwClkPtpLockRecoverTrap NOTIFICATION-TYPE
                        OBJECTS { hw1588ClkInIndex }
                        STATUS current
                        DESCRIPTION
                                "This trap generates when the lock state of ptp recover."
                        ::= { hwClkAlarmTrapsPrefix 14 }


                -- 1.3.6.1.4.1.2011.6.25.1.11.3.0.15
                hwClkPtpAsymMeasureFailTrap NOTIFICATION-TYPE
                        OBJECTS { hwFrameIndex, hwSlotIndex, hwPortIndex, hwPtpTimeMeanpathdelayCur }
                        STATUS current
                        DESCRIPTION
                                "This trap generates when the result of asymmetry measure time offset is large than 55 ns."
                        ::= { hwClkAlarmTrapsPrefix 15 }


                -- 1.3.6.1.4.1.2011.6.25.1.11.3.0.16
                hwClkPtpAsymMeasureRestoreTrap NOTIFICATION-TYPE
                        OBJECTS { hwFrameIndex, hwSlotIndex, hwPortIndex, hwPtpTimeMeanpathdelayCur }
                        STATUS current
                        DESCRIPTION
                                "This trap generates when the asymmetry measure time offset is small than 55 ns."
                        ::= { hwClkAlarmTrapsPrefix 16 }
						
                -- 1.3.6.1.4.1.2011.6.25.1.11.3.0.17
                hwClkQlFailTrap NOTIFICATION-TYPE
                        OBJECTS { hwFrameIndex, hwSlotIndex, hwPortIndex, hwClkInQL, hwClkInQL }
                        STATUS current
                        DESCRIPTION
                                "This trap generates when the input QL of clock source less than the lower-limit."
                        ::= { hwClkAlarmTrapsPrefix 17 }
						
                -- 1.3.6.1.4.1.2011.6.25.1.11.3.0.18
                hwClkQlRestoreTrap NOTIFICATION-TYPE
                        OBJECTS { hwFrameIndex, hwSlotIndex, hwPortIndex, hwClkInQL, hwClkInQL }
                        STATUS current
                        DESCRIPTION
                                "This trap generates when the input QL of clock source recovers."
                        ::= { hwClkAlarmTrapsPrefix 18 }

                -- 1.3.6.1.4.1.2011.6.25.1.11.3.0.19
                hwClkOutExternalClosedTrap NOTIFICATION-TYPE
                        STATUS current
                        DESCRIPTION
                                "This trap generates when the output of external clock is closed"
                        ::= { hwClkAlarmTrapsPrefix 19 }
				
                -- 1.3.6.1.4.1.2011.6.25.1.11.3.0.20
                hwClkOutExternalOpenedTrap NOTIFICATION-TYPE
                        STATUS current
                        DESCRIPTION
                                "This trap generates when the output of external clock is opened."
                        ::= { hwClkAlarmTrapsPrefix 20 }
						
                -- 1.3.6.1.4.1.2011.6.25.1.12
                hw1588ACR OBJECT IDENTIFIER ::= { hwClkMibObjects 12 }


                -- 1.3.6.1.4.1.2011.6.25.1.12.1
                hw1588ACRMasterTable OBJECT-TYPE
                        SYNTAX SEQUENCE OF Hw1588ACRMasterEntry
                        MAX-ACCESS not-accessible
                        STATUS current
                        DESCRIPTION
                                "1588 ACR clock manage table.
                                The index of this table is master index.
                                "
                        ::= { hw1588ACR 1 }


                -- 1.3.6.1.4.1.2011.6.25.1.12.1.1
                hw1588ACRMasterEntry OBJECT-TYPE
                        SYNTAX Hw1588ACRMasterEntry
                        MAX-ACCESS not-accessible
                        STATUS current
                        DESCRIPTION
                                "1588 ACR clock manage table.
                                The index of this entry is master index.
                                "
                        INDEX { hw1588ACRMasterIndex }
                        ::= { hw1588ACRMasterTable 1 }


                Hw1588ACRMasterEntry ::=
                        SEQUENCE {
                                hw1588ACRMasterIndex
                                        Integer32,
                                hw1588ACRMasterIPAddr
                                        IpAddress,
                                hw1588ACRMasterNegotiate
                                        INTEGER,
                                hw1588ACRRowStatus
                                        RowStatus
                         }

                -- 1.3.6.1.4.1.2011.6.25.1.12.1.1.1
                hw1588ACRMasterIndex OBJECT-TYPE
                        SYNTAX Integer32 (1..2)
                        MAX-ACCESS read-write
                        STATUS current
                        DESCRIPTION
                                "Index of 1588 ACR master.
                                Range: 1 - 2
                                "
                        ::= { hw1588ACRMasterEntry 1 }


                -- 1.3.6.1.4.1.2011.6.25.1.12.1.1.2
                hw1588ACRMasterIPAddr OBJECT-TYPE
                        SYNTAX IpAddress
                        MAX-ACCESS read-write
                        STATUS current
                        DESCRIPTION
                                "1588 ACR master IP address"
                        ::= { hw1588ACRMasterEntry 2 }


                -- 1.3.6.1.4.1.2011.6.25.1.12.1.1.3
                hw1588ACRMasterNegotiate OBJECT-TYPE
                        SYNTAX INTEGER
                                {
                                idle(1),
                                negotiate(2)
                                }
                        MAX-ACCESS read-only
                        STATUS current
                        DESCRIPTION
                                "Port enabled type.
                                Options:
                                1. idle(1)     - the negotiate state is idle
                                2. negotiate(2)- the negotiate state is negotiate
                                "
                        ::= { hw1588ACRMasterEntry 3 }


                -- 1.3.6.1.4.1.2011.6.25.1.12.1.1.4
                hw1588ACRRowStatus OBJECT-TYPE
                        SYNTAX RowStatus
                        MAX-ACCESS read-create
                        STATUS current
                        DESCRIPTION
                                "Row status"
                        ::= { hw1588ACRMasterEntry 4 }


                -- 1.3.6.1.4.1.2011.6.25.1.12.2
                hw1588ACRManage OBJECT IDENTIFIER ::= { hw1588ACR 2 }


                -- 1.3.6.1.4.1.2011.6.25.1.12.2.1
                hw1588ACRNegotiateState OBJECT-TYPE
                        SYNTAX INTEGER
                                {
				negotiateOn(1),
				negotiateOff(2)
                                }
                        MAX-ACCESS read-create
                        STATUS current
                        DESCRIPTION
                                "The 1588 ACR negotiate state.
                                Options:
				1. negotiateOn(1)  - start negotiate
				2. negotiateOff(2) - stop negotiating
                                "
                        ::= { hw1588ACRManage 1 }


                -- 1.3.6.1.4.1.2011.6.25.1.12.2.2
                hw1588ACRDomain OBJECT-TYPE
                        SYNTAX Integer32 (0..255)
                        MAX-ACCESS read-write
                        STATUS current
                        DESCRIPTION
                                "The domain.
                                Range: 0-255
                                Default: 0
                                "
                        ::= { hw1588ACRManage 2 }


                -- 1.3.6.1.4.1.2011.6.25.1.12.2.3
                hw1588ACRAnnounceTimeout OBJECT-TYPE
                        SYNTAX Integer32 (2..255)
                        MAX-ACCESS read-write
                        STATUS current
                        DESCRIPTION
                                "The timeout times of rx announce packet.
                                Range: 2-255
                                Default: 3
                                "
                        ::= { hw1588ACRManage 3 }


                -- 1.3.6.1.4.1.2011.6.25.1.12.2.4
                hw1588ACRMsgFormat OBJECT-TYPE
                        SYNTAX INTEGER
                                {
                                ptpeth(1),
                                ptpip(2)
                                }
                        MAX-ACCESS read-create
                        STATUS current
                        DESCRIPTION
                                "PTPACR message encapsulation format,the default value is ptpeth(1).
                                Options:
                                1. ptpeth(1)  - indicates that the PTPACR message is encapsulated into an Ethernet packet
                                2. ptpip(2)   - indicates that the PTPACR message is encapsulated into an IP packet
                                "
                        ::= { hw1588ACRManage 4 }


                -- 1.3.6.1.4.1.2011.6.25.1.12.2.5
                hw1588ACRInfoMode OBJECT-TYPE
                        SYNTAX INTEGER
                                {
                                multicast(1),
                                unicast(2)
                                }
                        MAX-ACCESS read-create
                        STATUS current
                        DESCRIPTION
                                "PTPACR Info Mode,the default value is multicast(1).
                                Options:
                                1. multicast(1) - the 1588 ACR info mode is multicast.
                                2. unicast(2)  - the 1588 ACR info mode is unicast.
                                "
                        ::= { hw1588ACRManage 5 }


                -- 1.3.6.1.4.1.2011.6.25.1.12.2.6
                hw1588ACRReqSendTimeInterval OBJECT-TYPE
                        SYNTAX Integer32 (1..21)
                        MAX-ACCESS read-create
                        STATUS current
                        DESCRIPTION
                                "PTPACR req send time interval.
                                Options:
                                1. 1/1024s(1)  - indicates that the time interval is 1/1024s
                                2. 1/512s (2)  - indicates that the time interval is 1/512s
                                3. 1/256s (3)  - indicates that the time interval is 1/256s  .
                                4. 1/128s (4)  - indicates that the time interval is 1/128s  .
                                5. 1/64s  (5)  - indicates that the time interval is 1/64s
                                6. 1/32s  (6)  - indicates that the time interval is 1/32s
                                7. 1/16s  (7)  - indicates that the time interval is 1/16s
                                8. 1/8s   (8)  - indicates that the time interval is 1/8s
                                9. 1/4s   (9)  - indicates that the time interval is 1/4s
                                10.1/2s   (10) - indicates that the time interval is  1/2s
                                11.1s     (11) - indicates that the time interval is  1s
                                12.2s     (12) - indicates that the time interval is  2s
                                13.4s     (13) - indicates that the time interval is  4s
                                14.8s     (14) - indicates that the time interval is  8s
                                15.16s    (15) - indicates that the time interval is  16s
                                16.32s    (16) - indicates that the time interval is  32s
                                17.64s    (17) - indicates that the time interval is  64s
                                18.128s   (18) - indicates that the time interval is  128s
                                19.256s   (19) - indicates that the time interval is  256s
                                20.512s   (20) - indicates that the time interval is  512s
                                21.1024s  (21) - indicates that the time interval is  1024s
                                "
                        ::= { hw1588ACRManage 6 }


                -- 1.3.6.1.4.1.2011.6.25.1.12.2.7
                hw1588ACRSourceIp OBJECT-TYPE
                        SYNTAX IpAddress
                        MAX-ACCESS read-write
                        STATUS current
                        DESCRIPTION
                                "The IP address of local.
                                Default:0.0.0.0
                                "
                        ::= { hw1588ACRManage 7 }


                -- 1.3.6.1.4.1.2011.6.25.1.12.2.8
                hw1588ACRDSCP OBJECT-TYPE
                        SYNTAX Integer32 (0..63)
                        MAX-ACCESS read-write
                        STATUS current
                        DESCRIPTION
                                "The dscp of ip head.
                                Range: 0-63
                                Default: 56"
                        ::= { hw1588ACRManage 8 }


                -- 1.3.6.1.4.1.2011.6.25.1.12.2.9
                hw1588ACRVlan OBJECT-TYPE
                        SYNTAX Integer32 (0..4094)
                        MAX-ACCESS read-write
                        STATUS current
                        DESCRIPTION
                                "PTPACR VLAN: 0-4094"
                        ::= { hw1588ACRManage 9 }


                -- 1.3.6.1.4.1.2011.6.25.1.12.2.10
                hw1588ACRVlanPRI OBJECT-TYPE
                        SYNTAX Integer32 (0..7)
                        MAX-ACCESS read-write
                        STATUS current
                        DESCRIPTION
                                "PTPACR VLAN priority: 0-7"
                        ::= { hw1588ACRManage 10 }


                -- 1.3.6.1.4.1.2011.6.25.1.12.2.11
                hw1588ACRGlbEnable OBJECT-TYPE
                        SYNTAX INTEGER
                                {
                                disable(1),
                                enable(2)
                                }
                        MAX-ACCESS read-write
                        STATUS current
                        DESCRIPTION
                                "The switch of 1588ACR.
                                Options:
                                1.disable(1) - disable 1588ACR function
                                2.enable(2)  - enable 1588ACR function
                                Default: disable(1)
                                "
                        ::= { hw1588ACRManage 11 }


                -- 1.3.6.1.4.1.2011.6.25.1.12.2.12
                hw1588ACRDeviceType OBJECT-TYPE
                        SYNTAX INTEGER
                                {
                                client(1),
                                server(2)
                                }
                        MAX-ACCESS read-write
                        STATUS current
                        DESCRIPTION
                                "The running device type.
                                Options:
                                1.client(1) - running as client
                                2.server(2) - running as server
                                Default: client(1)
                                "
                        ::= { hw1588ACRManage 12 }


                -- 1.3.6.1.4.1.2011.6.25.1.12.2.13
                hw1588ACRVpnInstance OBJECT-TYPE
                        SYNTAX OCTET STRING (SIZE (1..31))
                        MAX-ACCESS read-write
                        STATUS current
                        DESCRIPTION
                                "VPN instance of 1588ACR using."
                        ::= { hw1588ACRManage 13 }


                -- 1.3.6.1.4.1.2011.6.25.1.12.2.14
                hw1588ACRAnnounceInterval OBJECT-TYPE
                        SYNTAX Integer32 (7..14)
                        MAX-ACCESS read-write
                        STATUS current
                        DESCRIPTION
                                "The interval of request for server tx announce packet.
                                Options:
                                1. 1/8s (7)  - indicates that the time interval is 1/8s
                                2. 1/4s (8)  - indicates that the time interval is 1/4s
                                3. 1/2s (9)  - indicates that the time interval is  1/2s
                                4. 1s   (10) - indicates that the time interval is  1s
                                5. 2s   (11) - indicates that the time interval is  2s
                                6. 4s   (12) - indicates that the time interval is  4s
                                7. 8s   (13) - indicates that the time interval is  8s
                                8. 16s  (14) - indicates that the time interval is  16s
                                Default: 11
                                "
                        ::= { hw1588ACRManage 14 }


                -- 1.3.6.1.4.1.2011.6.25.1.12.2.15
                hw1588ACRSyncInterval OBJECT-TYPE
                        SYNTAX Integer32 (3..14)
                        MAX-ACCESS read-write
                        STATUS current
                        DESCRIPTION
                                "The interval of request for server tx sync packet.
                                Options:
                                1.  1/128s (3)  - indicates that the time interval is 1/128s
                                2.  1/64s  (4)  - indicates that the time interval is 1/64s
                                3.  1/32s  (5)  - indicates that the time interval is 1/32s
                                4.  1/16s  (6)  - indicates that the time interval is 1/16s
                                5.  1/8s   (7)  - indicates that the time interval is 1/8s
                                6.  1/4s   (8)  - indicates that the time interval is 1/4s
                                7.  1/2s   (9)  - indicates that the time interval is  1/2s
                                8.  1s     (10) - indicates that the time interval is  1s
                                9.  2s     (11) - indicates that the time interval is  2s
                                10. 4s     (12) - indicates that the time interval is  4s
                                11. 8s     (13) - indicates that the time interval is  8s
                                12. 16s    (14) - indicates that the time interval is  16s
                                Default: 3
                                "
                        ::= { hw1588ACRManage 15 }


                -- 1.3.6.1.4.1.2011.6.25.1.12.2.16
                hw1588ACRDelayRespInterval OBJECT-TYPE
                        SYNTAX Integer32 (3..14)
                        MAX-ACCESS read-write
                        STATUS current
                        DESCRIPTION
                                "The interval of request for server tx delay response packet.
                                Options:
                                1.  1/128s (3)  - indicates that the time interval is 1/128s
                                2.  1/64s  (4)  - indicates that the time interval is 1/64s
                                3.  1/32s  (5)  - indicates that the time interval is 1/32s
                                4.  1/16s  (6)  - indicates that the time interval is 1/16s
                                5.  1/8s   (7)  - indicates that the time interval is 1/8s
                                6.  1/4s   (8)  - indicates that the time interval is 1/4s
                                7.  1/2s   (9)  - indicates that the time interval is  1/2s
                                8.  1s     (10) - indicates that the time interval is  1s
                                9.  2s     (11) - indicates that the time interval is  2s
                                10. 4s     (12) - indicates that the time interval is  4s
                                11. 8s     (13) - indicates that the time interval is  8s
                                12. 16s    (14) - indicates that the time interval is  16s
                                Default: 3
                                "
                        ::= { hw1588ACRManage 16 }


                -- 1.3.6.1.4.1.2011.6.25.1.12.2.17
                hw1588ACRAnnounceDuration OBJECT-TYPE
                        SYNTAX Integer32 (60..1000)
                        MAX-ACCESS read-write
                        STATUS current
                        DESCRIPTION
                                "The timeout time of announce renegotiation.
				Range: 60-1000 -- 60s-1000s
				Default: 300   -- 300s
                                "
                        ::= { hw1588ACRManage 17 }


                -- 1.3.6.1.4.1.2011.6.25.1.12.2.18
                hw1588ACRSyncDuration OBJECT-TYPE
                        SYNTAX Integer32 (60..1000)
                        MAX-ACCESS read-write
                        STATUS current
                        DESCRIPTION
                                "The timeout time of sync renegotiation.
				Range: 60-1000  -- 60s-1000s
				Default: 300    -- 300s
                                "
                        ::= { hw1588ACRManage 18 }


                -- 1.3.6.1.4.1.2011.6.25.1.12.2.19
                hw1588ACRDelayRespDuration OBJECT-TYPE
                        SYNTAX Integer32 (60..1000)
                        MAX-ACCESS read-write
                        STATUS current
                        DESCRIPTION
                                "The timeout time of delay response renegotiation.
				Range: 60-1000  -- 60s-1000s
				Default: 300    -- 300s
				"
                        ::= { hw1588ACRManage 19 }


                -- 1.3.6.1.4.1.2011.6.25.1.12.2.20
                hw1588ACRNegoMode OBJECT-TYPE
                        SYNTAX INTEGER
                                {
				oneWay(1),
				twoWay(2)
                                }
                        MAX-ACCESS read-write
                        STATUS current
                        DESCRIPTION
                                "The negotiation mode.
                                Options:
				1.oneWay(1) - one way   
				2.twoWay(2) - two way
				Default: oneWay(1)
                                "
                        ::= { hw1588ACRManage 20 }


                -- 1.3.6.1.4.1.2011.6.25.1.12.2.21
                hw1588ACRNegoEnable OBJECT-TYPE
                        SYNTAX INTEGER
                                {
                                disable(1),
                                enable(2)
                                }
                        MAX-ACCESS read-write
                        STATUS current
                        DESCRIPTION
                                "The switch of 1588ACR negotiation.
                                Options:
                                1.disable(1) - disable 1588ACR negotiation
                                2.enable(2)  - enable 1588ACR negotiation
                                Default: disable(1)
                                "
                        ::= { hw1588ACRManage 21 }


                -- 1.3.6.1.4.1.2011.6.25.1.12.2.22
                hw1588ACRTraceSourceId OBJECT-TYPE
                        SYNTAX INTEGER
                                {
                                local(1),
                                server1(2),
                                server2(3)
                                }
                        MAX-ACCESS read-only
                        STATUS current
                        DESCRIPTION
                                "The trace source server ID.
                                Options:
                                1.local(1)   - no trace source
                                2.server1(2) - server1
                                3.server2(3) - server2
                                "
                        ::= { hw1588ACRManage 22 }


                -- 1.3.6.1.4.1.2011.6.25.1.12.3
                hw1588ACRDfx OBJECT IDENTIFIER ::= { hw1588ACR 3 }


                -- 1.3.6.1.4.1.2011.6.25.1.12.3.1
                hw1588ACRDfxPosMinPdCur OBJECT-TYPE
                        SYNTAX Integer32
                        MAX-ACCESS read-only
                        STATUS current
                        DESCRIPTION
                                "The current positive min packet delay.
                                "
                        ::= { hw1588ACRDfx 1 }


                -- 1.3.6.1.4.1.2011.6.25.1.12.3.2
                hw1588ACRDfxPosMinPdMin OBJECT-TYPE
                        SYNTAX Integer32
                        MAX-ACCESS read-only
                        STATUS current
                        DESCRIPTION
                                "The min positive min packet delay.
                                "
                        ::= { hw1588ACRDfx 2 }


                -- 1.3.6.1.4.1.2011.6.25.1.12.3.3
                hw1588ACRDfxPosMinPdMax OBJECT-TYPE
                        SYNTAX Integer32
                        MAX-ACCESS read-only
                        STATUS current
                        DESCRIPTION
                                "The max positive min packet delay.
                                "
                        ::= { hw1588ACRDfx 3 }


                -- 1.3.6.1.4.1.2011.6.25.1.12.3.4
                hw1588ACRDfxPosMinPdMean OBJECT-TYPE
                        SYNTAX Integer32
                        MAX-ACCESS read-only
                        STATUS current
                        DESCRIPTION
                                "The mean positive min packet delay.
                                "
                        ::= { hw1588ACRDfx 4 }


                -- 1.3.6.1.4.1.2011.6.25.1.12.3.5
                hw1588ACRDfxPosMinPdv OBJECT-TYPE
                        SYNTAX Integer32
                        MAX-ACCESS read-only
                        STATUS current
                        DESCRIPTION
                                "The positive min packet delay variation.
                                "
                        ::= { hw1588ACRDfx 5 }


                -- 1.3.6.1.4.1.2011.6.25.1.12.3.6
                hw1588ACRDfxPosMaxPdCur OBJECT-TYPE
                        SYNTAX Integer32
                        MAX-ACCESS read-only
                        STATUS current
                        DESCRIPTION
                                "The current positive max packet delay.
                                "
                        ::= { hw1588ACRDfx 6 }


                -- 1.3.6.1.4.1.2011.6.25.1.12.3.7
                hw1588ACRDfxPosMaxPdMin OBJECT-TYPE
                        SYNTAX Integer32
                        MAX-ACCESS read-only
                        STATUS current
                        DESCRIPTION
                                "The min positive max packet delay.
                                "
                        ::= { hw1588ACRDfx 7 }


                -- 1.3.6.1.4.1.2011.6.25.1.12.3.8
                hw1588ACRDfxPosMaxPdMax OBJECT-TYPE
                        SYNTAX Integer32
                        MAX-ACCESS read-only
                        STATUS current
                        DESCRIPTION
                                "The max positive max packet delay.
                                "
                        ::= { hw1588ACRDfx 8 }


                -- 1.3.6.1.4.1.2011.6.25.1.12.3.9
                hw1588ACRDfxPosMaxPdMean OBJECT-TYPE
                        SYNTAX Integer32
                        MAX-ACCESS read-only
                        STATUS current
                        DESCRIPTION
                                "The mean positive max packet delay.
                                "
                        ::= { hw1588ACRDfx 9 }


                -- 1.3.6.1.4.1.2011.6.25.1.12.3.10
                hw1588ACRDfxPosMaxPdv OBJECT-TYPE
                        SYNTAX Integer32
                        MAX-ACCESS read-only
                        STATUS current
                        DESCRIPTION
                                "The positive max packet delay variation.
                                "
                        ::= { hw1588ACRDfx 10 }


                -- 1.3.6.1.4.1.2011.6.25.1.12.3.11
                hw1588ACRDfxNegMinPdCur OBJECT-TYPE
                        SYNTAX Integer32
                        MAX-ACCESS read-only
                        STATUS current
                        DESCRIPTION
                                "The current negative min packet delay.
                                "
                        ::= { hw1588ACRDfx 11 }


                -- 1.3.6.1.4.1.2011.6.25.1.12.3.12
                hw1588ACRDfxNegMinPdMin OBJECT-TYPE
                        SYNTAX Integer32
                        MAX-ACCESS read-only
                        STATUS current
                        DESCRIPTION
                                "The min negative min packet delay.
                                "
                        ::= { hw1588ACRDfx 12 }


                -- 1.3.6.1.4.1.2011.6.25.1.12.3.13
                hw1588ACRDfxNegMinPdMax OBJECT-TYPE
                        SYNTAX Integer32
                        MAX-ACCESS read-only
                        STATUS current
                        DESCRIPTION
                                "The max negative min packet delay.
                                "
                        ::= { hw1588ACRDfx 13 }


                -- 1.3.6.1.4.1.2011.6.25.1.12.3.14
                hw1588ACRDfxNegMinPdMean OBJECT-TYPE
                        SYNTAX Integer32
                        MAX-ACCESS read-only
                        STATUS current
                        DESCRIPTION
                                "The mean negative min packet delay.
                                "
                        ::= { hw1588ACRDfx 14 }


                -- 1.3.6.1.4.1.2011.6.25.1.12.3.15
                hw1588ACRDfxNegMinPdv OBJECT-TYPE
                        SYNTAX Integer32
                        MAX-ACCESS read-only
                        STATUS current
                        DESCRIPTION
                                "The negative min packet delay variation.
                                "
                        ::= { hw1588ACRDfx 15 }


                -- 1.3.6.1.4.1.2011.6.25.1.12.3.16
                hw1588ACRDfxNegMaxPdCur OBJECT-TYPE
                        SYNTAX Integer32
                        MAX-ACCESS read-only
                        STATUS current
                        DESCRIPTION
                                "The current negative max packet delay.
                                "
                        ::= { hw1588ACRDfx 16 }


                -- 1.3.6.1.4.1.2011.6.25.1.12.3.17
                hw1588ACRDfxNegMaxPdMin OBJECT-TYPE
                        SYNTAX Integer32
                        MAX-ACCESS read-only
                        STATUS current
                        DESCRIPTION
                                "The min negative max packet delay.
                                "
                        ::= { hw1588ACRDfx 17 }


                -- 1.3.6.1.4.1.2011.6.25.1.12.3.18
                hw1588ACRDfxNegMaxPdMax OBJECT-TYPE
                        SYNTAX Integer32
                        MAX-ACCESS read-only
                        STATUS current
                        DESCRIPTION
                                "The max negative max packet delay.
                                "
                        ::= { hw1588ACRDfx 18 }


                -- 1.3.6.1.4.1.2011.6.25.1.12.3.19
                hw1588ACRDfxNegMaxPdMean OBJECT-TYPE
                        SYNTAX Integer32
                        MAX-ACCESS read-only
                        STATUS current
                        DESCRIPTION
                                "The mean negative max packet delay.
                                "
                        ::= { hw1588ACRDfx 19 }


                -- 1.3.6.1.4.1.2011.6.25.1.12.3.20
                hw1588ACRDfxNegMaxPdv OBJECT-TYPE
                        SYNTAX Integer32
                        MAX-ACCESS read-only
                        STATUS current
                        DESCRIPTION
                                "The negative max packet delay variation.
                                "
                        ::= { hw1588ACRDfx 20 }


                -- 1.3.6.1.4.1.2011.6.25.1.12.4
                hw1588ACRServerTable OBJECT-TYPE
                        SYNTAX SEQUENCE OF Hw1588ACRServerEntry
                        MAX-ACCESS not-accessible
                        STATUS current
                        DESCRIPTION
                                "1588ACR server management table.
                                The index of this table is server index.
                                "
                        ::= { hw1588ACR 4 }


                -- 1.3.6.1.4.1.2011.6.25.1.12.4.1
                hw1588ACRServerEntry OBJECT-TYPE
                        SYNTAX Hw1588ACRServerEntry
                        MAX-ACCESS not-accessible
                        STATUS current
                        DESCRIPTION
                                "1588ACR server management table.
                                The index of this entry is server index.
                                "
                        INDEX { hw1588ACRServerIndex }
                        ::= { hw1588ACRServerTable 1 }


                Hw1588ACRServerEntry ::=
                        SEQUENCE {
                                hw1588ACRServerIndex
                                        Integer32,
                                hw1588ACRServerIpAddr
                                        IpAddress,
                                hw1588ACRServerNegoStatus
                                        INTEGER,
                                hw1588ACRServerSsm
                                        INTEGER,
                                hw1588ACRServerPriority
                                        Integer32,
                                hw1588ACRServerPTSFLossAnnounce
                                        INTEGER,
                                hw1588ACRServerPTSFLossSync
                                        INTEGER,
                                hw1588ACRServerPTSFLossDelayResp
                                        INTEGER
                         }

                -- 1.3.6.1.4.1.2011.6.25.1.12.4.1.1
                hw1588ACRServerIndex OBJECT-TYPE
                        SYNTAX Integer32 (1..2)
                        MAX-ACCESS read-only
                        STATUS current
                        DESCRIPTION
                                "The server index.
                                Range: 1-2
                                "
                        ::= { hw1588ACRServerEntry 1 }


                -- 1.3.6.1.4.1.2011.6.25.1.12.4.1.2
                hw1588ACRServerIpAddr OBJECT-TYPE
                        SYNTAX IpAddress
                        MAX-ACCESS read-write
                        STATUS current
                        DESCRIPTION
                                "The IP address of server."
                        ::= { hw1588ACRServerEntry 2 }


                -- 1.3.6.1.4.1.2011.6.25.1.12.4.1.3
                hw1588ACRServerNegoStatus OBJECT-TYPE
                        SYNTAX INTEGER
                                {
                                init(1),
                                success(2),
                                failed(3)
                                }
                        MAX-ACCESS read-only
                        STATUS current
                        DESCRIPTION
                                "The status of negotiation.
                                Options:
                                1. init(1)    - no enable negotiation
                                2. success(2) - negotiate succesfully
                                3. failed(3)  - negotiate failed
                                "
                        ::= { hw1588ACRServerEntry 3 }


                -- 1.3.6.1.4.1.2011.6.25.1.12.4.1.4
                hw1588ACRServerSsm OBJECT-TYPE
                        SYNTAX INTEGER
                                {
                                prc(2),
                                ssua(4),
                                ssub(8),
                                sec(11),
                                dnu(15)
                                }
                        MAX-ACCESS read-only
                        STATUS current
                        DESCRIPTION
                                "The quality level.
				Options:
				1. prc(2)  - prc
				2. ssua(4) - ssua
				3. ssub(8) - ssub
				4. sec(11) - sec
				5. dnu(15) - dnu



                                "
                        ::= { hw1588ACRServerEntry 4 }


                -- 1.3.6.1.4.1.2011.6.25.1.12.4.1.5
                hw1588ACRServerPriority OBJECT-TYPE
                        SYNTAX Integer32
                        MAX-ACCESS read-only
                        STATUS current
                        DESCRIPTION
                                "The priority.
                                "
                        ::= { hw1588ACRServerEntry 5 }


                -- 1.3.6.1.4.1.2011.6.25.1.12.4.1.6
                hw1588ACRServerPTSFLossAnnounce OBJECT-TYPE
                        SYNTAX INTEGER
                                {
                                normal(1),
                                failed(2),
                                none(255)
                                }
                        MAX-ACCESS read-only
                        STATUS current
                        DESCRIPTION
                                "The announce PTSF status.
                                Options:
                                1. normal(1)   - status is normal
                                2. failed(2)   - status is abnormal
                                3. none(255)   - not referenced"
                        ::= { hw1588ACRServerEntry 6 }


                -- 1.3.6.1.4.1.2011.6.25.1.12.4.1.7
                hw1588ACRServerPTSFLossSync OBJECT-TYPE
                        SYNTAX INTEGER
                                {
                                normal(1),
                                failed(2),
                                none(255)
                                }
                        MAX-ACCESS read-only
                        STATUS current
                        DESCRIPTION
                                "The sync PTSF status.
                                Options:
                                1. normal(1)   - status is normal
                                2. failed(2)   - status is abnormal
                                3. none(255)   - not referenced"
                        ::= { hw1588ACRServerEntry 7 }


                -- 1.3.6.1.4.1.2011.6.25.1.12.4.1.8
                hw1588ACRServerPTSFLossDelayResp OBJECT-TYPE
                        SYNTAX INTEGER
                                {
                                normal(1),
                                failed(2),
                                none(255)
                                }
                        MAX-ACCESS read-only
                        STATUS current
                        DESCRIPTION
                                "The delay response PTSF status.
                                Options:
                                1. normal(1)   - status is normal
                                2. failed(2)   - status is abnormal
                                3. none(255)   - not referenced"
                        ::= { hw1588ACRServerEntry 8 }



        END

--
-- HUAWEI-CLK-MIB.MIB
--
