-- ============================================================================
-- Copyright (C) 2014 by  HUAWEI TECHNOLOGIES. All rights reserved.
-- Description: This mib is used for querying the statistics of an Ethernet port.
-- Reference:  
-- Version: V1.20
-- ============================================================================
  HUAWEI-RMON-MIB DEFINITIONS ::= BEGIN
   
    IMPORTS
      OBJECT-TYPE,Counter32,Counter64,MODULE-IDENTITY
        FROM SNMPv2-SMI
      etherStatsTable, etherStatsIndex, etherStatsEntry
        FROM RMON-MIB 
      ifIndex     
                  FROM IF-MIB         
      hwEthernetPort  
          FROM  HUAWEI-MIB;
          
    hwExtInterface MODULE-IDENTITY
      LAST-UPDATED "201406290000Z"
      ORGANIZATION "Huawei Technologies Co.,Ltd."
      CONTACT-INFO                                        
                   "Huawei Industrial Base                
                    Bantian, Longgang                     
                    Shenzhen 518129                       
                    People's Republic of China            
                    Website: http://www.huawei.com        
                    Email: support@huawei.com             
                   "                                      
      DESCRIPTION                             
        "This mib is used for querying the statistics of an Ethernet port.
        "
        
--  Revision history 
      REVISION     "201406290000Z" 
      DESCRIPTION  "V1.01, Modify the ORGANIZATION to satisfy for the new OMSYS tool."
	    
      REVISION     "201204170900Z"     
      DESCRIPTION  "V1.19, add the following leaves into hwEtherStatsInfoTable:
                        hwEtherStatsAlignErrors                 
                        hwEtherStatsTotalUnicastPkts                  
                        hwEtherStatsTotalOctets.                       
                        modified the following leaves into hwEtherStatsInfoTable:
                        hwEtherStatsRxPkts                 
                        hwEtherStatsRxBroadcastPkts                  
                        hwEtherStatsRxMulticastPkts                     
                        hwEtherStatsTotalPkts                 
                        hwEtherStatsTotalUnicastPkts                  
                        hwEtherStatsTotalBroadcastPkts
                        hwEtherStatsRecvOctetsInfo
                        hwEtherStatsDownDiscardPacketsInfo
                        hwEtherStatsUpDiscardPacketsInfo
                        modified the description of MIB. 
                   " 
        
      REVISION     "201203160900Z"     
      DESCRIPTION  "V1.18, modified the description of MIB. "

      REVISION     "201202090900Z"     
      DESCRIPTION  "V1.17, add the following leaves into hwEtherStatsInfoTable:
                        hwEtherStatsTxPkts                 
                        hwEtherStatsRxPkts                 
                        hwEtherStatsRxBroadcastPkts        
                        hwEtherStatsTxBroadcastPkts        
                        hwEtherStatsRxMulticastPkts        
                        hwEtherStatsTxMulticastPkts        
                        hwEtherStatsRxUndersizePkts        
                        hwEtherStatsRxOversizePkts         
                        hwEtherStatsTxCollisionPkts        
                        hwEtherStatsDiscardedUndersizedPkts
                        hwEtherStatsTxUndersizedPkts       
                        hwEtherStatsTxFragmentsPkts        
                        hwEtherStatsRxFragmentsPkts        
                        hwEtherStatsTxJabbers              
                        hwEtherStatsRxJabbers              
                        hwEtherStatsTxOversizedPkts        
                        hwEtherStatsRx64octetsPkts         
                        hwEtherStatsTx64octetsPkts         
                        hwEtherStatsRx65to127octetsPkts    
                        hwEtherStatsTx65to127octetsPkts    
                        hwEtherStatsRx128to255octetsPkts   
                        hwEtherStatsTx128to255octetsPkts   
                        hwEtherStatsRx256to511octetsPkts   
                        hwEtherStatsTx256to511octetsPkts   
                        hwEtherStatsRx512to1023octetsPkts  
                        hwEtherStatsTx512to1023octetsPkts  
                        hwEtherStatsRx1024to1518octetsPkts 
                        hwEtherStatsTx1024to1518octetsPkts 
                        hwEtherStatsTxErrorPkts            
                        hwEtherStatsRxErrorPkts            
                        hwEtherStatsTxCRCErrorPkts. 
                    "   
                        
      REVISION     "201107090900Z"     
      DESCRIPTION  "V1.16, add the following leaves into hwEtherStatsInfoTable:
                        hwEtherStatsSendGreenOctets
                        hwEtherStatsSendGreenPkts
                        hwEtherStatsDiscardGreenPkts
                        hwEtherStatsSendYellowOctets
                        hwEtherStatsSendYellowPkts
                        hwEtherStatsDiscardYellowPkts. 
                    "
      
      REVISION     "201011090900Z"     
      DESCRIPTION  "V1.15, modified the description of MIB. "
      
      REVISION     "201010090900Z"     
      DESCRIPTION  "V1.14, modified the description of MIB. "
            
      REVISION     "201009100900Z"
      DESCRIPTION  "V1.13, modified the syntax from Counter32 to Counter64 for the leaves below:
                  hwEtherStatsPktsRecvPauseInfo
                  hwEtherStatsPktsSendPauseInfo
                  hwEtherStatsPkts1519to2047OctetsInfo
                  hwEtherStatsPkts2048to4095OctetsInfo
                  hwEtherStatsPkts4096to9216OctetsInfo
                  hwEtherStatsRecvOctetsInfo
                  hwEtherStatsSendOctetsInfo
                  hwEtherStatsPktsSendSingleCollisionInfo
                  hwEtherStatsPktsSendMultiCollisionInfo
                  hwEtherStatsUpDiscardPacketsInfo
                  hwEtherStatsDownDiscardPacketsInfo
                  hwEtherStatsAlignmentErrorFramesInfo
                  hwEtherStatsDropEvents
                  hwEtherStatsOctets
                  hwEtherStatsPkts
                  hwEtherStatsBroadcastPkts
                  hwEtherStatsMulticastPkts
                  hwEtherStatsCRCAlignErrors
                  hwEtherStatsUndersizePkts
                  hwEtherStatsOversizePkts
                  hwEtherStatsFragments
                  hwEtherStatsJabbers
                  hwEtherStatsCollisions
                  hwEtherStatsPkts64Octets
                  hwEtherStatsPkts65to127Octets
                  hwEtherStatsPkts128to255Octets
                  hwEtherStatsPkts256to511Octets
                  hwEtherStatsPkts512to1023Octets
                  hwEtherStatsPkts1024to1518Octets
                  hwEtherStatsReceiveUnicastPacketsInfo
                  hwEtherStatsSendUnicastPacketsInfo.
                  "
                
      REVISION     "201007050900Z"
      DESCRIPTION  "V1.12, corrected the names of hwetherStatsInfoTable and hwetherStatsInfoEntry to hwEtherStatsInfoTable and hwEtherStatsInfoEntry.
                    Added leaves into hwEtherStatsInfoTable according to etherStatsTable.
                    The mapping relation between hwEtherStatsInfoTable and etherStatsTable is as follows:
                        hwEtherStatsDropEvents            <==>  etherStatsDropEvents            
                        hwEtherStatsOctets                <==>  etherStatsOctets                
                        hwEtherStatsPkts                  <==>  etherStatsPkts                  
                        hwEtherStatsBroadcastPkts         <==>  etherStatsBroadcastPkts         
                        hwEtherStatsMulticastPkts         <==>  etherStatsMulticastPkts         
                        hwEtherStatsCRCAlignErrors        <==>  etherStatsCRCAlignErrors        
                        hwEtherStatsUndersizePkts         <==>  etherStatsUndersizePkts         
                        hwEtherStatsOversizePkts          <==>  etherStatsOversizePkts          
                        hwEtherStatsFragments             <==>  etherStatsFragments             
                        hwEtherStatsJabbers               <==>  etherStatsJabbers               
                        hwEtherStatsCollisions            <==>  etherStatsCollisions            
                        hwEtherStatsPkts64Octets          <==>  etherStatsPkts64Octets          
                        hwEtherStatsPkts65to127Octets     <==>  etherStatsPkts65to127Octets     
                        hwEtherStatsPkts128to255Octets    <==>  etherStatsPkts128to255Octets    
                        hwEtherStatsPkts256to511Octets    <==>  etherStatsPkts256to511Octets    
                        hwEtherStatsPkts512to1023Octets   <==>  etherStatsPkts512to1023Octets   
                        hwEtherStatsPkts1024to1518Octets  <==>  etherStatsPkts1024to1518Octets
                        
                    Deleted the following leaves:
                        hwEtherStatsPktsRecvPause
                        hwEtherStatsPktsSendPause
                        hwEtherStatsPkts1519to2047Octets
                        hwEtherStatsPkts2048to4095Octets
                        hwEtherStatsPkts4096to9216Octets
                        hwEtherStatsRecvOctets
                        hwEtherStatsSendOctets
                        hwEtherStatsPktsSendSingleCollision
                        hwEtherStatsPktsSendMultiCollision
                        hwEtherStatsUpDiscardPackets
                        hwEtherStatsDownDiscardPackets
                    Modified the descriptions of mib.
                    "
      
      REVISION     "201005050900Z"
      DESCRIPTION  "V1.11, modified the errors of the MIB file."      
      
      REVISION     "201004270000Z"
      DESCRIPTION  "V1.10, added hwEtherStatsPortStateChange in hwetherStatsInfoTable."
                  
      REVISION     "201003050000Z"
      DESCRIPTION  "V1.09, added hwEtherStatsAlignmentErrorFramesInfo in hwetherStatsInfoTable."
      
      REVISION     "201001280000Z"
      DESCRIPTION  "V1.08, added hwEtherStatsReceiveUnicastPackets, hwEtherStatsSendUnicastPackets in etherStatsTable."      
                  
      REVISION     "200912280000Z"
      DESCRIPTION  "V1.06, added Huawei private leaf node."
          
      REVISION     "200805310000Z"
      DESCRIPTION  "V1.05, deleted Chinese character."
                    
      REVISION     "200804240000Z"
      DESCRIPTION  "V1.04, added hwEtherStatsUpDiscardPackets, hwEtherStatsDownDiscardPackets in etherStatsTable."
    
      REVISION     "200611270000Z"        
      DESCRIPTION  "V1.01, added hwEtherStatsPkts1519to2047Octets, hwEtherStatsPkts2048to4095Octets,
                    hwEtherStatsPkts4096to9216Octets in etherStatsTable."
                
      REVISION     "200611240000Z"        
      DESCRIPTION  "V1.00, initial version."        
        
      ::= { hwEthernetPort 2 }

-- hwEtherStatsInfoTable

     hwEtherStatsInfoTable OBJECT-TYPE
       SYNTAX SEQUENCE OF HwEtherStatsInfoEntry
       MAX-ACCESS not-accessible
       STATUS current
       DESCRIPTION 
         "Indicates the statistics table of an Ethernet port. It is used for querying the
          extended performance statistics of Ethernet ports of Huawei.
          The index of this table is ifIndex.
          "
       ::= { hwExtInterface 8 }
       
     hwEtherStatsInfoEntry OBJECT-TYPE
       SYNTAX HwEtherStatsInfoEntry
       MAX-ACCESS not-accessible
       STATUS current
       DESCRIPTION 
         "Indicates the statistics table of an Ethernet port. It is used for querying the
          extended performance statistics of Ethernet ports of Huawei.
          The index of this entry is ifIndex.
          "
       INDEX { ifIndex }
       ::= { hwEtherStatsInfoTable 1 }  
    
     HwEtherStatsInfoEntry ::= 
       SEQUENCE {
           hwEtherStatsPktsRecvPauseInfo                     Counter64,
           hwEtherStatsPktsSendPauseInfo                     Counter64,
           hwEtherStatsPkts1519to2047OctetsInfo              Counter64,
           hwEtherStatsPkts2048to4095OctetsInfo              Counter64,
           hwEtherStatsPkts4096to9216OctetsInfo              Counter64,
           hwEtherStatsRecvOctetsInfo                        Counter64,
           hwEtherStatsSendOctetsInfo                        Counter64,
           hwEtherStatsPktsSendSingleCollisionInfo           Counter64,
           hwEtherStatsPktsSendMultiCollisionInfo            Counter64,
           hwEtherStatsUpDiscardPacketsInfo                  Counter64,
           hwEtherStatsDownDiscardPacketsInfo                Counter64,
           hwEtherStatsAlignmentErrorFramesInfo              Counter64,
           hwEtherStatsPortStateChange                       Counter32,
           hwEtherStatsDropEvents                            Counter64,
           hwEtherStatsOctets                                Counter64,
           hwEtherStatsRxPkts                                  Counter64,
           hwEtherStatsRxBroadcastPkts                         Counter64,
           hwEtherStatsRxMulticastPkts                         Counter64,
           hwEtherStatsCRCAlignErrors                        Counter64,
           hwEtherStatsUndersizePkts                         Counter64,
           hwEtherStatsOversizePkts                          Counter64,
           hwEtherStatsFragments                             Counter64,
           hwEtherStatsJabbers                               Counter64,
           hwEtherStatsCollisions                            Counter64,
           hwEtherStatsPkts64Octets                          Counter64,
           hwEtherStatsPkts65to127Octets                     Counter64,
           hwEtherStatsPkts128to255Octets                    Counter64,
           hwEtherStatsPkts256to511Octets                    Counter64,
           hwEtherStatsPkts512to1023Octets                   Counter64,
           hwEtherStatsPkts1024to1518Octets                  Counter64,
           hwEtherStatsReceiveUnicastPacketsInfo             Counter64,
           hwEtherStatsSendUnicastPacketsInfo                Counter64,
           hwEtherStatsSendGreenOctets                       Counter64,
           hwEtherStatsSendGreenPkts                         Counter64,
           hwEtherStatsDiscardGreenPkts                      Counter64,       
           hwEtherStatsSendYellowOctets                      Counter64,
           hwEtherStatsSendYellowPkts                        Counter64,
           hwEtherStatsDiscardYellowPkts                     Counter64,
           hwEtherStatsTxPkts                                Counter64,
           hwEtherStatsTotalPkts                                Counter64,
           hwEtherStatsTotalBroadcastPkts                       Counter64,
           hwEtherStatsTxBroadcastPkts                       Counter64,
           hwEtherStatsTotalMulticastPkts                       Counter64,
           hwEtherStatsTxMulticastPkts                       Counter64,
           hwEtherStatsRxUndersizePkts                       Counter64,
           hwEtherStatsRxOversizePkts                        Counter64,
           hwEtherStatsTxCollisionPkts                       Counter64,
           hwEtherStatsDiscardedUndersizedPkts               Counter64,
           hwEtherStatsTxUndersizedPkts                      Counter64,
           hwEtherStatsTxFragmentsPkts                       Counter64,
           hwEtherStatsRxFragmentsPkts                       Counter64,
           hwEtherStatsTxJabbers                             Counter64,
           hwEtherStatsRxJabbers                             Counter64,
           hwEtherStatsTxOversizedPkts                       Counter64,
           hwEtherStatsRx64octetsPkts                        Counter64,
           hwEtherStatsTx64octetsPkts                        Counter64,
           hwEtherStatsRx65to127octetsPkts                   Counter64,
           hwEtherStatsTx65to127octetsPkts                   Counter64,
           hwEtherStatsRx128to255octetsPkts                  Counter64,
           hwEtherStatsTx128to255octetsPkts                  Counter64,
           hwEtherStatsRx256to511octetsPkts                  Counter64,
           hwEtherStatsTx256to511octetsPkts                  Counter64,
           hwEtherStatsRx512to1023octetsPkts                 Counter64,
           hwEtherStatsTx512to1023octetsPkts                 Counter64,
           hwEtherStatsRx1024to1518octetsPkts                Counter64,
           hwEtherStatsTx1024to1518octetsPkts                Counter64,
           hwEtherStatsTxErrorPkts                           Counter64,
           hwEtherStatsRxErrorPkts                           Counter64,
           hwEtherStatsTxCRCErrorPkts                        Counter64,
           hwEtherStatsAlignErrors                           Counter64,
           hwEtherStatsTotalUnicastPkts                      Counter64,
           hwEtherStatsTotalOctets                           Counter64                                             
     }
     
     hwEtherStatsPktsRecvPauseInfo OBJECT-TYPE
       SYNTAX     Counter64 
       UNITS      "Packets"
       MAX-ACCESS read-only
       STATUS     current
       DESCRIPTION
           "Number of PAUSE frames received by the port."
       ::= { hwEtherStatsInfoEntry 1 }
         
     hwEtherStatsPktsSendPauseInfo OBJECT-TYPE
       SYNTAX     Counter64 
       UNITS      "Packets"
       MAX-ACCESS read-only
       STATUS     current
       DESCRIPTION
           "Number of PAUSE frames send from the port."
       ::= { hwEtherStatsInfoEntry 2 }
       
     hwEtherStatsPkts1519to2047OctetsInfo OBJECT-TYPE
       SYNTAX     Counter64    
       UNITS      "Packets"
       MAX-ACCESS read-only
       STATUS     current
       DESCRIPTION
           "Total number of frames of 1519-2047 bytes."
       ::= { hwEtherStatsInfoEntry 3 }
         
     hwEtherStatsPkts2048to4095OctetsInfo OBJECT-TYPE
       SYNTAX     Counter64   
       UNITS      "Packets"
       MAX-ACCESS read-only
       STATUS     current
       DESCRIPTION
           "Total number of frames of 2048-4095 bytes."
       ::= { hwEtherStatsInfoEntry 4 }
         
     hwEtherStatsPkts4096to9216OctetsInfo OBJECT-TYPE
       SYNTAX     Counter64  
       UNITS      "Packets"
       MAX-ACCESS read-only
       STATUS     current
       DESCRIPTION
           "Total number of frames of 4096-9216 bytes."
       ::= { hwEtherStatsInfoEntry 5 }
         
     hwEtherStatsRecvOctetsInfo OBJECT-TYPE
       SYNTAX     Counter64  
       UNITS      "Octets"
       MAX-ACCESS read-only
       STATUS     current
       DESCRIPTION
           "Total number of the octets received."
       ::= { hwEtherStatsInfoEntry 6 }
         
     hwEtherStatsSendOctetsInfo OBJECT-TYPE
       SYNTAX     Counter64  
       UNITS      "Octets"
       MAX-ACCESS read-only
       STATUS     current
       DESCRIPTION
           "Total number of the octets sent correctly."
       ::= { hwEtherStatsInfoEntry 7 }
         
     hwEtherStatsPktsSendSingleCollisionInfo OBJECT-TYPE
       SYNTAX     Counter64 
       UNITS      "Packets"
       MAX-ACCESS read-only
       STATUS     current
       DESCRIPTION
           "Total number of packets sent correctly after a single collision."
       ::= { hwEtherStatsInfoEntry 8 }
         
     hwEtherStatsPktsSendMultiCollisionInfo OBJECT-TYPE
       SYNTAX     Counter64  
       UNITS      "Packets"
       MAX-ACCESS read-only
       STATUS     current
       DESCRIPTION
           "Total number of packets sent correctly after multiple collisions."
       ::= { hwEtherStatsInfoEntry 9 }
         
     hwEtherStatsUpDiscardPacketsInfo OBJECT-TYPE
       SYNTAX     Counter64   
       UNITS      "Packets"
       MAX-ACCESS read-only
       STATUS     current
       DESCRIPTION
           "Total number of upstream discarded packets."
       ::= { hwEtherStatsInfoEntry 10 }
         
     hwEtherStatsDownDiscardPacketsInfo OBJECT-TYPE
       SYNTAX     Counter64  
       UNITS      "Packets"
       MAX-ACCESS read-only
       STATUS     current
       DESCRIPTION
           "Total number of downstream discarded packets."
       ::= { hwEtherStatsInfoEntry 11 }
         
     hwEtherStatsAlignmentErrorFramesInfo OBJECT-TYPE
       SYNTAX     Counter64  
       UNITS      "Frames"
       MAX-ACCESS read-only
       STATUS     current
       DESCRIPTION
           "Total number of alignment error frames."
       ::= { hwEtherStatsInfoEntry 12 }
     
     hwEtherStatsPortStateChange OBJECT-TYPE
       SYNTAX     Counter32  
       UNITS      "Times"
       MAX-ACCESS read-only
       STATUS     current
       DESCRIPTION
           "Total number of port state change."
       ::= { hwEtherStatsInfoEntry 13 }     

     hwEtherStatsDropEvents OBJECT-TYPE
       SYNTAX     Counter64
       MAX-ACCESS read-only
       STATUS     current
       DESCRIPTION
           "Total number of events in which packets were dropped by the probe due to lack of resources.
            Note that this number is not the necessary number of packets dropped; it is just the 
            number of times this condition has been detected.
           "
       ::= { hwEtherStatsInfoEntry 14 }

     hwEtherStatsOctets OBJECT-TYPE
       SYNTAX     Counter64
       UNITS      "Octets"
       MAX-ACCESS read-only
       STATUS     current
       DESCRIPTION
           "Total number of octets of data (including those in bad packets) received on the network 
            (excluding framing bits but including FCS octets).
            This object can be used as a reasonable estimate of 10-Megabit ethernet utilization.  
            If greater precision is desired, the etherStatsPkts and etherStatsOctets objects should 
            be sampled before and after a common interval. The differences in the sampled values are 
            Pkts and Octets, respectively, and the number of seconds in the interval is interval.  
            These values are used to calculate the Utilization
            as follows:

                            Pkts * (9.6 + 6.4) + (Octets * .8)
            Utilization = -------------------------------------
                                    Interval * 10,000

            The result of this equation is the value Utilization which is the percent utilization of 
            the ethernet segment on a scale of 0 to 100 percent.
           "
       ::= { hwEtherStatsInfoEntry 15 }

     hwEtherStatsRxPkts OBJECT-TYPE
       SYNTAX     Counter64
       UNITS      "Packets"
       MAX-ACCESS read-only
       STATUS     current
       DESCRIPTION
           "Total number of packets (including bad packets, broadcast packets, and multicast packets) received.
           "
       ::= { hwEtherStatsInfoEntry 16 }

     hwEtherStatsRxBroadcastPkts OBJECT-TYPE
       SYNTAX     Counter64
       UNITS      "Packets"
       MAX-ACCESS read-only
       STATUS     current
       DESCRIPTION
           "Total number of good packets received that were directed to the broadcast address.  
            Note that this does not include multicast packets.
           "
       ::= { hwEtherStatsInfoEntry 17 }

     hwEtherStatsRxMulticastPkts OBJECT-TYPE
       SYNTAX     Counter64
       UNITS      "Packets"
       MAX-ACCESS read-only
       STATUS     current
       DESCRIPTION
           "Total number of good packets received that were directed to a multicast address.  
            Note that this number does not include packets directed to the broadcast address.
           "
       ::= { hwEtherStatsInfoEntry 18 }

     hwEtherStatsCRCAlignErrors OBJECT-TYPE
       SYNTAX     Counter64
       UNITS      "Packets"
       MAX-ACCESS read-only
       STATUS     current
       DESCRIPTION
           "Total number of packets that had a length (excluding framing bits, but
            including FCS octets) of between 64 and 1518 octets, inclusive, but had either a bad
            Frame Check Sequence (FCS) with an integral number of octets (FCS Error) or a bad FCS 
            with a non-integral number of octets (Alignment Error).
           "
       ::= { hwEtherStatsInfoEntry 19 }

     hwEtherStatsUndersizePkts OBJECT-TYPE
       SYNTAX     Counter64
       UNITS      "Packets"
       MAX-ACCESS read-only
       STATUS     current
       DESCRIPTION
           "Total number of packets that were less than 64 octets long (excluding framing 
            bits, but including FCS octets) and were otherwise well formed.
           "
       ::= { hwEtherStatsInfoEntry 20 }

     hwEtherStatsOversizePkts OBJECT-TYPE
       SYNTAX     Counter64
       UNITS      "Packets"
       MAX-ACCESS read-only
       STATUS     current
       DESCRIPTION
           "Total number of packets that were longer than 1518 octets (excluding framing 
            bits, but including FCS octets) and were otherwise well formed.
           "
       ::= { hwEtherStatsInfoEntry 21 }

     hwEtherStatsFragments OBJECT-TYPE
       SYNTAX     Counter64
       UNITS      "Packets"
       MAX-ACCESS read-only
       STATUS     current
       DESCRIPTION
           "Total number of packets that were less than 64 octets in length (excluding 
            framing bits but including FCS octets) and had either a bad Frame Check Sequence
            (FCS) with an integral number of octets (FCS Error) or a bad FCS with a non-integral 
            number of octets (Alignment Error).

            Note that it is entirely normal for etherStatsFragments to increment.  This is because 
            it counts both runts (which are normal occurrences due to collisions) and noise hits.
           "
       ::= { hwEtherStatsInfoEntry 22 }

     hwEtherStatsJabbers OBJECT-TYPE
       SYNTAX     Counter64
       UNITS      "Packets"
       MAX-ACCESS read-only
       STATUS     current
       DESCRIPTION
           "Total number of packets that were longer than 1518 octets (excluding framing 
            bits, but including FCS octets), and had either a bad Frame Check Sequence (FCS) with 
            an integral number of octets (FCS Error) or a bad FCS with a non-integral number of 
            octets (Alignment Error).

            Note that this definition of jabber is different than the definition in IEEE-802.3 
            section 8.2.1.5(10BASE5) and section 10.3.1.4 (10BASE2). These documents define jabber 
            as the condition where any packet exceeds 20 ms.  The allowed range to detect jabber 
            is between 20 ms and 150 ms.
           "
       ::= { hwEtherStatsInfoEntry 23 }

     hwEtherStatsCollisions OBJECT-TYPE
       SYNTAX     Counter64
       UNITS      "Collisions"
       MAX-ACCESS read-only
       STATUS     current
       DESCRIPTION
           "The best estimate of the total number of collisions on this Ethernet segment.

            The value returned will depend on the location of the RMON probe. Section 
            8.2.1.3 (10BASE-5) and section 10.3.1.3 (10BASE-2) of IEEE standard 802.3 
            states that a station must detect a collision, in the receive mode, if three or 
            more stations are transmitting simultaneously. A repeater port must detect a 
            collision when two or more stations are transmitting simultaneously. Thus a probe
            placed on a repeater port could record more collisions than a probe connected to 
            a station on the same segment would.

            Probe location plays a much smaller role when considering 10BASE-T. 14.2.1.4(10BASE-T) 
            of IEEE standard 802.3 defines a collision as the simultaneous presence of signals
            on the DO and RD circuits (transmitting and receiving at the same time). A 10BASE-T 
            station can only detect collisions when it is transmitting. Thus probes placed on
            a station and a repeater, should report the same number of collisions.

            Note also that an RMON probe inside a repeater should ideally report collisions 
            between the repeater and one or more other hosts (transmit collisions as defined by 
            IEEE802.3k) plus receiver collisions observed on any coax segments to which the repeater 
            is connected.
           "
       ::= { hwEtherStatsInfoEntry 24 }

     hwEtherStatsPkts64Octets OBJECT-TYPE
       SYNTAX     Counter64
       UNITS      "Packets"
       MAX-ACCESS read-only
       STATUS     current
       DESCRIPTION
           "Total number of packets (including bad packets) that were 64 octets in length
            (excluding framing bits but including FCS octets).
           "
       ::= { hwEtherStatsInfoEntry 25 }

     hwEtherStatsPkts65to127Octets OBJECT-TYPE
       SYNTAX     Counter64
       UNITS      "Packets"
       MAX-ACCESS read-only
       STATUS     current
       DESCRIPTION
           "Total number of packets (including bad packets) that were between
            65 and 127 octets in length inclusive(excluding framing bits but including FCS octets).
           "
       ::= { hwEtherStatsInfoEntry 26 }

     hwEtherStatsPkts128to255Octets OBJECT-TYPE
       SYNTAX     Counter64
       UNITS      "Packets"
       MAX-ACCESS read-only
       STATUS     current
       DESCRIPTION
           "Total number of packets (including bad packets) that were between
            128 and 255 octets in length inclusive(excluding framing bits but including FCS octets).
           "
       ::= { hwEtherStatsInfoEntry 27 }

     hwEtherStatsPkts256to511Octets OBJECT-TYPE
       SYNTAX     Counter64
       UNITS      "Packets"
       MAX-ACCESS read-only
       STATUS     current
       DESCRIPTION
           "Total number of packets (including bad packets) that were between
            256 and 511 octets in length inclusive(excluding framing bits but including FCS octets).
           "
       ::= { hwEtherStatsInfoEntry 28 }

     hwEtherStatsPkts512to1023Octets OBJECT-TYPE
       SYNTAX     Counter64
       UNITS      "Packets"
       MAX-ACCESS read-only
       STATUS     current
       DESCRIPTION
           "Total number of packets (including bad packets) that were between
            512 and 1023 octets in length inclusive(excluding framing bits but including FCS octets).
           "
       ::= { hwEtherStatsInfoEntry 29 }

     hwEtherStatsPkts1024to1518Octets OBJECT-TYPE
       SYNTAX     Counter64
       UNITS      "Packets"
       MAX-ACCESS read-only
       STATUS     current
       DESCRIPTION
           "Total number of packets (including bad packets) that were between
            1024 and 1518 octets in length inclusive(excluding framing bits but including FCS octets).
           "
       ::= { hwEtherStatsInfoEntry 30 }
       
      
     hwEtherStatsReceiveUnicastPacketsInfo OBJECT-TYPE
       SYNTAX     Counter64
       UNITS      "Packets"
       MAX-ACCESS read-only
       STATUS     current
       DESCRIPTION
           "Total number of good packets received that were directed to a unicast address.
           "
       ::= { hwEtherStatsInfoEntry 31 }
          
     hwEtherStatsSendUnicastPacketsInfo OBJECT-TYPE
       SYNTAX     Counter64
       UNITS      "Packets"
       MAX-ACCESS read-only
       STATUS     current
       DESCRIPTION
           "Total number of good packets that are sent and directed to a unicast address.
           "
       ::= { hwEtherStatsInfoEntry 32 }
       
     hwEtherStatsSendGreenOctets OBJECT-TYPE
       SYNTAX     Counter64
       UNITS      "Octets"
       MAX-ACCESS read-only
       STATUS     current
       DESCRIPTION
           "Total number of green octets that are sent.
           "
       ::= { hwEtherStatsInfoEntry 33 }
       
     hwEtherStatsSendGreenPkts OBJECT-TYPE
       SYNTAX     Counter64
       UNITS      "Packets"
       MAX-ACCESS read-only
       STATUS     current
       DESCRIPTION
           "Total number of green packets that are sent.
           "
       ::= { hwEtherStatsInfoEntry 34 }
       
     hwEtherStatsDiscardGreenPkts OBJECT-TYPE
       SYNTAX     Counter64
       UNITS      "Packets"
       MAX-ACCESS read-only
       STATUS     current
       DESCRIPTION
           "Total number of green packets that are discarded.
           "
       ::= { hwEtherStatsInfoEntry 35 }
       
     hwEtherStatsSendYellowOctets OBJECT-TYPE
       SYNTAX     Counter64
       UNITS      "Octets"
       MAX-ACCESS read-only
       STATUS     current
       DESCRIPTION
           "Total number of yellow octets that are sent.
           "
       ::= { hwEtherStatsInfoEntry 36 }
       
     hwEtherStatsSendYellowPkts OBJECT-TYPE
       SYNTAX     Counter64
       UNITS      "Packets"
       MAX-ACCESS read-only
       STATUS     current
       DESCRIPTION
           "Total number of yellow packets that are sent.
           "
       ::= { hwEtherStatsInfoEntry 37 }
       
     hwEtherStatsDiscardYellowPkts OBJECT-TYPE
       SYNTAX     Counter64
       UNITS      "Packets"
       MAX-ACCESS read-only
       STATUS     current
       DESCRIPTION
           "Total number of yellow packets that are discarded.
           "   
       ::= { hwEtherStatsInfoEntry 38 }
       
     hwEtherStatsTxPkts OBJECT-TYPE
       SYNTAX     Counter64
       UNITS      "Packets"
       MAX-ACCESS read-only
       STATUS     current
       DESCRIPTION
           "Total number of frames that are transmitted.
           "
       ::= { hwEtherStatsInfoEntry 39 }
       
     hwEtherStatsTotalPkts OBJECT-TYPE
       SYNTAX     Counter64
       UNITS      "Packets"
       MAX-ACCESS read-only
       STATUS     current
       DESCRIPTION
           "Total number of frames.
           "
       ::= { hwEtherStatsInfoEntry 40 }
       
     hwEtherStatsTotalBroadcastPkts OBJECT-TYPE
       SYNTAX     Counter64
       UNITS      "Packets"
       MAX-ACCESS read-only
       STATUS     current
       DESCRIPTION
           "Total number of broadcast frames.
           "
       ::= { hwEtherStatsInfoEntry 41 }
       
     hwEtherStatsTxBroadcastPkts OBJECT-TYPE
       SYNTAX     Counter64
       UNITS      "Packets"
       MAX-ACCESS read-only
       STATUS     current
       DESCRIPTION
           "Total number of broadcast frames that are transmitted.
           "
       ::= { hwEtherStatsInfoEntry 42 }
       
     hwEtherStatsTotalMulticastPkts OBJECT-TYPE
       SYNTAX     Counter64
       UNITS      "Packets"
       MAX-ACCESS read-only
       STATUS     current
       DESCRIPTION
           "Total number of multicast frames.
           "
       ::= { hwEtherStatsInfoEntry 43 }
       
     hwEtherStatsTxMulticastPkts OBJECT-TYPE
       SYNTAX     Counter64
       UNITS      "Packets"
       MAX-ACCESS read-only
       STATUS     current
       DESCRIPTION
           "Total number of multicast frames that are transmitted.
           "
       ::= { hwEtherStatsInfoEntry 44 }
       
     hwEtherStatsRxUndersizePkts OBJECT-TYPE
       SYNTAX     Counter64
       UNITS      "Packets"
       MAX-ACCESS read-only
       STATUS     current
       DESCRIPTION
           "Total number of undersize frames that are received.
           "
       ::= { hwEtherStatsInfoEntry 45 }
       
     hwEtherStatsRxOversizePkts OBJECT-TYPE
       SYNTAX     Counter64
       UNITS      "Packets"
       MAX-ACCESS read-only
       STATUS     current
       DESCRIPTION
           "Total number of oversize frames that are received.
           "
       ::= { hwEtherStatsInfoEntry 46 }
       
     hwEtherStatsTxCollisionPkts OBJECT-TYPE
       SYNTAX     Counter64
       UNITS      "Packets"
       MAX-ACCESS read-only
       STATUS     current
       DESCRIPTION
           "Total number of collision frames that are transmitted.
           "
       ::= { hwEtherStatsInfoEntry 47 }
       
     hwEtherStatsDiscardedUndersizedPkts OBJECT-TYPE
       SYNTAX     Counter64
       UNITS      "Packets"
       MAX-ACCESS read-only
       STATUS     current
       DESCRIPTION
           "Total number of packets that were less than 64 octets long (excluding framing 
            bits, but including FCS octets) and were otherwise well formed.
           "
       ::= { hwEtherStatsInfoEntry 48 }
       
     hwEtherStatsTxUndersizedPkts OBJECT-TYPE
       SYNTAX     Counter64
       UNITS      "Packets"
       MAX-ACCESS read-only
       STATUS     current
       DESCRIPTION
           "Total number of undersized frames that are transmitted.
           "
       ::= { hwEtherStatsInfoEntry 49 }
       
     hwEtherStatsTxFragmentsPkts OBJECT-TYPE
       SYNTAX     Counter64
       UNITS      "Packets"
       MAX-ACCESS read-only
       STATUS     current
       DESCRIPTION
           "Total number of fragments frames that are transmitted.
           "
       ::= { hwEtherStatsInfoEntry 50 }
       
     hwEtherStatsRxFragmentsPkts OBJECT-TYPE
       SYNTAX     Counter64
       UNITS      "Packets"
       MAX-ACCESS read-only
       STATUS     current
       DESCRIPTION
           "Total number of fragments frames that are received.
           "
       ::= { hwEtherStatsInfoEntry 51 }
       
     hwEtherStatsTxJabbers OBJECT-TYPE
       SYNTAX     Counter64
       UNITS      "Packets"
       MAX-ACCESS read-only
       STATUS     current
       DESCRIPTION
           "Total number of jabbers frames that are transmitted.
           "
       ::= { hwEtherStatsInfoEntry 52 }
       
     hwEtherStatsRxJabbers OBJECT-TYPE
       SYNTAX     Counter64
       UNITS      "Packets"
       MAX-ACCESS read-only
       STATUS     current
       DESCRIPTION
           "Total number of jabbers frames that are received.
           "
       ::= { hwEtherStatsInfoEntry 53 }
       
     hwEtherStatsTxOversizedPkts OBJECT-TYPE
       SYNTAX     Counter64
       UNITS      "Packets"
       MAX-ACCESS read-only
       STATUS     current
       DESCRIPTION
           "Total number of oversized frames that are transmitted.
           "
       ::= { hwEtherStatsInfoEntry 54 }
       
     hwEtherStatsRx64octetsPkts OBJECT-TYPE
       SYNTAX     Counter64
       UNITS      "Packets"
       MAX-ACCESS read-only
       STATUS     current
       DESCRIPTION
           "Total number of 64 octets that are received.
           "
       ::= { hwEtherStatsInfoEntry 55 }
       
     hwEtherStatsTx64octetsPkts OBJECT-TYPE
       SYNTAX     Counter64
       UNITS      "Packets"
       MAX-ACCESS read-only
       STATUS     current
       DESCRIPTION
           "Total number of 64 octets that are transmitted.
           "
       ::= { hwEtherStatsInfoEntry 56 }
       
     hwEtherStatsRx65to127octetsPkts OBJECT-TYPE
       SYNTAX     Counter64
       UNITS      "Packets"
       MAX-ACCESS read-only
       STATUS     current
       DESCRIPTION
           "Total number of 65 to 127 octets that are received.
           "
       ::= { hwEtherStatsInfoEntry 57 }
       
     hwEtherStatsTx65to127octetsPkts OBJECT-TYPE
       SYNTAX     Counter64
       UNITS      "Packets"
       MAX-ACCESS read-only
       STATUS     current
       DESCRIPTION
           "Total number of 65 to 127 octets that are transmitted.
           "
       ::= { hwEtherStatsInfoEntry 58 }
       
     hwEtherStatsRx128to255octetsPkts OBJECT-TYPE
       SYNTAX     Counter64
       UNITS      "Packets"
       MAX-ACCESS read-only
       STATUS     current
       DESCRIPTION
           "Total number of 128 to 255 octets that are received.
           "
       ::= { hwEtherStatsInfoEntry 59 } 
     
     hwEtherStatsTx128to255octetsPkts OBJECT-TYPE
       SYNTAX     Counter64
       UNITS      "Packets"
       MAX-ACCESS read-only
       STATUS     current
       DESCRIPTION
           "Total number of 128 to 255 octets that are transmitted.
           "
       ::= { hwEtherStatsInfoEntry 60 }         
     
     hwEtherStatsRx256to511octetsPkts OBJECT-TYPE
       SYNTAX     Counter64
       UNITS      "Packets"
       MAX-ACCESS read-only
       STATUS     current
       DESCRIPTION
           "Total number of 256 to 511 octets that are received.
           "
       ::= { hwEtherStatsInfoEntry 61 }         
     
     hwEtherStatsTx256to511octetsPkts OBJECT-TYPE
       SYNTAX     Counter64
       UNITS      "Packets"
       MAX-ACCESS read-only
       STATUS     current
       DESCRIPTION
           "Total number of 256 to 511 octets that are transmitted.
           "
       ::= { hwEtherStatsInfoEntry 62 }         
     
     hwEtherStatsRx512to1023octetsPkts OBJECT-TYPE
       SYNTAX     Counter64
       UNITS      "Packets"
       MAX-ACCESS read-only
       STATUS     current
       DESCRIPTION
           "Total number of 512 to 1023 octets that are received.
           "
       ::= { hwEtherStatsInfoEntry 63 }         
     
     hwEtherStatsTx512to1023octetsPkts OBJECT-TYPE
       SYNTAX     Counter64
       UNITS      "Packets"
       MAX-ACCESS read-only
       STATUS     current
       DESCRIPTION
           "Total number of 512 to 1023 octets that are transmitted.
           "
       ::= { hwEtherStatsInfoEntry 64 }  
     
     hwEtherStatsRx1024to1518octetsPkts OBJECT-TYPE
       SYNTAX     Counter64
       UNITS      "Packets"
       MAX-ACCESS read-only
       STATUS     current
       DESCRIPTION
           "Total number of 1024 to 1518 octets that are received.
           "
       ::= { hwEtherStatsInfoEntry 65 } 
       
     hwEtherStatsTx1024to1518octetsPkts OBJECT-TYPE
       SYNTAX     Counter64
       UNITS      "Packets"
       MAX-ACCESS read-only
       STATUS     current
       DESCRIPTION
           "Total number of 1024 to 1518 octets that are transmitted.
           "
       ::= { hwEtherStatsInfoEntry 66 } 
       
     hwEtherStatsTxErrorPkts OBJECT-TYPE
       SYNTAX     Counter64
       UNITS      "Packets"
       MAX-ACCESS read-only
       STATUS     current
       DESCRIPTION
           "Total number of error frames that are transmitted.
           "
       ::= { hwEtherStatsInfoEntry 67 } 
       
     hwEtherStatsRxErrorPkts OBJECT-TYPE
       SYNTAX     Counter64
       UNITS      "Packets"
       MAX-ACCESS read-only
       STATUS     current
       DESCRIPTION
           "Total number of error frames that are received.
           "
       ::= { hwEtherStatsInfoEntry 68 } 
       
     hwEtherStatsTxCRCErrorPkts OBJECT-TYPE
       SYNTAX     Counter64
       UNITS      "Packets"
       MAX-ACCESS read-only
       STATUS     current
       DESCRIPTION
           "Total number of CRC error frames that are transmitted.
           "
       ::= { hwEtherStatsInfoEntry 69 }  
       
     hwEtherStatsAlignErrors OBJECT-TYPE
       SYNTAX     Counter64
       UNITS      "Packets"
       MAX-ACCESS read-only
       STATUS     current
       DESCRIPTION
           "Total number of packets received that had a non-integral number of octets (Alignment Error).
           "
       ::= { hwEtherStatsInfoEntry 70 }  
       
     hwEtherStatsTotalUnicastPkts OBJECT-TYPE
       SYNTAX     Counter64
       UNITS      "Packets"
       MAX-ACCESS read-only
       STATUS     current
       DESCRIPTION
           "Total number of packets that are sent to or reveived from a unicast address.
           "
       ::= { hwEtherStatsInfoEntry 71 } 
       
     hwEtherStatsTotalOctets OBJECT-TYPE
       SYNTAX     Counter64
       UNITS      "Octets"
       MAX-ACCESS read-only
       STATUS     current
       DESCRIPTION
           "Total number of Octets.
           "
       ::= { hwEtherStatsInfoEntry 72 }   

  END
