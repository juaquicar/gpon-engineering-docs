-- =================================================================
-- Copyright (C) 2016 by HUAWEI TECHNOLOGIES. All rights reserved.
-- Description:  The MIB is used for defining Huawei's ACCESS management common MIB objects.
-- Reference:
-- Version: V1.15
-- ================================================================

    HUAWEI-LINE-COMMON-MIB DEFINITIONS ::= BEGIN
        IMPORTS
            MODULE-IDENTITY, mib-2, OBJECT-TYPE, Counter32, Counter64,
            Unsigned32, Integer32, zeroDotZero, IpAddress, Gauge32, NOTIFICATION-TYPE
                FROM SNMPv2-SMI
            TruthValue, DateAndTime, RowStatus, MacAddress,TEXTUAL-CONVENTION
                FROM SNMPv2-TC
            ifIndex
                FROM IF-MIB
            MODULE-COMPLIANCE, OBJECT-GROUP
                FROM SNMPv2-CONF
            OwnerString, EntryStatus
                FROM RMON-MIB
           hwFrameIndex, hwSlotIndex,hwSubslotIndex,hwPortIndex,hwConfigChangeIP
                FROM HUAWEI-DEVICE-MIB
            huaweiMgmt, huaweiUtility
                FROM HUAWEI-MIB;

        hwAccessCommonMIB MODULE-IDENTITY
            LAST-UPDATED "201606300900Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION
                 "The MIB is used for defining Huawei's ACCESS management common MIB objects."

        -- Revision history 
            REVISION     "201606300900Z"
            DESCRIPTION  "V1.15,
                          - Add the enumerate of leaf hwXponOntDdmInfoExSubType in table hwXponDeviceOntDdmInfoExTable.  
                          - Add the enumerate of leaf hwOpticsDdmInfoExSubType in table hwOpticsDdmInfoExTable.                                                                             
                         "                                                                           
                         
            REVISION     "201601040900Z"
            DESCRIPTION  "V1.14,
                          - Add the enumerate of leaf hwXponOntDdmInfoExModuleType in table hwXponDeviceOntDdmInfoExTable.                                                                             
                         "
        
            REVISION     "201412250900Z"
            DESCRIPTION  "V1.13,
                          -Modify the undefined name of leaf hwXponNniOpticsModuleInfoRateIdentifier in table hwXponNniOpticsModuleInfoTable.                                                                             
                         "	
        
            REVISION     "201412250900Z"
            DESCRIPTION  "V1.12,
                          -Modify the value range of leaf hwXponOntDdmInfoExUsedType in table hwXponDeviceOntDdmInfoExTable.                                                                             
                         "
                         
            REVISION     "201409180900Z"
            DESCRIPTION  "V1.11,
                          -Modify the value range of leaf hwOpticsDdmInfoExSubType in table hwOpticsDdmInfoExTable.                                                                             
                         "
                         
            REVISION     "201407060900Z"
            DESCRIPTION  "V1.10,
                          -Modify the range of nodes hwXponOntDdmInfoExPortId.                                                    
                         "

            REVISION     "201307250900Z"
            DESCRIPTION  "V1.09,
                          -Add the table of hwXponNniOpticsModuleInfoTable."
			  
            REVISION     "201307050900Z"
            DESCRIPTION  "V1.08,
                          -Add the leaf nodes hwXponOntDdmInfoExPortId, hwXponOntDdmInfoExVendorName, hwXponOntDdmInfoExVendorRev, 
                           hwXponOntDdmInfoExVendorSN, hwXponOntDdmInfoExDateCode in table hwXponDeviceOntDdmInfoExTable."

            REVISION     "201301150900Z"
            DESCRIPTION  "V1.07,
                          -Modify the leaf of hwPortActualmode, add (65535) enum of the node
                         "

            REVISION     "201105260900Z"
            DESCRIPTION  "V1.06,
                          -Modify the leaf nodes name of hwOpticsDdmInfoExRxPowerLow,hwXponOntDdmInfoExRxPowerLow to hwOpticsDdmInfoExRxPower,hwXponOntDdmInfoExRxPower
                          -Modify the postfix name of all the leaf nodes in the table hwOpticsDdmInfoExTable and hwXponDeviceOntDdmInfoExTable
                          from HighAlarm,LowAlarm,HighWarning,LowWarning to HighAlarmThreshold,LowAlarmThreshold,HighWarningThreshold,LowWarningThreshold
                          -Add the leaf nodes hwOpticsDdmInfoExCatvRxPowerLowAlarmThreshold,hwOpticsDdmInfoExCatvRxPowerHighAlarmThreshold,hwOpticsDdmInfoExModuleType,
                          hwOpticsDdmInfoExSubType,hwOpticsDdmInfoExPrecision,hwOpticsDdmInfoExEncapsulationType,hwOpticsDdmInfoExVendorPN,hwOpticsDdmInfoExUsedType
                          in table hwOpticsDdmInfoExTable.
                          -Add the leaf nodes hwXponOntDdmInfoExCatvRxPowerLowAlarmThreshold,hwXponOntDdmInfoExCatvRxPowerHighAlarmThreshold,hwXponOntDdmInfoExModuleType,
                          hwXponOntDdmInfoExSubType,hwXponOntDdmInfoExPrecision,hwXponOntDdmInfoExEncapsulationType,hwXponOntDdmInfoExVendorPN,hwXponOntDdmInfoExUsedType
                          in table hwXponDeviceOntDdmInfoExTable.
                         "

            REVISION     "201103110900Z"
            DESCRIPTION  "V1.05,
                          Add a leaf hwOpticsDdmInfo10GTxBiasCurrent to HwOpticsDdmInfoExEntry
                          Add a leaf hwOpticsDdmInfo10GTxPower to HwOpticsDdmInfoExEntry
                          Add a leaf hwXponOntDdmInfoExOltRxOntPower to HwXponDeviceOntDdmInfoExEntry.
                         "


            REVISION     "201011170900Z"
            DESCRIPTION  "V1.04, modify the node name of hwProtTypeAdaptFaultAlarmTrap to hwPortTypeAdaptFaultAlarmTrap
                          modify the node name of hwProtTypeAdaptFaultRestoreAlarmTrap to hwPortTypeAdaptFaultRestoreAlarmTrap
                          modify the node name of hwProtTypeAdaptSucessAlarmTrap to hwPortTypeAdaptSuccessAlarmTrap.
                         "

            REVISION     "201009280900Z"
            DESCRIPTION  "V1.03, modify the description of the whole MIB file."

            REVISION     "201008220900Z"
            DESCRIPTION  "V1.02, modify the description of the temperature.
                          modify the node name of hwXponOntDdmInfoExTable to hwXponDeviceOntDdmInfoExEntry
                          for clearing the compilation warning.
                         "

            REVISION     "201005200900Z"
            DESCRIPTION  "V1.01, add the definition of the trap node,include:
                          hwProtTypeAdaptFaultAlarmTrap
                          hwProtTypeAdaptFaultRestoreAlarmTrap
                          hwProtTypeAdaptSucessAlarmTrap
                          hwXponnniPortSwitchAlarmTrap
                          hwXponnniPortSwitchTrap
                         "

            REVISION     "200912300900Z"
            DESCRIPTION  "V1.00, Initial version."
            ::= { huaweiUtility  158 }

        hwAccessCommonObjectMIB        OBJECT IDENTIFIER ::= { hwAccessCommonMIB 1}
        hwLineCommonTrapsVbOids        OBJECT IDENTIFIER ::= { hwAccessCommonMIB 50}
        hwLineCommonTraps              OBJECT IDENTIFIER ::= { hwAccessCommonMIB 51}
        hwLineTraps                    OBJECT IDENTIFIER ::= { hwLineCommonTraps 1}
        hwLineTrapsPrefix              OBJECT IDENTIFIER ::= { hwLineTraps 0 }
        hwLineAlarmTraps               OBJECT IDENTIFIER ::= { hwLineCommonTraps 2}
        hwLineAlarmTrapsPrefix         OBJECT IDENTIFIER ::= { hwLineAlarmTraps 0 }
        hwAccessCommonObjects          OBJECT IDENTIFIER ::= { hwAccessCommonObjectMIB  1}
        hwAccessCommonControlObjects   OBJECT IDENTIFIER ::= { hwAccessCommonObjects 1}
        hwAccessCommonStatisticObjects OBJECT IDENTIFIER ::= { hwAccessCommonObjects 2}

        hwOpticsDdmInfoExTable OBJECT-TYPE
            SYNTAX      SEQUENCE OF HwOpticsDdmInfoExEntry
            MAX-ACCESS  not-accessible
            STATUS      current
            DESCRIPTION
                "Table hwOpticsDdmInfoExTable supports the query of the information about the optical transceiver.
                 The index of this table is ifIndex.
                "
            ::= { hwAccessCommonControlObjects 1 }

        hwOpticsDdmInfoExEntry OBJECT-TYPE
            SYNTAX      HwOpticsDdmInfoExEntry
            MAX-ACCESS  not-accessible
            STATUS      current
            DESCRIPTION
                "Table hwOpticsDdmInfoExTable supports the query of the information about the optical transceiver.
                 The index of this entry is ifIndex.
                "
            INDEX       { ifIndex }
            ::= { hwOpticsDdmInfoExTable 1 }

        HwOpticsDdmInfoExEntry  ::=
            SEQUENCE {
                hwOpticsDdmInfoExTemperature                            Integer32,
                hwOpticsDdmInfoExTemperatureHighAlarmThreshold          Integer32,
                hwOpticsDdmInfoExTemperatureLowAlarmThreshold           Integer32,
                hwOpticsDdmInfoExTemperatureHighWarningThreshold        Integer32,
                hwOpticsDdmInfoExTemperatureLowWarningThreshold         Integer32,
                hwOpticsDdmInfoExSupplyVoltage                          Integer32,
                hwOpticsDdmInfoExSupplyVoltageHighAlarmThreshold        Integer32,
                hwOpticsDdmInfoExSupplyVoltageLowAlarmThreshold         Integer32,
                hwOpticsDdmInfoExSupplyVoltageHighWarningThreshold      Integer32,
                hwOpticsDdmInfoExSupplyVoltageLowWarningThreshold       Integer32,
                hwOpticsDdmInfoExTxBiasCurrent                          Integer32,
                hwOpticsDdmInfoExTxBiasCurrentHighAlarmThreshold        Integer32,
                hwOpticsDdmInfoExTxBiasCurrentLowAlarmThreshold         Integer32,
                hwOpticsDdmInfoExTxBiasCurrentHighWarningThreshold      Integer32,
                hwOpticsDdmInfoExTxBiasCurrentLowWarningThreshold       Integer32,
                hwOpticsDdmInfoExTxPower                                Integer32,
                hwOpticsDdmInfoExTxPowerHighAlarmThreshold              Integer32,
                hwOpticsDdmInfoExTxPowerLowAlarmThreshold               Integer32,
                hwOpticsDdmInfoExTxPowerHighWarningThreshold            Integer32,
                hwOpticsDdmInfoExTxPowerLowWarningThreshold             Integer32,
                hwOpticsDdmInfoExRxPower                                Integer32,
                hwOpticsDdmInfoExRxPowerHighAlarmThreshold              Integer32,
                hwOpticsDdmInfoExRxPowerLowAlarmThreshold               Integer32,
                hwOpticsDdmInfoExRxPowerHighWarningThreshold            Integer32,
                hwOpticsDdmInfoExRxPowerLowWarningThreshold             Integer32,
                hwOpticsDdmInfo10GTxBiasCurrent                         Integer32,
                hwOpticsDdmInfo10GTxPower                               Integer32,
                hwOpticsDdmInfoExCatvRxPowerHighAlarmThreshold          Integer32,
                hwOpticsDdmInfoExCatvRxPowerLowAlarmThreshold           Integer32,
                hwOpticsDdmInfoExModuleType                             INTEGER,
                hwOpticsDdmInfoExSubType                                INTEGER,
                hwOpticsDdmInfoExPrecision                              Integer32,
                hwOpticsDdmInfoExEncapsulationType                      INTEGER,
                hwOpticsDdmInfoExVendorPN                               OCTET STRING,
                hwOpticsDdmInfoExUsedType                               INTEGER
            }

        hwOpticsDdmInfoExTemperature OBJECT-TYPE
            SYNTAX      Integer32
            UNITS       "0.000001 C(centigrade)"
            MAX-ACCESS  read-only
            STATUS      current
            DESCRIPTION
                "Temperature of the optical transceiver.
                 Unit: 0.000001 C(centigrade)
                 Options:
                 1. invalid(0x7FFFFFFF)      - Indicates that the query fails or no information is detected
                "
            ::= { hwOpticsDdmInfoExEntry  1 }

        hwOpticsDdmInfoExTemperatureHighAlarmThreshold OBJECT-TYPE
            SYNTAX      Integer32
            UNITS       "0.000001 C(centigrade)"
            MAX-ACCESS  read-only
            STATUS      current
            DESCRIPTION
                "Upper alarm threshold of the temperature.
                 Unit: 0.000001 C(centigrade)
                 Options:
                 1. invalid(0x7FFFFFFF)      - Indicates that the query fails or no information is detected
                "
            ::= { hwOpticsDdmInfoExEntry  2 }

        hwOpticsDdmInfoExTemperatureLowAlarmThreshold OBJECT-TYPE
            SYNTAX      Integer32
            UNITS       "0.000001 C(centigrade)"
            MAX-ACCESS  read-only
            STATUS      current
            DESCRIPTION
                "Lower alarm threshold of the temperature.
                 Unit: 0.000001 C(centigrade)
                 Options:
                 1. invalid(0x7FFFFFFF)      - Indicates that the query fails or no information is detected
                "
            ::= { hwOpticsDdmInfoExEntry  3 }

        hwOpticsDdmInfoExTemperatureHighWarningThreshold OBJECT-TYPE
            SYNTAX      Integer32
            UNITS       "0.000001 C(centigrade)"
            MAX-ACCESS  read-only
            STATUS      current
            DESCRIPTION
                "Upper warning threshold of the temperature.
                 Unit: 0.000001 C(centigrade)
                 Options:
                 1. invalid(0x7FFFFFFF)      - Indicates that the query fails or no information is detected
                "
            ::= { hwOpticsDdmInfoExEntry  4 }

        hwOpticsDdmInfoExTemperatureLowWarningThreshold OBJECT-TYPE
            SYNTAX      Integer32
            UNITS       "0.000001 C(centigrade)"
            MAX-ACCESS  read-only
            STATUS      current
            DESCRIPTION
                "Lower warning threshold of the temperature.
                 Unit: 0.000001 C(centigrade)
                 Options:
                 1. invalid(0x7FFFFFFF)      - Indicates that the query fails or no information is detected
                "
            ::= { hwOpticsDdmInfoExEntry  5 }

        hwOpticsDdmInfoExSupplyVoltage OBJECT-TYPE
            SYNTAX      Integer32
            UNITS       "0.000001V"
            MAX-ACCESS  read-only
            STATUS      current
            DESCRIPTION
                "Voltage of the optical transceiver.
                 Unit: 0.000001V
                 Options:
                 1. invalid(0x7FFFFFFF)      - Indicates that the query fails or no information is detected
                "
            ::= { hwOpticsDdmInfoExEntry  6 }

        hwOpticsDdmInfoExSupplyVoltageHighAlarmThreshold OBJECT-TYPE
            SYNTAX      Integer32
            UNITS       "0.000001V"
            MAX-ACCESS  read-only
            STATUS      current
            DESCRIPTION
                "Upper alarm threshold of the voltage.
                 Unit: 0.000001V
                 Options:
                 1. invalid(0x7FFFFFFF)      - Indicates that the query fails or no information is detected
                "
            ::= { hwOpticsDdmInfoExEntry  7 }

        hwOpticsDdmInfoExSupplyVoltageLowAlarmThreshold OBJECT-TYPE
            SYNTAX      Integer32
            UNITS       "0.000001V"
            MAX-ACCESS  read-only
            STATUS      current
            DESCRIPTION
                "Lower alarm threshold of the voltage.
                 Unit: 0.000001V
                 Options:
                 1. invalid(0x7FFFFFFF)      - Indicates that the query fails or no information is detected
                "
            ::= { hwOpticsDdmInfoExEntry  8 }

        hwOpticsDdmInfoExSupplyVoltageHighWarningThreshold OBJECT-TYPE
            SYNTAX      Integer32
            UNITS       "0.000001V"
            MAX-ACCESS  read-only
            STATUS      current
            DESCRIPTION
                "Upper warning threshold of the voltage.
                 Unit: 0.000001V
                 Options:
                 1. invalid(0x7FFFFFFF)      - Indicates that the query fails or no information is detected
                "
            ::= { hwOpticsDdmInfoExEntry  9 }

        hwOpticsDdmInfoExSupplyVoltageLowWarningThreshold OBJECT-TYPE
            SYNTAX      Integer32
            UNITS       "0.000001V"
            MAX-ACCESS  read-only
            STATUS      current
            DESCRIPTION
                "Lower warning threshold of the voltage.
                 Unit: 0.000001V
                 Options:
                 1. invalid(0x7FFFFFFF)      - Indicates that the query fails or no information is detected
                "
            ::= { hwOpticsDdmInfoExEntry  10 }

        hwOpticsDdmInfoExTxBiasCurrent OBJECT-TYPE
            SYNTAX      Integer32
            UNITS       "0.000001A"
            MAX-ACCESS  read-only
            STATUS      current
            DESCRIPTION
                "Current of the optical transceiver.
                 Unit: 0.000001A
                 Options:
                 1. invalid(-1)      - Indicates that the query fails or no information is detected
                "
            ::= { hwOpticsDdmInfoExEntry  11 }


        hwOpticsDdmInfoExTxBiasCurrentHighAlarmThreshold OBJECT-TYPE
            SYNTAX      Integer32
            UNITS       "0.000001A"
            MAX-ACCESS  read-only
            STATUS      current
            DESCRIPTION
                "Upper alarm threshold of the bias current.
                 Unit: 0.000001A
                 Options:
                 1. invalid(-1)      - Indicates that the query fails or no information is detected
                "
            ::= { hwOpticsDdmInfoExEntry  12 }

        hwOpticsDdmInfoExTxBiasCurrentLowAlarmThreshold OBJECT-TYPE
            SYNTAX      Integer32
            UNITS       "0.000001A"
            MAX-ACCESS  read-only
            STATUS      current
            DESCRIPTION
                "Lower alarm threshold of the bias current.
                 Unit: 0.000001A
                 Options:
                 1. invalid(-1)      - Indicates that the query fails or no information is detected
                "
            ::= { hwOpticsDdmInfoExEntry  13 }

        hwOpticsDdmInfoExTxBiasCurrentHighWarningThreshold OBJECT-TYPE
            SYNTAX      Integer32
            UNITS       "0.000001A"
            MAX-ACCESS  read-only
            STATUS      current
            DESCRIPTION
                "Upper warning threshold of the bias current.
                 Unit: 0.000001A
                 Options:
                 1. invalid(-1)      - Indicates that the query fails or no information is detected
                "
            ::= { hwOpticsDdmInfoExEntry  14 }

        hwOpticsDdmInfoExTxBiasCurrentLowWarningThreshold OBJECT-TYPE
            SYNTAX      Integer32
            UNITS       "0.000001A"
            MAX-ACCESS  read-only
            STATUS      current
            DESCRIPTION
                "Lower warning threshold of the bias current.
                 Unit: 0.000001A
                 Options:
                 1. invalid(-1)      - Indicates that the query fails or no information is detected
                "
            ::= { hwOpticsDdmInfoExEntry  15 }

        hwOpticsDdmInfoExTxPower OBJECT-TYPE
            SYNTAX      Integer32
            UNITS       "0.000001dBm"
            MAX-ACCESS  read-only
            STATUS      current
            DESCRIPTION
                "Tx optical power of the optical transceiver.
                 Unit: 0.000001dBm
                 Options:
                 1. invalid(0x7FFFFFFF)      - Indicates that the query fails or no information is detected
                "
            ::= { hwOpticsDdmInfoExEntry  16 }

        hwOpticsDdmInfoExTxPowerHighAlarmThreshold OBJECT-TYPE
            SYNTAX      Integer32
            UNITS       "0.000001dBm"
            MAX-ACCESS  read-only
            STATUS      current
            DESCRIPTION
                "Upper alarm threshold of the Tx power.
                 Unit: 0.000001dBm
                 Options:
                 1. invalid(0x7FFFFFFF)      - Indicates that the query fails or no information is detected
                "
            ::= { hwOpticsDdmInfoExEntry  17 }

        hwOpticsDdmInfoExTxPowerLowAlarmThreshold OBJECT-TYPE
            SYNTAX      Integer32
            UNITS       "0.000001dBm"
            MAX-ACCESS  read-only
            STATUS      current
            DESCRIPTION
                "Lower alarm threshold of the Tx power.
                 Unit: 0.000001dBm
                 Options:
                 1. invalid(0x7FFFFFFF)      - Indicates that the query fails or no information is detected
                "
            ::= { hwOpticsDdmInfoExEntry  18 }

        hwOpticsDdmInfoExTxPowerHighWarningThreshold OBJECT-TYPE
            SYNTAX      Integer32
            UNITS       "0.000001dBm"
            MAX-ACCESS  read-only
            STATUS      current
            DESCRIPTION
                "Upper warning threshold of the Tx power.
                 Unit: 0.000001dBm
                 Options:
                 1. invalid(0x7FFFFFFF)      - Indicates that the query fails or no information is detected
                "
            ::= { hwOpticsDdmInfoExEntry  19 }

        hwOpticsDdmInfoExTxPowerLowWarningThreshold OBJECT-TYPE
            SYNTAX      Integer32
            UNITS       "0.000001dBm"
            MAX-ACCESS  read-only
            STATUS      current
            DESCRIPTION
                "Lower warning threshold of the Tx power.
                 Unit: 0.000001dBm
                 Options:
                 1. invalid(0x7FFFFFFF)      - Indicates that the query fails or no information is detected
                "
            ::= { hwOpticsDdmInfoExEntry  20 }

        hwOpticsDdmInfoExRxPower OBJECT-TYPE
            SYNTAX      Integer32
            UNITS       "0.000001dBm"
            MAX-ACCESS  read-only
            STATUS      current
            DESCRIPTION
                "Rx optical power of the optical transceiver.
                 Unit: 0.000001dBm
                 Options:
                 1. invalid(0x7FFFFFFF)      - Indicates that the query fails or no information is detected
                "
            ::= { hwOpticsDdmInfoExEntry  21 }

        hwOpticsDdmInfoExRxPowerHighAlarmThreshold   OBJECT-TYPE
            SYNTAX      Integer32
            UNITS       "0.000001dBm"
            MAX-ACCESS  read-only
            STATUS      current
            DESCRIPTION
                "Upper alarm threshold of the Rx power.
                 Unit: 0.000001dBm
                 Options:
                 1. invalid(0x7FFFFFFF)      - Indicates that the query fails or no information is detected
                "
            ::= { hwOpticsDdmInfoExEntry  22 }

        hwOpticsDdmInfoExRxPowerLowAlarmThreshold OBJECT-TYPE
            SYNTAX      Integer32
            UNITS       "0.000001dBm"
            MAX-ACCESS  read-only
            STATUS      current
            DESCRIPTION
                "Lower alarm threshold of the Rx power.
                 Unit: 0.000001dBm
                 Options:
                 1. invalid(0x7FFFFFFF)      - Indicates that the query fails or no information is detected
                "
            ::= { hwOpticsDdmInfoExEntry  23 }

        hwOpticsDdmInfoExRxPowerHighWarningThreshold OBJECT-TYPE
            SYNTAX      Integer32
            UNITS       "0.000001dBm"
            MAX-ACCESS  read-only
            STATUS      current
            DESCRIPTION
                "Upper warning threshold of the Rx power.
                 Unit: 0.000001dBm
                 Options:
                 1. invalid(0x7FFFFFFF)      - Indicates that the query fails or no information is detected
                "
            ::= { hwOpticsDdmInfoExEntry  24 }

        hwOpticsDdmInfoExRxPowerLowWarningThreshold OBJECT-TYPE
            SYNTAX      Integer32
            UNITS       "0.000001dBm"
            MAX-ACCESS  read-only
            STATUS      current
            DESCRIPTION
                "Lower warning threshold of the Rx power.
                 Unit: 0.000001dBm
                 Options:
                 1. invalid(0x7FFFFFFF)      - Indicates that the query fails or no information is detected
                "
            ::= { hwOpticsDdmInfoExEntry  25 }

        hwOpticsDdmInfo10GTxBiasCurrent OBJECT-TYPE
            SYNTAX      Integer32
            UNITS       "0.000001A"
            MAX-ACCESS  read-only
            STATUS      current
            DESCRIPTION
                "Current of the 10g optical transceiver.
                 Unit: 0.000001A
                 Options:
                 1. invalid(-1)      - Indicates that the query fails or no information is detected
                "
            ::= { hwOpticsDdmInfoExEntry  26 }

        hwOpticsDdmInfo10GTxPower OBJECT-TYPE
            SYNTAX      Integer32
            UNITS       "0.01dBm"
            MAX-ACCESS  read-only
            STATUS      current
            DESCRIPTION
                "Tx optical power of the 10g optical transceiver.
                 Unit: 0.01dBm
                 Options:
                 1. invalid(0x7FFFFFFF)      - Indicates that the query fails or no information is detected
                "
            ::= { hwOpticsDdmInfoExEntry  27 }

         hwOpticsDdmInfoExCatvRxPowerHighAlarmThreshold OBJECT-TYPE
            SYNTAX      Integer32
            UNITS       "0.000001dBm"
            MAX-ACCESS  read-only
            STATUS      current
            DESCRIPTION
                "Upper AlarmThreshold threshold of the CATV Rx power.
                 Unit: 0.000001dBm
                 Options:
                 1. invalid(0x7FFFFFFF)      - Indicates that the query fails or no information is detected
                "
            ::= { hwOpticsDdmInfoExEntry  28 }

        hwOpticsDdmInfoExCatvRxPowerLowAlarmThreshold OBJECT-TYPE
            SYNTAX      Integer32
            UNITS       "0.000001dBm"
            MAX-ACCESS  read-only
            STATUS      current
            DESCRIPTION
                "Lower AlarmThreshold threshold of the CATV Rx power.
                 Unit: 0.000001dBm
                 Options:
                 1. invalid(0x7FFFFFFF)      - Indicates that the query fails or no information is detected
                "
            ::= { hwOpticsDdmInfoExEntry  29 }


        hwOpticsDdmInfoExModuleType OBJECT-TYPE
            SYNTAX      INTEGER {
                gpon(1),
                epon(2),
                epon10g(3),
                gpon10g(4),
                wdmpon(5),
                hybridpon(6),
                gponepon(7),
                unknown(8),
                invalid(-1)
            }
            MAX-ACCESS  read-only
            STATUS      current
            DESCRIPTION
                "Options:
                 1. gpon(1)          - GPON
                 2. epon(2)          - EPON
                 3. epon10g(3)       - 10G EPON
                 4. gpon10g(4)       - 10G GPON
                 5. wdmpon(5)        - WDM PON
                 6. hybridpon(6)     - hybrid PON
                 7. gponepon(7)      - GPON/EPON
                 8. unknown(8)       - Unknown
                 9. invalid(-1)      - Indicates that the query fails or no information is detected
                "
            ::= { hwOpticsDdmInfoExEntry  30 }

        hwOpticsDdmInfoExSubType OBJECT-TYPE
            SYNTAX      INTEGER {
                classbplus(1),
                classcplus(2),
                classb(3),
                classcplusplus(4),
                n2a(33),
                n2b(34),
                n1(35),
                e1(36),
                e2a(37),
                e2b(38),
                n1n2ae1e2a(39),
                px20(65),
                px20plus(66),
                px20plusplus(67),
                pr30(97),
                pr20(98),
                prx30(99),
                prx20(100),
                prx40(101),
                pr40(102),
                classbPlusAndPx20Plus(129),
                classbAndPx20(130),
                unknown(145),
                invalid(-1)
            }
            MAX-ACCESS  read-only
            STATUS      current
            DESCRIPTION
            "Options:
             1.  classbplus(1)              - CLASS B+             
             2.  classcplus(2)              - CLASS C+
             3.  classb(3)                  - CLASS B
             4.  classcplusplus(4)          - CLASS C++
             5.  n2a(33)                    - N2a  
             6.  n2b(34)                    - N2b
             7.  n1(35)                     - N1
             8.  e1(36)                     - E1
             9.  e2a(37)                    - N2a
             10. e2b(38)                    - N2b
             11. n1n2ae1e2a(39)             - N1/N2a/E1/E2a
             12. px20(65)                   - PX20
             13. px20plus(66)               - PX20+
             14. px20plusplus(67)           - PX20++
             15. pr30(97)                   - PR30
             16. pr20(98)                   - PR20
             17. prx30(99)                  - PRX30
             18. prx20(100)                 - PRX20
             19. prx40(101)                 - PRX40  
             20. pr40(102)                  - PR40   
             21. classbPlusAndPx20Plus(129) - GPON CLASS B+/EPON PX20+
             22. classbAndPx20(130)         - GPON CLASS B/EPON PX20
             23. unknown(145)               - Unknown
             24. invalid(-1)                - Indicates that the query fails or no information is detected
            "
            ::= { hwOpticsDdmInfoExEntry  31 } 
            
        hwOpticsDdmInfoExPrecision OBJECT-TYPE
            SYNTAX      Integer32
            UNITS       "0.1dBm"
            MAX-ACCESS  read-only
            STATUS      current
            DESCRIPTION
                "This object indicates the precision of optical power.
                 Unit: 0.1dBm
                 Options:
                 1. invalid(-1)      - Indicates that the query fails or no information is detected
                "
            ::= { hwOpticsDdmInfoExEntry  32 }

        hwOpticsDdmInfoExEncapsulationType OBJECT-TYPE
            SYNTAX      INTEGER {
                sff2x5(1),
                sff2x10(2),
                sfp(3),
                xfp(4),
                lxfp(5),
                bosaonboard(6),
                unknown(7),
                invalid(-1)
            }
            MAX-ACCESS  read-only
            STATUS      current
            DESCRIPTION
                "Options:
                 1. sff2x5(1)               - SFF 2x5
                 2. sff2x10(2)              - SFF 2x10
                 3. sfp(3)                  - SFP
                 4. xfp(4)                  - XFP
                 5. lxfp(5)                 - LXFP
                 6. bosaonboard(6)          - BOSA ON BOARD
                 7. unknown(7)              - Unknown
                 8. invalid(-1)             - Indicates that the query fails or no information is detected
                "
            ::= { hwOpticsDdmInfoExEntry  33 }

        hwOpticsDdmInfoExVendorPN OBJECT-TYPE
            SYNTAX      OCTET STRING (SIZE (0..17))
            MAX-ACCESS  read-only
            STATUS      current
            DESCRIPTION
                "This object indicates the part number."
            ::= { hwOpticsDdmInfoExEntry  34 }

        hwOpticsDdmInfoExUsedType OBJECT-TYPE
            SYNTAX      INTEGER {
                olt(1),
                onu(3),
                catvtriplex(4),
                unknown(5),
                invalid(-1)
            }
            MAX-ACCESS  read-only
            STATUS      current
            DESCRIPTION
                "This object indicates the application scenario of the optical transceiver.
                 Options:
                 1. olt(1)                 - OLT
                 2. onu(3)                 - ONU
                 3. catvtriplex(4)         - CATV TriPlex
                 4. unknown(5)             - Unknown
                 5. invalid(-1)            - Indicates that the query fails or no information is detected
                "
            ::= { hwOpticsDdmInfoExEntry  35 }

  --Table hwXponDeviceOntDdmInfoExTable
        hwXponDeviceOntDdmInfoExTable OBJECT-TYPE
            SYNTAX      SEQUENCE OF HwXponDeviceOntDdmInfoExEntry
            MAX-ACCESS  not-accessible
            STATUS      current
            DESCRIPTION
                "Table hwXponDeviceOntDdmInfoExTable supports the query of the
                 information about the optical transceiver of the ONT port.
                 The index of this table is a combination of ifIndex and hwXponOntDdmInfoExOntIndex.
                "
            ::= { hwAccessCommonControlObjects 2 }

        hwXponDeviceOntDdmInfoExEntry OBJECT-TYPE
            SYNTAX      HwXponDeviceOntDdmInfoExEntry
            MAX-ACCESS  not-accessible
            STATUS      current
            DESCRIPTION
                "Table hwXponDeviceOntDdmInfoExTable supports the query of the
                 information about the optical transceiver of the ONT port.
                 The index of this entry is a combination of ifIndex and hwXponOntDdmInfoExOntIndex.
                "
            INDEX       { ifIndex, hwXponOntDdmInfoExOntIndex}
            ::= { hwXponDeviceOntDdmInfoExTable 1 }

        HwXponDeviceOntDdmInfoExEntry  ::=
            SEQUENCE {
                hwXponOntDdmInfoExOntIndex                          Integer32,
                hwXponOntDdmInfoExTemperature                       Integer32,
                hwXponOntDdmInfoExTemperatureHighAlarmThreshold     Integer32,
                hwXponOntDdmInfoExTemperatureLowAlarmThreshold      Integer32,
                hwXponOntDdmInfoExTemperatureHighWarningThreshold   Integer32,
                hwXponOntDdmInfoExTemperatureLowWarningThreshold    Integer32,
                hwXponOntDdmInfoExSupplyVoltage                     Integer32,
                hwXponOntDdmInfoExSupplyVoltageHighAlarmThreshold   Integer32,
                hwXponOntDdmInfoExSupplyVoltageLowAlarmThreshold    Integer32,
                hwXponOntDdmInfoExSupplyVoltageHighWarningThreshold Integer32,
                hwXponOntDdmInfoExSupplyVoltageLowWarningThreshold  Integer32,
                hwXponOntDdmInfoExTxBiasCurrent                     Integer32,
                hwXponOntDdmInfoExTxBiasCurrentHighAlarmThreshold   Integer32,
                hwXponOntDdmInfoExTxBiasCurrentLowAlarmThreshold    Integer32,
                hwXponOntDdmInfoExTxBiasCurrentHighWarningThreshold Integer32,
                hwXponOntDdmInfoExTxBiasCurrentLowWarningThreshold  Integer32,
                hwXponOntDdmInfoExTxPower                           Integer32,
                hwXponOntDdmInfoExTxPowerHighAlarmThreshold         Integer32,
                hwXponOntDdmInfoExTxPowerLowAlarmThreshold          Integer32,
                hwXponOntDdmInfoExTxPowerHighWarningThreshold       Integer32,
                hwXponOntDdmInfoExTxPowerLowWarningThreshold        Integer32,
                hwXponOntDdmInfoExRxPower                           Integer32,
                hwXponOntDdmInfoExRxPowerHighAlarmThreshold         Integer32,
                hwXponOntDdmInfoExRxPowerLowAlarmThreshold          Integer32,
                hwXponOntDdmInfoExRxPowerHighWarningThreshold       Integer32,
                hwXponOntDdmInfoExRxPowerLowWarningThreshold        Integer32,
                hwXponOntDdmInfoExOltRxOntPower                     Integer32,
                hwXponOntDdmInfoExCatvRxPowerHighAlarmThreshold     Integer32,
                hwXponOntDdmInfoExCatvRxPowerLowAlarmThreshold      Integer32,
                hwXponOntDdmInfoExModuleType                        INTEGER,
                hwXponOntDdmInfoExSubType                           INTEGER,
                hwXponOntDdmInfoExPrecision                         Integer32,
                hwXponOntDdmInfoExEncapsulationType                 INTEGER,
                hwXponOntDdmInfoExVendorPN                          OCTET STRING,
                      hwXponOntDdmInfoExUsedType                          INTEGER,
                      hwXponOntDdmInfoExPortId                            Integer32,
                      hwXponOntDdmInfoExVendorName                        OCTET STRING,
                      hwXponOntDdmInfoExVendorRev                         OCTET STRING,
                      hwXponOntDdmInfoExVendorSN                          OCTET STRING,
                      hwXponOntDdmInfoExDateCode                          OCTET STRING
            }

        hwXponOntDdmInfoExOntIndex  OBJECT-TYPE
            SYNTAX      Integer32
            MAX-ACCESS  not-accessible
            STATUS      current
            DESCRIPTION
                "ONT ID, range: 0-127"
            ::= { hwXponDeviceOntDdmInfoExEntry 1 }

        hwXponOntDdmInfoExTemperature OBJECT-TYPE
            SYNTAX      Integer32
            UNITS       "0.000001 C(centigrade)"
            MAX-ACCESS  read-only
            STATUS      current
            DESCRIPTION
                "Temperature of the optical transceiver on the ONT.
                 Unit: 0.000001 C(centigrade)
                 Options:
                 1. invalid(0x7FFFFFFF)      - Indicates that the query fails or no information is detected
                "
            ::= { hwXponDeviceOntDdmInfoExEntry  2 }

        hwXponOntDdmInfoExTemperatureHighAlarmThreshold OBJECT-TYPE
            SYNTAX      Integer32
            UNITS       "0.000001 C(centigrade)"
            MAX-ACCESS  read-only
            STATUS      current
            DESCRIPTION
                "Upper alarm threshold of the temperature.
                 Unit: 0.000001 C(centigrade)
                 Options:
                 1. invalid(0x7FFFFFFF)      - Indicates that the query fails or no information is detected
                "
            ::= { hwXponDeviceOntDdmInfoExEntry  3 }

        hwXponOntDdmInfoExTemperatureLowAlarmThreshold OBJECT-TYPE
            SYNTAX      Integer32
            UNITS       "0.000001 C(centigrade)"
            MAX-ACCESS  read-only
            STATUS      current
            DESCRIPTION
                "Lower alarm threshold of the temperature.
                 Unit: 0.000001 C(centigrade)
                 Options:
                 1. invalid(0x7FFFFFFF)      - Indicates that the query fails or no information is detected
                "
            ::= { hwXponDeviceOntDdmInfoExEntry  4 }

        hwXponOntDdmInfoExTemperatureHighWarningThreshold OBJECT-TYPE
            SYNTAX      Integer32
            UNITS       "0.000001 C(centigrade)"
            MAX-ACCESS  read-only
            STATUS      current
            DESCRIPTION
                "Upper warning threshold of the temperature.
                 Unit: 0.000001 C(centigrade)
                 Options:
                 1. invalid(0x7FFFFFFF)      - Indicates that the query fails or no information is detected
                "
            ::= { hwXponDeviceOntDdmInfoExEntry  5 }

        hwXponOntDdmInfoExTemperatureLowWarningThreshold OBJECT-TYPE
            SYNTAX      Integer32
            UNITS       "0.000001 C(centigrade)"
            MAX-ACCESS  read-only
            STATUS      current
            DESCRIPTION
                "Lower warning threshold of the temperature.
                 Unit: 0.000001 C(centigrade)
                 Options:
                 1. invalid(0x7FFFFFFF)      - Indicates that the query fails or no information is detected
                "
            ::= { hwXponDeviceOntDdmInfoExEntry  6 }

        hwXponOntDdmInfoExSupplyVoltage OBJECT-TYPE
            SYNTAX      Integer32
            UNITS       "0.000001V"
            MAX-ACCESS  read-only
            STATUS      current
            DESCRIPTION
                "Voltage of the optical transceiver on the ONT.
                 Unit: 0.000001V
                 Options:
                 1. invalid(0x7FFFFFFF)      - Indicates that the query fails or no information is detected
                "
            ::= { hwXponDeviceOntDdmInfoExEntry  7 }

        hwXponOntDdmInfoExSupplyVoltageHighAlarmThreshold OBJECT-TYPE
            SYNTAX      Integer32
            UNITS       "0.000001V"
            MAX-ACCESS  read-only
            STATUS      current
            DESCRIPTION
                "Upper alarm threshold of the voltage.
                 Unit: 0.000001V
                 Options:
                 1. invalid(0x7FFFFFFF)      - Indicates that the query fails or no information is detected
                "
            ::= { hwXponDeviceOntDdmInfoExEntry  8 }

        hwXponOntDdmInfoExSupplyVoltageLowAlarmThreshold OBJECT-TYPE
            SYNTAX      Integer32
            UNITS       "0.000001V"
            MAX-ACCESS  read-only
            STATUS      current
            DESCRIPTION
                "Lower alarm threshold of the voltage.
                 Unit: 0.000001V
                 Options:
                 1. invalid(0x7FFFFFFF)      - Indicates that the query fails or no information is detected
                "
            ::= { hwXponDeviceOntDdmInfoExEntry  9 }

        hwXponOntDdmInfoExSupplyVoltageHighWarningThreshold OBJECT-TYPE
            SYNTAX      Integer32
            UNITS       "0.000001V"
            MAX-ACCESS  read-only
            STATUS      current
            DESCRIPTION
                "Upper warning threshold of the voltage.
                 Unit: 0.000001V
                 Options:
                 1. invalid(0x7FFFFFFF)      - Indicates that the query fails or no information is detected
                "
            ::= { hwXponDeviceOntDdmInfoExEntry  10 }

        hwXponOntDdmInfoExSupplyVoltageLowWarningThreshold OBJECT-TYPE
            SYNTAX      Integer32
            UNITS       "0.000001V"
            MAX-ACCESS  read-only
            STATUS      current
            DESCRIPTION
                "Lower warning threshold of the voltage.
                 Unit: 0.000001V
                 Options:
                 1. invalid(0x7FFFFFFF)      - Indicates that the query fails or no information is detected
                "
            ::= { hwXponDeviceOntDdmInfoExEntry  11 }

        hwXponOntDdmInfoExTxBiasCurrent OBJECT-TYPE
            SYNTAX      Integer32
            UNITS       "0.000001A"
            MAX-ACCESS  read-only
            STATUS      current
            DESCRIPTION
                "Current of the optical transceiver on the ONT.
                 Unit: 0.000001A
                 Options:
                 1. invalid(-1)      - Indicates that the query fails or no information is detected
                "
            ::= { hwXponDeviceOntDdmInfoExEntry  12 }

        hwXponOntDdmInfoExTxBiasCurrentHighAlarmThreshold OBJECT-TYPE
            SYNTAX      Integer32
            UNITS       "0.000001A"
            MAX-ACCESS  read-only
            STATUS      current
            DESCRIPTION
                "Upper alarm threshold of the bias current.
                 Unit: 0.000001A
                 Options:
                 1. invalid(-1)      - Indicates that the query fails or no information is detected
                "
            ::= { hwXponDeviceOntDdmInfoExEntry  13 }

        hwXponOntDdmInfoExTxBiasCurrentLowAlarmThreshold OBJECT-TYPE
            SYNTAX      Integer32
            UNITS       "0.000001A"
            MAX-ACCESS  read-only
            STATUS      current
            DESCRIPTION
                "Lower alarm threshold of the bias current.
                 Unit: 0.000001A
                 Options:
                 1. invalid(-1)      - Indicates that the query fails or no information is detected
                "
            ::= { hwXponDeviceOntDdmInfoExEntry  14 }

        hwXponOntDdmInfoExTxBiasCurrentHighWarningThreshold OBJECT-TYPE
            SYNTAX      Integer32
            UNITS       "0.000001A"
            MAX-ACCESS  read-only
            STATUS      current
            DESCRIPTION
                "Upper warning threshold of the bias current.
                 Unit: 0.000001A
                 Options:
                 1. invalid(-1)      - Indicates that the query fails or no information is detected
                "
            ::= { hwXponDeviceOntDdmInfoExEntry  15 }

        hwXponOntDdmInfoExTxBiasCurrentLowWarningThreshold OBJECT-TYPE
            SYNTAX      Integer32
            UNITS       "0.000001A"
            MAX-ACCESS  read-only
            STATUS      current
            DESCRIPTION
                "Lower warning threshold of the bias current.
                 Unit: 0.000001A
                 Options:
                 1. invalid(-1)      - Indicates that the query fails or no information is detected
                "
            ::= { hwXponDeviceOntDdmInfoExEntry  16 }

        hwXponOntDdmInfoExTxPower OBJECT-TYPE
            SYNTAX      Integer32
            UNITS       "0.000001dBm"
            MAX-ACCESS  read-only
            STATUS      current
            DESCRIPTION
                "Tx optical power of the optical transceiver on the ONT.
                 Unit: 0.000001dBm
                 Options:
                 1. invalid(0x7FFFFFFF)      - Indicates that the query fails or no information is detected
                "
            ::= { hwXponDeviceOntDdmInfoExEntry  17 }

        hwXponOntDdmInfoExTxPowerHighAlarmThreshold OBJECT-TYPE
            SYNTAX      Integer32
            UNITS       "0.000001dBm"
            MAX-ACCESS  read-only
            STATUS      current
            DESCRIPTION
                "Upper alarm threshold of the Tx power.
                 Unit: 0.000001dBm
                 Options:
                 1. invalid(0x7FFFFFFF)      - Indicates that the query fails or no information is detected
                "
            ::= { hwXponDeviceOntDdmInfoExEntry  18 }

        hwXponOntDdmInfoExTxPowerLowAlarmThreshold OBJECT-TYPE
            SYNTAX      Integer32
            UNITS       "0.000001dBm"
            MAX-ACCESS  read-only
            STATUS      current
            DESCRIPTION
                "Lower alarm threshold of the Tx power.
                 Unit: 0.000001dBm
                 Options:
                 1. invalid(0x7FFFFFFF)      - Indicates that the query fails or no information is detected
                "
            ::= { hwXponDeviceOntDdmInfoExEntry  19 }

        hwXponOntDdmInfoExTxPowerHighWarningThreshold OBJECT-TYPE
            SYNTAX      Integer32
            UNITS       "0.000001dBm"
            MAX-ACCESS  read-only
            STATUS      current
            DESCRIPTION
                "Upper warning threshold of the Tx power.
                 Unit: 0.000001dBm
                 Options:
                 1. invalid(0x7FFFFFFF)      - Indicates that the query fails or no information is detected
                "
            ::= { hwXponDeviceOntDdmInfoExEntry  20 }

        hwXponOntDdmInfoExTxPowerLowWarningThreshold OBJECT-TYPE
            SYNTAX      Integer32
            UNITS       "0.000001dBm"
            MAX-ACCESS  read-only
            STATUS      current
            DESCRIPTION
                "Lower warning threshold of the Tx power.
                 Unit: 0.000001dBm
                 Options:
                 1. invalid(0x7FFFFFFF)      - Indicates that the query fails or no information is detected
                "
            ::= { hwXponDeviceOntDdmInfoExEntry  21 }

        hwXponOntDdmInfoExRxPower OBJECT-TYPE
            SYNTAX      Integer32
            UNITS       "0.000001dBm"
            MAX-ACCESS  read-only
            STATUS      current
            DESCRIPTION
                "Rx optical power of the optical transceiver on the ONT.
                 Unit: 0.000001dBm
                 Options:
                 1. invalid(0x7FFFFFFF)      - Indicates that the query fails or no information is detected
                "
            ::= { hwXponDeviceOntDdmInfoExEntry  22 }

        hwXponOntDdmInfoExRxPowerHighAlarmThreshold   OBJECT-TYPE
            SYNTAX      Integer32
            UNITS       "0.000001dBm"
            MAX-ACCESS  read-only
            STATUS      current
            DESCRIPTION
                "Upper alarm threshold of the Rx power.
                 Unit: 0.000001dBm
                 Options:
                 1. invalid(0x7FFFFFFF)      - Indicates that the query fails or no information is detected
                "
            ::= { hwXponDeviceOntDdmInfoExEntry  23 }

        hwXponOntDdmInfoExRxPowerLowAlarmThreshold OBJECT-TYPE
            SYNTAX      Integer32
            UNITS       "0.000001dBm"
            MAX-ACCESS  read-only
            STATUS      current
            DESCRIPTION
                "Lower alarm threshold of the Rx power.
                 Unit: 0.000001dBm
                 Options:
                 1. invalid(0x7FFFFFFF)      - Indicates that the query fails or no information is detected
                "
            ::= { hwXponDeviceOntDdmInfoExEntry  24 }

        hwXponOntDdmInfoExRxPowerHighWarningThreshold OBJECT-TYPE
            SYNTAX      Integer32
            UNITS       "0.000001dBm"
            MAX-ACCESS  read-only
            STATUS      current
            DESCRIPTION
                "Upper warning threshold of the Rx power.
                 Unit: 0.000001dBm
                 Options:
                 1. invalid(0x7FFFFFFF)      - Indicates that the query fails or no information is detected
                "
            ::= { hwXponDeviceOntDdmInfoExEntry  25 }

        hwXponOntDdmInfoExRxPowerLowWarningThreshold OBJECT-TYPE
            SYNTAX      Integer32
            UNITS       "0.000001dBm"
            MAX-ACCESS  read-only
            STATUS      current
            DESCRIPTION
                "Lower warning threshold of the Rx power.
                 Unit: 0.000001dBm
                 Options:
                 1. invalid(0x7FFFFFFF)      - Indicates that the query fails or no information is detected
                "
            ::= { hwXponDeviceOntDdmInfoExEntry  26 }

        hwXponOntDdmInfoExOltRxOntPower OBJECT-TYPE
            SYNTAX      Integer32
            UNITS       "0.000001dBm"
            MAX-ACCESS  read-only
            STATUS      current
            DESCRIPTION
                "threshold of the ont Tx power.
                 Unit: 0.000001dBm
                 Options:
                 1. invalid(0x7FFFFFFF)      - Indicates that the query fails or no information is detected
                "
            ::= { hwXponDeviceOntDdmInfoExEntry  27 }

         hwXponOntDdmInfoExCatvRxPowerHighAlarmThreshold OBJECT-TYPE
            SYNTAX      Integer32
            UNITS       "0.000001dBm"
            MAX-ACCESS  read-only
            STATUS      current
            DESCRIPTION
                "Upper AlarmThreshold threshold of the CATV Rx power.
                 Unit: 0.000001dBm
                 Options:
                 1. invalid(0x7FFFFFFF)      - Indicates that the query fails or no information is detected
                "
            ::= { hwXponDeviceOntDdmInfoExEntry  28 }

        hwXponOntDdmInfoExCatvRxPowerLowAlarmThreshold OBJECT-TYPE
            SYNTAX      Integer32
            UNITS       "0.000001dBm"
            MAX-ACCESS  read-only
            STATUS      current
            DESCRIPTION
                "Lower AlarmThreshold threshold of the CATV Rx power.
                 Unit: 0.000001dBm
                 Options:
                 1. invalid(0x7FFFFFFF)      - Indicates that the query fails or no information is detected
                "
            ::= { hwXponDeviceOntDdmInfoExEntry  29 }

        hwXponOntDdmInfoExModuleType OBJECT-TYPE
            SYNTAX      INTEGER {
                gpon(1),
                epon(2),
                epon10g(3),
                gpon10g(4),
                wdmpon(5),
                hybridpon(6),
                gponepon(7),
                unknown(8), 
                xgspon(9),
                invalid(-1)
            }
            MAX-ACCESS  read-only
            STATUS      current
            DESCRIPTION
                "Options:
                 1. gpon(1)          - GPON
                 2. epon(2)          - EPON
                 3. epon10g(3)       - 10G EPON
                 4. gpon10g(4)       - 10G GPON
                 5. wdmpon(5)        - WDM PON
                 6. hybridpon(6)     - hybrid PON
                 7. gponepon(7)      - GPON/EPON
                 8. unknown(8)       - Unknown
                 9. xgspon(9)        - XGS-PON
                 10.invalid(-1) - Indicates that the query fails or no information is detected
                "
            ::= { hwXponDeviceOntDdmInfoExEntry  30 }

        hwXponOntDdmInfoExSubType OBJECT-TYPE
            SYNTAX      INTEGER{
                classbplus(1),
                classcplus(2),
                classb(3),
		classcplusplus(4),
                n2a(33),
                n2b(34),
                n1(35),
                e1(36),
                e2a(37),
                e2b(38),
                n1n2ae1e2a(39),
                px20(65),
                px20plus(66),
                px20plusplus(67),
                pr30(97),
                pr20(98),
                prx30(99),
                prx20(100),
                prx40(101),
                pr40(102),
                classbPlusAndPx20Plus(129),
                classbAndPx20(130),
                unknown(145),
                invalid(-1)
            }
            MAX-ACCESS  read-only
            STATUS      current
            DESCRIPTION
                "Options:
                 1.  classbplus(1)              - CLASS B+
                 2.  classcplus(2)              - CLASS C+
                 3.  classb(3)                  - CLASS B
                 4.  classcplusplus(4)          - CLASS C++
                 5.  n2a(33)                    - N2a
                 6.  n2b(34)                    - N2b
                 7.  n1(35)                     - N1
                 8.  e1(36)                     - E1
                 9.  e2a(37)                    - N2a
                 10. e2b(38)                    - N2b
                 11. n1n2ae1e2a(39)             - N1/N2a/E1/E2a
                 12. px20(65)                   - PX20
                 13. px20plus(66)               - PX20+
                 14. px20plusplus(67)           - PX20++
                 15. pr30(97)                   - PR30
                 16. pr20(98)                   - PR20
                 17. prx30(99)                  - PRX30
                 18. prx20(100)                 - PRX20
                 19. prx40(101)                 - PRX40  
                 20. pr40(102)                  - PR40   
                 21. classbPlusAndPx20Plus(129) - GPON CLASS B+/EPON PX20+
                 22. classbAndPx20(130)         - GPON CLASS B/EPON PX20
                 23. unknown(145)               - Unknown
                 24. invalid(-1)                - Indicates that the query fails or no information is detected
                "
            ::= { hwXponDeviceOntDdmInfoExEntry  31 }

        hwXponOntDdmInfoExPrecision OBJECT-TYPE
            SYNTAX      Integer32
            UNITS       "0.1dBm"
            MAX-ACCESS  read-only
            STATUS      current
            DESCRIPTION
                "This object indicates the precision of optical power.
                 Unit: 0.1dBm
                 Options:
                 1. invalid(-1)      - Indicates that the query fails or no information is detected
                "
            ::= { hwXponDeviceOntDdmInfoExEntry  32 }

        hwXponOntDdmInfoExEncapsulationType OBJECT-TYPE
            SYNTAX      INTEGER
            {
                sff2x5(1),
                sff2x10(2),
                sfp(3),
                xfp(4),
                lxfp(5),
                bosaonboard(6),
                unknown(7),
                invalid(-1)
            }
            MAX-ACCESS  read-only
            STATUS      current
            DESCRIPTION
                "Options:
                 1. sff2x5(1)               - SFF 2x5
                 2. sff2x10(2)              - SFF 2x10
                 3. sfp(3)                  - SFP
                 4. xfp(4)                  - XFP
                 5. lxfp(5)                 - LXFP
                 6. bosaonboard(6)          - BOSA ON BOARD
                 7. unknown(7)              - Unknown
                 8. invalid(-1)             - Indicates that the query fails or no information is detected
                "
            ::= { hwXponDeviceOntDdmInfoExEntry  33 }

        hwXponOntDdmInfoExVendorPN OBJECT-TYPE
            SYNTAX      OCTET STRING (SIZE (0..17))
            MAX-ACCESS  read-only
            STATUS      current
            DESCRIPTION
                "This object indicates the part number."
            ::= { hwXponDeviceOntDdmInfoExEntry  34 }

        hwXponOntDdmInfoExUsedType OBJECT-TYPE
            SYNTAX      INTEGER {
                olt(1),
                onu(3),
                catvtriplex(4),
                unknown(5),
                sfponu(6),
                invalid(-1)
            }
            MAX-ACCESS  read-only
            STATUS      current
            DESCRIPTION
                "This object indicates the application scenario of the optical transceiver.
                 Options:
                 1. olt(1)                 - OLT
                 2. onu(3)                 - ONU
                 3. catvtriplex(4)         - CATV TriPlex
                 4. unknown(5)             - Unknown
                 5. sfponu(6)              - SFP ONU
                 6. invalid(-1)            - Indicates that the query fails or no information is detected
                "
            ::= { hwXponDeviceOntDdmInfoExEntry  35 }
        hwXponOntDdmInfoExPortId OBJECT-TYPE
            SYNTAX Integer32 (-1 | 0..1)
            MAX-ACCESS  read-only
            STATUS      current
            DESCRIPTION
                "This object indicates the ID of the ONT PON port where the optical module is located. 
                 It is numbered from 0. 
                 Options:
                 1. invalid(-1)      - Indicates that the query fails or no information is detected
                "
            ::= { hwXponDeviceOntDdmInfoExEntry  36 } 
        hwXponOntDdmInfoExVendorName OBJECT-TYPE
            SYNTAX OCTET STRING (SIZE (0..17))
            MAX-ACCESS read-only
            STATUS current
            DESCRIPTION
                "This object indicates the SFP vendor name (ASCII)."
            ::= { hwXponDeviceOntDdmInfoExEntry  37 }            
        hwXponOntDdmInfoExVendorRev OBJECT-TYPE
            SYNTAX OCTET STRING (SIZE (0..5))
            MAX-ACCESS read-only
            STATUS current
            DESCRIPTION
                "This object indicates the revision level for part number provided by vendor (ASCII)."
            ::= { hwXponDeviceOntDdmInfoExEntry  38 }            
        hwXponOntDdmInfoExVendorSN OBJECT-TYPE
            SYNTAX OCTET STRING (SIZE (0..17))
            MAX-ACCESS read-only
            STATUS current
            DESCRIPTION
                "This object indicates the serial number provided by vendor (ASCII)."
            ::= { hwXponDeviceOntDdmInfoExEntry  39 }            
        hwXponOntDdmInfoExDateCode OBJECT-TYPE
            SYNTAX OCTET STRING (SIZE (0..17))
            MAX-ACCESS read-only
            STATUS current
            DESCRIPTION
                "This object indicates manufacturing date code of the vendor (ASCII)."
            ::= { hwXponDeviceOntDdmInfoExEntry  40 }   
	    
	             
  --Table hwXponNniOpticsModuleInfoTable
        hwXponNniOpticsModuleInfoTable OBJECT-TYPE
            SYNTAX      SEQUENCE OF HwXponNniOpticsModuleInfoEntry
            MAX-ACCESS  not-accessible
            STATUS      current
            DESCRIPTION
                "The table supports the query of the
                 information about the optical transceiver of the ONT port.
                 The index of this table is ifIndex.
                "
            ::= { hwAccessCommonControlObjects 3 }

        hwXponNniOpticsModuleInfoEntry OBJECT-TYPE
            SYNTAX      HwXponNniOpticsModuleInfoEntry
            MAX-ACCESS  not-accessible
            STATUS      current
            DESCRIPTION
                "The table supports the query of the
                 information about the optical transceiver of the ONT port.
                 The index of this entry is ifIndex.
                "
            INDEX       { ifIndex }
            ::= { hwXponNniOpticsModuleInfoTable 1 }

        HwXponNniOpticsModuleInfoEntry  ::=
            SEQUENCE {
                hwXponNniOpticsModuleInfoVendorName                      OCTET STRING,
                hwXponNniOpticsModuleInfoVendorRev                       OCTET STRING,
                hwXponNniOpticsModuleInfoVendorOUI                       OCTET STRING,
                hwXponNniOpticsModuleInfoVendorPN                        OCTET STRING,
                hwXponNniOpticsModuleInfoVendorSN                        OCTET STRING,
                hwXponNniOpticsModuleInfoDateCode                        OCTET STRING,
                hwXponNniOpticsModuleInfoSFF8472Compliance               INTEGER,
                hwXponNniOpticsModuleInfoWaveLength                      Integer32,
                hwXponNniOpticsModuleInfoIdentifier                      INTEGER,
                hwXponNniOpticsModuleInfoExtID                           INTEGER,
                hwXponNniOpticsModuleInfoConnector                       INTEGER,
                hwXponNniOpticsModuleInfoEncoding                        INTEGER,
                hwXponNniOpticsModuleInfoLength9Micronkm                 Integer32,
                hwXponNniOpticsModuleInfoLength50Micron                  Integer32,
                hwXponNniOpticsModuleInfoLength62Micron5                 Integer32,
                hwXponNniOpticsModuleInfoLengthCopper                    Integer32,
                hwXponNniOpticsModuleInfoLengthOm3                       Integer32,
                hwXponNniOpticsModuleInfoBrMax                           Integer32,
                hwXponNniOpticsModuleInfoBrMin                           Integer32,
                hwXponNniOpticsModuleInfoBrNominal                       Integer32,
                hwXponNniOpticsModuleInfoDiagnosticMonitoringType        Integer32,
                hwXponNniOpticsModuleInfoOptions                         Integer32,
                hwXponNniOpticsModuleInfoEnhancedOptions                 Integer32,
                hwXponNniOpticsModuleInfoCcBase                          Integer32,
                hwXponNniOpticsModuleInfoCcExt                           Integer32,
                hwXponNniOpticsModuleInfoRateIdentifier                  INTEGER
            }

        hwXponNniOpticsModuleInfoVendorName  OBJECT-TYPE
            SYNTAX      OCTET STRING (SIZE (0..17))
            MAX-ACCESS  read-only
            STATUS      current
            DESCRIPTION
                "This object indicates the vendor name."
            ::= { hwXponNniOpticsModuleInfoEntry 1 }

        hwXponNniOpticsModuleInfoVendorRev  OBJECT-TYPE
            SYNTAX      OCTET STRING (SIZE (0..5))
            MAX-ACCESS  read-only
            STATUS      current
            DESCRIPTION
                "This object indicates the revision level for part number provided by vendor."
            ::= { hwXponNniOpticsModuleInfoEntry 2 }

        hwXponNniOpticsModuleInfoVendorOUI  OBJECT-TYPE
            SYNTAX      OCTET STRING (SIZE (0..9))
            MAX-ACCESS  read-only
            STATUS      current
            DESCRIPTION
                "This object indicates the vendor IEEE company ID."
            ::= { hwXponNniOpticsModuleInfoEntry 3 }

        hwXponNniOpticsModuleInfoVendorPN  OBJECT-TYPE
            SYNTAX      OCTET STRING (SIZE (0..17))
            MAX-ACCESS  read-only
            STATUS      current
            DESCRIPTION
                "This object indicates the part number provided by vendor."
            ::= { hwXponNniOpticsModuleInfoEntry 4 }

        hwXponNniOpticsModuleInfoVendorSN  OBJECT-TYPE
            SYNTAX      OCTET STRING (SIZE (0..17))
            MAX-ACCESS  read-only
            STATUS      current
            DESCRIPTION
                "This object indicates the serial number provided by vendor."
            ::= { hwXponNniOpticsModuleInfoEntry 5 }

        hwXponNniOpticsModuleInfoDateCode  OBJECT-TYPE
            SYNTAX      OCTET STRING (SIZE (0..17))
            MAX-ACCESS  read-only
            STATUS      current
            DESCRIPTION
                "This object indicates manufacturing date code of the vendor."
            ::= { hwXponNniOpticsModuleInfoEntry 6 }

        hwXponNniOpticsModuleInfoSFF8472Compliance  OBJECT-TYPE
            SYNTAX      INTEGER {
                undefined(1),
                includesRev93SFF8472(2),
                includesRev94SFF8472(3),
                includesRev95SFF8472(4),
                includesRev102SFF8472(5),
                includesRev104SFF8472(6),
                includesRev110SFF8472(7),
                invalid(-1)
            }
            MAX-ACCESS  read-only
            STATUS      current
            DESCRIPTION
                "Indicates which revision of SFF-8472 the transceiver complies
                 Options:
                 1. undefined(1)               - Not included or undefined
                 2. includesRev93SFF8472(2)    - Includes functionality described in Rev 9.3
                 3. includesRev94SFF8472(3)    - Includes functionality described in Rev 9.4
                 4. includesRev95SFF8472(4)    - Includes functionality described in Rev 9.5
                 5. includesRev102SFF8472(5)   - Includes functionality described in Rev 10.2
                 6. includesRev104SFF8472(6)   - Includes functionality described in Rev 10.4
                 7. includesRev110SFF8472(7)   - Includes functionality described in Rev 11.0
                 8. invalid (-1)               - Indicates that the query fails or no information is detected
                "
            ::= { hwXponNniOpticsModuleInfoEntry 7 }

        hwXponNniOpticsModuleInfoWaveLength  OBJECT-TYPE
            SYNTAX      Integer32
            MAX-ACCESS  read-only
            STATUS      current
            DESCRIPTION
                "This object indicates the laser wavelength, units of nm."
            ::= { hwXponNniOpticsModuleInfoEntry 8 }

        hwXponNniOpticsModuleInfoIdentifier  OBJECT-TYPE
            SYNTAX      INTEGER {
                unknown(1),
                gbic(2),
                solderedToMotherboard(3),
                sfporsfpplus(4),
                invalid(-1)
            }
            MAX-ACCESS  read-only
            STATUS      current
            DESCRIPTION
                "This object indicates the type of serial transceiver.
                 Options:
                 1. unknown(1)                      - Unknown or unspecified
                 2. gbic(2)                         - GBIC
                 3. solderedToMotherboard(3)        - Module soldered to motherboard
                 4. sfporsfpplus(4)                 - SFP or SFP Plus
                 5. invalid(-1)                     - Indicates that the query fails or no information is detected
                "
            ::= { hwXponNniOpticsModuleInfoEntry 9 }

        hwXponNniOpticsModuleInfoExtID  OBJECT-TYPE
            SYNTAX      INTEGER {
                notSpecifiedOrNotCompliant(1),
                moddef1(2),
                moddef2(3),
                moddef3(4),
                bySerialIDOnly(5),
                moddef5(6),
                moddef6(7),
                moddef7(8),
                invalid(-1)
            }
            MAX-ACCESS  read-only
            STATUS      current
            DESCRIPTION
                "This object indicates the extended identifier of type of serial transceiver.
                 Options:
                 1. notSpecifiedOrNotCompliant(1)   - Not specified or not compliant with a defined MOD_DEF
                 2. moddef1(2)                      - GBIC is compliant with MOD_DEF 1
                 3. moddef2(3)                      - GBIC is compliant with MOD_DEF 2
                 4. moddef3(4)                      - GBIC is compliant with MOD_DEF 3
                 5. bySerialIDOnly(5)               - GBIC/SFP function is defined by serial ID only
                 6. moddef5(6)                      - GBIC is compliant with MOD_DEF 5
                 7. moddef6(7)                      - GBIC is compliant with MOD_DEF 6
                 8. moddef7(8)                      - GBIC is compliant with MOD_DEF 7
                 9. invalid(-1)                     - Indicates that the query fails or no information is detected
                "
            ::= { hwXponNniOpticsModuleInfoEntry 10 }

        hwXponNniOpticsModuleInfoConnector  OBJECT-TYPE
            SYNTAX      INTEGER {
                unknown(1),
                sc(2),
                copperConnector1(3),
                copperConnector2(4),
                bnctnc(5),
                coaxialHeaders(6),
                fiberJack(7),
                lc(8),
                mtrj(9),
                mu(10),
                sg(11),
                opticalPigtail(12),
                hssdcII(13),
                copperPigtail(14),
                invalid(-1)
            }
            MAX-ACCESS  read-only
            STATUS      current
            DESCRIPTION
                "This object indicates the code for connector type.
                 Options:
                 1.  unknown(1)              - Unknown
                 2.  sc(2)                   - SC
                 3.  copperConnector1(3)     - Fibre Channel Style 1 copper connector
                 4.  copperConnector2(4)     - Fibre Channel Style 2 copper connector
                 5.  bnctnc(5)               - BNC/TNC
                 6.  coaxialHeaders(6)       - Fibre Channel coaxial headers
                 7.  fiberJack(7)            - FiberJack
                 8.  lc(8)                   - LC
                 9.  mtrj(9)                 - MT-RJ
                 10. mu(10)                  - MU
                 11. sg(11)                  - SG
                 12. opticalPigtail(12)      - Optical pigtail
                 13. hssdcII(13)             - HSSDC II
                 14. copperPigtail(14)       - Copper Pigtail
                 15. invalid(-1)             - Indicates that the query fails or no information is detected
                "
                ::= { hwXponNniOpticsModuleInfoEntry 11 }

        hwXponNniOpticsModuleInfoEncoding  OBJECT-TYPE
            SYNTAX      INTEGER {
                unspecified(1),
                encodingMethod8B10B(2),
                encodingMethod4B5B(3),
                nrz(4),
                manchester(5),
                sonetScrambled(6),
                encodingMethod64B66B(7),
                invalid(-1)
            }
            MAX-ACCESS  read-only
            STATUS      current
            DESCRIPTION
                "This object indicates the code for serial encoding algorithm.
                 Options:
                 1. unspecified(1)            - Unspecified
                 2. encodingMethod8B10B(2)    - 8B10B
                 3. encodingMethod4B5B(3)     - 4B5B
                 4. nrz(4)                    - NRZ
                 5. manchester(5)             - Manchester
                 6. sonetScrambled(6)         - SONET Scrambled
                 7. encodingMethod64B66B(7)   - 64B66B
                 8. invalid(-1)               - Indicates that the query fails or no information is detected
                "
            ::= { hwXponNniOpticsModuleInfoEntry 12 }

        hwXponNniOpticsModuleInfoLength9Micronkm  OBJECT-TYPE
            SYNTAX      Integer32
            MAX-ACCESS  read-only
            STATUS      current
            DESCRIPTION
                "This object indicates the link length supported for 9/125 micron fiber, units of 1000 m."
            ::= { hwXponNniOpticsModuleInfoEntry 13 }

        hwXponNniOpticsModuleInfoLength50Micron  OBJECT-TYPE
            SYNTAX      Integer32
            MAX-ACCESS  read-only
            STATUS      current
            DESCRIPTION
                "This object indicates the link length supported for 50/125 micron fiber, units of 10 m."
            ::= { hwXponNniOpticsModuleInfoEntry 14 }

        hwXponNniOpticsModuleInfoLength62Micron5  OBJECT-TYPE
            SYNTAX      Integer32
            MAX-ACCESS  read-only
            STATUS      current
            DESCRIPTION
                "This object indicates the link length supported for 62.5/125 micron fiber, units of 10 m."
            ::= { hwXponNniOpticsModuleInfoEntry 15 }

        hwXponNniOpticsModuleInfoLengthCopper  OBJECT-TYPE
            SYNTAX      Integer32
            MAX-ACCESS  read-only
            STATUS      current
            DESCRIPTION
                "This object indicates the link length supported for copper, units of meters."
            ::= { hwXponNniOpticsModuleInfoEntry 16 }

        hwXponNniOpticsModuleInfoLengthOm3  OBJECT-TYPE
            SYNTAX      Integer32
            MAX-ACCESS  read-only
            STATUS      current
            DESCRIPTION
                "This object indicates the link length supported for 50/125 micron OM3 fiber, units of 10 m."
            ::= { hwXponNniOpticsModuleInfoEntry 17 }

        hwXponNniOpticsModuleInfoBrMax  OBJECT-TYPE
            SYNTAX      Integer32
            MAX-ACCESS  read-only
            STATUS      current
            DESCRIPTION
                "This object indicates the upper bit rate margin, units of %."
            ::= { hwXponNniOpticsModuleInfoEntry 18 }

        hwXponNniOpticsModuleInfoBrMin  OBJECT-TYPE
            SYNTAX      Integer32
            MAX-ACCESS  read-only
            STATUS      current
            DESCRIPTION
                "This object indicates the lower bit rate margin, units of %."
            ::= { hwXponNniOpticsModuleInfoEntry 19 }

        hwXponNniOpticsModuleInfoBrNominal  OBJECT-TYPE
            SYNTAX      Integer32
            MAX-ACCESS  read-only
            STATUS      current
            DESCRIPTION
                "This object indicates the nominal bit rate, units of 100 MBits/sec."
            ::= { hwXponNniOpticsModuleInfoEntry 20 }

        hwXponNniOpticsModuleInfoDiagnosticMonitoringType  OBJECT-TYPE
            SYNTAX      Integer32
            MAX-ACCESS  read-only
            STATUS      current
            DESCRIPTION
                "Indicates which type of diagnostic monitoring is implemented.
                 bit                 Description of Diagnostic Monitoring Type
                  7                  Reserved
                  6                  Digital diagnostic monitoring
                  5                  Internally Calibrated
                  4                  Externally Calibrated
                  3                  Received power measurement type:(0 = OMA, 1 = Average)
                  2                  Address change required
                  1-0                Reserved
                "
            ::= { hwXponNniOpticsModuleInfoEntry 21 }

        hwXponNniOpticsModuleInfoOptions  OBJECT-TYPE
            SYNTAX      Integer32
            MAX-ACCESS  read-only
            STATUS      current
            DESCRIPTION
                "Indicates which optional transceiver signals are implemented.
                  bit                 Description of option
                  10                  Cooled Transceiver Declaration
                   9                  Power Level Declaration
                   8                  Linear Receiver Output Implemented
                  7-6                 Reserved
                   5                  RATE_SELECT
                   4                  TX_DISABLE
                   3                  TX_FAULT
                   2                  LOS (signal inverted from standard definition)
                   1                  LOS (signal as defined in SFP MSA)
                   0                  Reserved
                "
            ::= { hwXponNniOpticsModuleInfoEntry 22 }

        hwXponNniOpticsModuleInfoEnhancedOptions  OBJECT-TYPE
            SYNTAX      Integer32
            MAX-ACCESS  read-only
            STATUS      current
            DESCRIPTION
                "Indicates which optional enhanced features are implemented.
                 bit                 Description of Enhanced Options
                  7                  Alarm/warning flags
                  6                  TX_DISABLE control and monitoring
                  5                  TX_FAULT monitoring
                  4                  RX_LOS monitoring
                  3                  RATE_SELECT control and monitoring
                  2                  Application Select control SFF-8079
                  1                  Soft Rate Select per per SFF-8431
                  0                  Reserved
                "
            ::= { hwXponNniOpticsModuleInfoEntry 23 }

        hwXponNniOpticsModuleInfoCcBase  OBJECT-TYPE
            SYNTAX      Integer32
            MAX-ACCESS  read-only
            STATUS      current
            DESCRIPTION
                "This object indicates the check code for Base ID Fields."
            ::= { hwXponNniOpticsModuleInfoEntry 24 }

        hwXponNniOpticsModuleInfoCcExt  OBJECT-TYPE
            SYNTAX      Integer32
            MAX-ACCESS  read-only
            STATUS      current
            DESCRIPTION
                "This object indicates the check code for the Extended ID Fields."
            ::= { hwXponNniOpticsModuleInfoEntry 25 }

        hwXponNniOpticsModuleInfoRateIdentifier  OBJECT-TYPE
            SYNTAX      INTEGER {
                undefined1(1),
                sff8079(2),
                sff8431Rx(3),
                undefined2(4),
                sff8431Tx(5),
                undefined3(6),
                sff8431IndependentRxAndTx(7),
                undefined4(8),
                fcpi5Rx(9),
                undefined5(10),
                fcpi5IndependentRxAndTx(11),
                invalid(-1)
            }
            MAX-ACCESS  read-only
            STATUS      current
            DESCRIPTION
                "This object indicates the code for connector type.
                 Options:
                 1.  undefined1(1)                    - Not included or undefined
                 2.  sff8079(2)                      - SFF-8079 4/2/1GRate_Select&AS0/AS1
                 3.  sff8431Rx(3)                    - SFF-8431 8/4/2G Rx Rate_Select only
                 4.  undefined2(4)                    - Not included or undefined
                 5.  sff8431Tx(5)                    - SFF-8431 8/4/2G Tx Rate_Select only
                 6.  undefined3(6)                    - Not included or undefined
                 7.  sff8431IndependentRxAndTx(7)    - SFF-8431 8/4/2G Independent Rx&Tx Rate_select
                 8.  undefined4(8)                    - Not included or undefined
                 9.  fcpi5Rx(9)                      - FC-PI-516/8/4G Rx Rate_select only High=16G only Low=8G/4G
                 10. undefined5(10)                   - Not included or undefined
                 11. fcpi5IndependentRxAndTx(11)     - FC-PI-5 16/8/4G Independent Rx&Tx Rate_select High=16G only Low=8G/4G
                 12. invalid(-1)                     - Indicates that the query fails or no information is detected
                "
            ::= { hwXponNniOpticsModuleInfoEntry 26 }

        -- trapVboids define
        hwPortHostmode OBJECT-TYPE
            SYNTAX      INTEGER {
                geMode(7),
                adaptMode(27),
                gponMode(114),
                eponMode(115)
            }
            MAX-ACCESS  accessible-for-notify
            STATUS      current
            DESCRIPTION
                "The port host mode.
                 Options:
                 1. geMode(7)     - Ge mode
                 2. adaptMode(27) - Adapt mode
                 3. gponMode(114) - Gpon mode
                 4. eponMode(115) - Epon mode
                "
            ::= { hwLineCommonTrapsVbOids 1 }

        hwPortActualmode OBJECT-TYPE
            SYNTAX      INTEGER {
                geMode(7),
                adaptMode(27),
                gponMode(114),
                eponMode(115),
                unknown(65535)
            }
            MAX-ACCESS  accessible-for-notify
            STATUS      current
            DESCRIPTION
                "The port actual mode.
                 Options:
                 1. geMode(7)     - Ge mode
                 2. adaptMode(27) - Adapt mode
                 3. gponMode(114) - Gpon mode
                 4. eponMode(115) - Epon mode
                 5. unknown(65535) - Unknown mode
                "
            ::= { hwLineCommonTrapsVbOids 2 }

        hwReservedValue OBJECT-TYPE
            SYNTAX      Integer32
            MAX-ACCESS  accessible-for-notify
            STATUS      current
            DESCRIPTION
                "Reserved value."
            ::= { hwLineCommonTrapsVbOids   3 }

        -- alarm trap define
        hwPortTypeAdaptFaultAlarmTrap NOTIFICATION-TYPE
            OBJECTS {
                hwFrameIndex,
                hwSlotIndex,
                hwPortIndex,
                hwPortHostmode,
                hwPortActualmode
            }
            STATUS      current
            DESCRIPTION
                "Port type adaptation fault alarm trap.
                 This trap message is generated when the uplink port on the ONU is set to work in adaptive mode,
                 the type of the OLT downlink port transmitting the optical signal is different from the type of
                 the uplink port on the ONU. As a result, the uplink port on the ONU is faulty.
                "
            ::= { hwLineAlarmTraps 0 1 }

        hwPortTypeAdaptFaultRestoreAlarmTrap NOTIFICATION-TYPE
            OBJECTS {
                hwFrameIndex,
                hwSlotIndex,
                hwPortIndex,
                hwPortHostmode,
                hwPortActualmode
                }
            STATUS      current
            DESCRIPTION
                "Port type adaptation fault recovery alarm trap.
                 This trap message is generated when the uplink port on the ONU is set to work in adaptive mode,
                 the type of the OLT downlink port transmitting the optical signal is the same as the type of
                 the uplink port on the ONU, and the service on the uplink port is restored.
                "
            ::= { hwLineAlarmTraps 0 2 }

        hwPortTypeAdaptSuccessAlarmTrap NOTIFICATION-TYPE
            OBJECTS {
                 hwFrameIndex,
                 hwSlotIndex,
                 hwPortIndex,
                 hwPortHostmode,
                 hwPortActualmode
             }
            STATUS      current
            DESCRIPTION
                "Port type adaptation success alarm trap.
                 This trap message is generated when the type of the OLT downlink port transmitting the optical signal changes,
                 the adaptation of the uplink port on the ONU is successful.
                "
            ::= { hwLineAlarmTraps 0 3 }

        hwXponnniPortSwitchAlarmTrap NOTIFICATION-TYPE
            OBJECTS {
                hwFrameIndex,
                hwSlotIndex,
                hwPortIndex,
                hwPortIndex
            }
            STATUS      current
            DESCRIPTION
                "Protection switchover occurs on the PON port and it has no effect on the service.
                 The first hwPortIndex is the source port index,
                 the second hwPortIndex is the destination port index.
                "
            ::= { hwLineAlarmTraps 0 4 }

        -- common trap define
        hwXponnniPortSwitchTrap NOTIFICATION-TYPE
            OBJECTS {
                hwReservedValue,
                ifIndex,
                ifIndex
            }
            STATUS      current
            DESCRIPTION
                "TypeC or TypeD port switch trap.
                 The first ifIndex is the active one after switching over.
                 The second ifIndex is the standby one after switching over.
                "
            ::= { hwLineTraps 0 1 }

  END
