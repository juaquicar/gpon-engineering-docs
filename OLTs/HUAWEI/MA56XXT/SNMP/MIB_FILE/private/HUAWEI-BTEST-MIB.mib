-- ============================================================================
-- Copyright (C) 2012 by  HUAWEI TECHNOLOGIES. All rights reserved.
-- Description:  This MIB is used for defining Huawei's BTEST MIB objects, which 
--               is used for Broad test.
-- Reference:  
-- Version: V3.15
-- ============================================================================
    HUAWEI-BTEST-MIB DEFINITIONS ::= BEGIN
    
        IMPORTS
            huaweiUtility                   
                FROM HUAWEI-MIB         
            HWPortType                      
                FROM HUAWEI-TC-MIB                              
            ifIndex                 
                FROM IF-MIB                     
            hwFrameIndex,hwSlotIndex
                FROM HUAWEI-DEVICE-MIB
            Integer32, Unsigned32, OBJECT-TYPE, MODULE-IDENTITY, NOTIFICATION-TYPE                  
                FROM SNMPv2-SMI                 
            TEXTUAL-CONVENTION, RowStatus                   
                FROM SNMPv2-TC
            hwTestGroupNo
                FROM HUAWEI-COMMTEST-MIB;
    
		hwBtest MODULE-IDENTITY 
            LAST-UPDATED "201201090000Z"
            ORGANIZATION "Huawei Technologies Co.,Ltd."
            CONTACT-INFO 
                   "Huawei Industrial Base
                    Bantian, Longgang
                    Shenzhen 518129
                    People's Republic of China
                    Website: http://www.huawei.com
                    Email: support@huawei.com
                   "
            DESCRIPTION  "This MIB is used for defining Huawei's BTEST MIB objects,which
                          is used for Broad test.
                         "
    
    --  Revision history
            REVISION    "201201090000Z" 
	    DESCRIPTION "V3.14, modify the description of the leaf hwBTSSAdslSeltTestParamUnCalibLineScale, hwBTSSAdslSeltTestParamUnCalibEchoRespReal, 
                         hwBTSSAdslSeltTestParamUnCalibEchoRespImg, hwBTSSAdslSeltTestParamCalibEchoRespReal, hwBTSSAdslSeltTestParamCalibEchoRespImg, 
                         hwBTSSAdslSeltTestParamVarUerC, hwBTSSAdslSeltTestParamQSPsdValue, hwBTSSAdslSeltTestParamUpShnCap, hwBTSSAdslSeltTestParamAttnAt180KHZ,
                         hwBTSSAdslSeltTestParamAttnAt300KHZ, hwBTSSAdslSeltTestParamUerMmdC, hwBTSSAdslSeltTestParamQlnMmdC.
	                "
    
            REVISION    "201105040000Z" 
	    DESCRIPTION "V3.13, add leaf node hwBTSSAdslSeltTestParamCalcEnable of hwBTSSAdslSeltTestTable for setting selt test calculation switch.
                         Add hwBTSSAdslSeltCalibrationTable for describing calibration data of selt test.
	                "
            REVISION    "201102220000Z" 
	    DESCRIPTION "V3.12, changes in this revision:
	                 modify the description of the leaf hwBTSSTestedPortOperMode,hwBTSSAdslSeltTestParamUmeC,
	                 hwBTSSAdslSeltTestParamCalibLineScale,hwBTSSAdslSeltTestParamQmeC,
	                 hwBTSSAdslSeltTestParamUnCalibLineScale,hwBTSSTestedPortOperMode.
	                "
	                     
            REVISION    "201102129000Z" 
	    DESCRIPTION "V3.11, changes in this revision:
	                 Add value resumeport(5) for hwBTSSTestedPortOperType.
	                "
    
            REVISION    "201010290000Z" 
	    DESCRIPTION "V3.10, changes in this revision:
	                 Add value -1(invalid) for hwBTSSAdslSeltLevel and modify the description.
	                "
	                
	    REVISION    "201009290000Z" 
	    DESCRIPTION "V3.09, changes in this revision:
	                 Add leaf node for new standard, include: 	
	             	 hwBTSSAdslSeltTestParamVarUerC 
	     		 hwBTSSAdslSeltTestParamUerMmdC 
	     		 hwBTSSAdslSeltTestParamQlnMmdC 
	                 hwBTSSAdslSeltTestParamUmeC 
	                 hwBTSSAdslSeltTestParamQmeC 
	                 hwBTSSAdslSeltTestParamUerStatus  
	                 hwBTSSAdslSeltTestParamQlnStatus  
                         Modify the range of leaf node, include: 
                    	 hwBTSSAdslSeltTestParamUnCalibLineScale 
                         hwBTSSAdslSeltTestParamUnCalibEchoRespReal 
	                 hwBTSSAdslSeltTestParamUnCalibEchoRespImg 
                         hwBTSSAdslSeltTestParamCalibLineScale 
                         hwBTSSAdslSeltTestParamCalibEchoRespReal 
	                 hwBTSSAdslSeltTestParamCalibEchoRespImg 
	                 hwBTSSAdslSeltTestParamQSPsdValue  
	                "      	  

            REVISION    "201009270900Z" 
	    DESCRIPTION "V3.08, changes in this revision:
	                 modify the description of the hwBTSSCaptureTrap.
	                "

            REVISION    "201007120900Z" 
	    DESCRIPTION "V3.07, changes in this revision:
	                 Add value -1(invalid) for hwBTSSTestedPortOperType and six enumerate values for hwBTSSTestedPortOperMode
	                 to support get operation.
	                "

            REVISION    "201006220900Z" 
	    DESCRIPTION "V3.06, changes in this revision:
	                 Modify chinese character.
	                "
	                    
            REVISION    "201003220000Z" 
            DESCRIPTION "V3.05, changes in this revision:
                         Add leaf node hwBTSSAdslSeltTestOperType of hwBTSSAdslSeltTestTable for setting or obtaining selt test
                         operation type.
                         Add leaf node hwBTSSAdslSeltTestParamLoopTermin of hwBTSSAdslSeltTestTable for obtaining selt test
                         parameter Loop Termination.
                         Add leaf node hwBTSSAdslSeltTestParamLoopGauge of hwBTSSAdslSeltTestTable for setting or obtaining selt
                         test parameter Loop Gauge.
                         Add leaf node hwBTSSAdslDeltTestOperType of hwBTSSAdslDeltTestTable for setting or obtaining delt test
                         operation type. 
                         Modify MAX-ACCESS ,include: 
                         hwBTSSAdslSeltTestParamAttnAt180KHZ
                         hwBTSSAdslSeltTestParamAttnAt300KHZ
                         hwBTSSAdslSeltTestParamQSPsdValue
                        "
	                    
            REVISION    "201002080000Z" 
            DESCRIPTION "V3.04, changes in this revision:
	                 Delete the definition of the trap node,include: 	
	               	 hwBTSSCaptureTrap
                         hwBTSSSeltStartReplyTrap
	                 hwBTSSSeltTestResultFirstFrameTrap
	                 hwBTSSSeltTestResultSecondFrameTrap
	                 hwBTSSSeltTestResultThirdFrameTrap
	                 hwBTSSSeltTestResultFourFrameTrap
 	                 hwBTSSSeltTestResultFifthsFrameTrap
	                 hwBTSSSeltTestResultSixthFrameTrap
	                 hwBTSSSeltTestResultSeventhFrameTrap
	                "	

            REVISION    "201001120000Z" 
            DESCRIPTION "V3.03, changes in this revision:
                         Add the definition of hwBTSSDeltResultDataTrap node.
                        "                               
            
            REVISION    "200906040900Z" 
            DESCRIPTION "V3.02, changes in this revision:
                         Add the definition of SYNTAX HWBTSSxDslLineOverLap, and change the SYNTAX from INTEGER to HWBTSSxDslLineOverLap
                         for hwBTSSxDslLineOverlapType of table hwBTSSxDslLineCfgTable
                         Add leaf hwBTSSCoTestBusyFlag into table hwBTSSCoTestTable OBJECT-TYPE
                         Add hwBTSSAuxPortCfgTable for describing aux port used for BTSS.
                         Add hwBTSSTestedPortOperTable for describing operation for tested port.
                         Add hwBTSSCqtTransTestTable for describeing CQT test by transparent command.
                         Add hwBTSSMultiFrameMiscOperTable for describing test relatived operation for multi-frame.
                         Add hwBTSSAdslSeltTestTable for describing selt test for adsl2+.
                         Add hwBTSSAdslDeltTestTable for describing Delt test for adsl2+.
                         Add hwBTSSLoopLineToneOprTable for Loop Line Tone.
                         Add leaf node hwBTSSTestedPortOperTrap for sending trap when tested port operation. 
                         Add leaf node hwBTSSCqtTransTestOperResultTrap for sending trap when starting or stoping Cqt transparent test.
                         Add leaf node hwBTSSCqtTransTestResultTrap for sending trap when reporting the result after Cqt transparent test. 
                         Add leaf node hwBTSSLoopLineToneOperTrap for sending trap when reporting the test result of Loop Line Tone.
                                                  
                         Delete leafs hwBTSSxDslLineExtCrossMatrixRauModuleNo and wBTSSxDslLineExtCrossMatrixRauPortNo from table
                         Delete tables, include:
                         hwBTSSxDslLineCfgTable
                         hwBTSSCqtTemplateTable
                         hwBTSSCqtMaintainTable
                         hwBTSSCqtFrTestTable
                         hwBTSSCqtTdrTestTable
                         hwBTSSCqtDmtTestTable
                         hwBTSSCqtNseTestTable
                         hwBTSSCqtLbTestTable
                         hwBTSSCqtLcTestTable 
                         hwBTSSCqtFrTestResultTable
                         hwBTSSCqtTdrTestResultTable
                         hwBTSSCqtDmtTestResultTable
                         hwBTSSCqtNseTestResultTable
                         hwBTSSCqtLbTestResultTable
                         hwBTSSCqtLcTestResultTable
                         Delete traps, include:
                         hwBTSSCqtFrTestTrap 
                         hwBTSSCqtTdrTestTrap
                         hwBTSSCqtDmtTestTrap
                         hwBTSSCqtNseTestTrap
                         hwBTSSCqtLbTestTrap
                         hwBTSSCqtLcTestTrap
                         hwBTSSCqtStopFrTestTrap
                         hwBTSSCqtStopTdrTestTrap
                         hwBTSSCqtStopDmtTestTrap
                         hwBTSSCqtStopNseTestTrap
                         hwBTSSCqtStopLbTestTrap
                         hwBTSSCqtStopLcTestTrap
                        "
            
            REVISION    "200308280900Z" 
            DESCRIPTION "V3.00, change in this revision: 
                         Change the style of description.
                        "   
            
            REVISION    "200306280900Z" 
            DESCRIPTION "V2.00, change in this revision:
                         Correct the SYNTAX.
                        "
            
            REVISION    "200304280900Z" 
            DESCRIPTION "V1.00, initial version, by FixNet Mib Group."                              
            ::= { hwTest 3 }
            
        HWBTSSxDslLineOverLap ::= TEXTUAL-CONVENTION
            STATUS  current
            DESCRIPTION
                "Set overlap mode of xDSL with PSTN line.
                 Options:
                 1. overLap(1) - xDSL overlap with POTS line
                 2. direct(2)  - There is no pots line, no splitter, no phone
                 3. unknown(3) - The mode is unknown
                "
            SYNTAX   INTEGER 
                {
                 overLap(1),
                 direct(2),
                 unknown(3)
                }
                
        CqtQualitativeResultString ::= TEXTUAL-CONVENTION
            STATUS current
            DESCRIPTION    
                "This string to contain qualitative result."
            SYNTAX OCTET STRING (SIZE (0..255))
                        
        
        hwTest OBJECT IDENTIFIER ::= { huaweiUtility 21 }
                
        hwBTestMib OBJECT IDENTIFIER ::= { hwBtest 1 }
                
        hwBTestMIBObjects OBJECT IDENTIFIER ::= { hwBTestMib 1 }
                
        hwBTSSxDslLineCfgTable OBJECT-TYPE
            SYNTAX SEQUENCE OF HwBTSSxDslLineCfgEntry
            MAX-ACCESS not-accessible
            STATUS current
            DESCRIPTION
                "The hwBTSSxDslLineCfgTable table describes xDSL line configuration.
                 This table is used for bandwidth test.
                 The index of this table is ifIndex.
                "
            ::= { hwBTestMIBObjects 1 }
                
        hwBTSSxDslLineCfgEntry OBJECT-TYPE
            SYNTAX HwBTSSxDslLineCfgEntry
            MAX-ACCESS not-accessible
            STATUS current
            DESCRIPTION
                "The hwBTSSxDslLineCfgTable table describes xDSL line configuration.
                 This table is used for bandwidth test.
                 The index of this entry is ifIndex.
                "
            INDEX { ifIndex }
            ::= { hwBTSSxDslLineCfgTable 1 }
                
        HwBTSSxDslLineCfgEntry ::=
            SEQUENCE 
                { 
                hwBTSSxDslLineOverlapType   HWBTSSxDslLineOverLap
                }
        
        hwBTSSxDslLineOverlapType OBJECT-TYPE
            SYNTAX HWBTSSxDslLineOverLap
            MAX-ACCESS read-write
            STATUS current
            DESCRIPTION
                "Overlap mode of xDSL with PSTN line.
                 Options:
                 1. overLap(1) - xDSL overlap with POTS line
                 2. direct(2)  - There is no pots line, no splitter, no phone
                 3. unknown(3) - The mode is unknown 
                 Default: unknown(3)
                "
            DEFVAL { 3 }
            ::= { hwBTSSxDslLineCfgEntry 1 }
                
        hwBTSSCoTestTable OBJECT-TYPE
            SYNTAX SEQUENCE OF HwBTSSCoTestEntry
            MAX-ACCESS not-accessible
            STATUS current
            DESCRIPTION
                "xDSL central office emulational measurement table.The table is used for xDSL central emulational measurement.
                 The index of this table is ifIndex.
                "
            ::= { hwBTestMIBObjects 2 }
                
        hwBTSSCoTestEntry OBJECT-TYPE
            SYNTAX HwBTSSCoTestEntry
            MAX-ACCESS not-accessible
            STATUS current
            DESCRIPTION                      
                "xDSL central office emulational measurement table.The table is used for xDSL central emulational measurement.
                 The index of this entry is ifIndex.
                "
            INDEX { ifIndex }
            ::= { hwBTSSCoTestTable 1 }
                
        HwBTSSCoTestEntry ::=
            SEQUENCE 
                { 
                hwBTSSCoOperType
                    INTEGER,
                hwBTSSCoTestResult
                    INTEGER,
                hwBTSSCoTestBusyFlag
                    INTEGER
                }
        
        hwBTSSCoOperType OBJECT-TYPE
            SYNTAX INTEGER
                {
                stop(1),
                start(2)
                }
            MAX-ACCESS read-write
            STATUS current
            DESCRIPTION
                "CO emulational operation type.
                 Options:
                 1. stop(1)  - Stop CO emulational 
                 2. start(2) - Start CO emulational
                "
            ::= { hwBTSSCoTestEntry 1 }
                
        hwBTSSCoTestResult OBJECT-TYPE
            SYNTAX INTEGER
                {
                normal(1),
                testfail(2)
                }
            MAX-ACCESS accessible-for-notify
            STATUS current
            DESCRIPTION
                "CO emulational test result.
                 Options:
                 1. normal(1)   - The test of CO emulational is successful
                 2. testfail(2) - Fail in test of CO emulational
                "
            ::= { hwBTSSCoTestEntry 2 }
        
        hwBTSSCoTestBusyFlag OBJECT-TYPE
            SYNTAX INTEGER  
                { 
                busyNoTest(1),  
                busyTest(2),
                busystrenTest(3) 
                }
            MAX-ACCESS  read-write
            STATUS current
            DESCRIPTION
                "CO force test flag
                 Options:
                 1. busyNoTest(1)    - No test on busy
                 2. busyTest(2)      - Test on busy
                 3. busystrenTest(3) - Forced test on busy
                "
            ::= { hwBTSSCoTestEntry 3 }
        
                
        hwBTSSAuxPortCfgTable   OBJECT-TYPE
            SYNTAX          SEQUENCE OF HwBTSSAuxPortCfgEntry
            MAX-ACCESS      not-accessible
            STATUS          current
            DESCRIPTION
                "Configuration table of the broadband test auxiliary port
                 This table is used to configure a certain type of emulation port required in the CO emulation test.       
                 The indexes of this table are hwTestGroupNo and hwBTSSAuxPortType.
                "
            ::= { hwBTestMIBObjects 17 }
        
        hwBTSSAuxPortCfgEntry   OBJECT-TYPE
            SYNTAX          HwBTSSAuxPortCfgEntry
            MAX-ACCESS      not-accessible
            STATUS          current
            DESCRIPTION     
                "Configuration table of the broadband test auxiliary port
                 This table is used to configure a certain type of emulation port required in the CO emulation test.       
                 The indexes of this entry are hwTestGroupNo and hwBTSSAuxPortType.
                "
            INDEX           { hwTestGroupNo, hwBTSSAuxPortType }
            ::= { hwBTSSAuxPortCfgTable 1 }
        
        HwBTSSAuxPortCfgEntry ::=
            SEQUENCE 
                {
                hwBTSSAuxPortType       INTEGER,
                hwBTSSAuxPortIfIndex    Integer32,
                hwBTSSAuxPortRowStatus  RowStatus
                }
        
        hwBTSSAuxPortType OBJECT-TYPE
            SYNTAX      INTEGER
                {
                adsl(1),
                vdsl(2),
                gshdsl(3)
                }
            MAX-ACCESS  not-accessible
            STATUS      current
            DESCRIPTION
                "Assistance port type of BTSS.
                 Options:
                 1. adsl(1)   - Assistance port type of BTSS is adsl
                 2. vdsl(2)   - Assistance port type of BTSS is vdsl
                 3. gshdsl(3) - Assistance port type of BTSS is gshdsl
                "
            ::= { hwBTSSAuxPortCfgEntry 1 }
        
        hwBTSSAuxPortIfIndex OBJECT-TYPE
            SYNTAX      Integer32
            MAX-ACCESS  read-create
            STATUS      current
            DESCRIPTION
                "Assistance port ifIndex of BTSS."
            ::= { hwBTSSAuxPortCfgEntry 2 }
             
        hwBTSSAuxPortRowStatus OBJECT-TYPE
            SYNTAX      RowStatus
            MAX-ACCESS  read-create
            STATUS      current
            DESCRIPTION
                "Row status(add(4),delete(6))."
            ::= { hwBTSSAuxPortCfgEntry 3 }
            
        hwBTSSTestedPortOperTable   OBJECT-TYPE
            SYNTAX          SEQUENCE OF HwBTSSTestedPortOperEntry
            MAX-ACCESS      not-accessible
            STATUS          current
            DESCRIPTION
                "This table describes operation for tested port.
                 The index of this table is ifIndex.
                "
            ::= { hwBTestMIBObjects 18 }
        
        hwBTSSTestedPortOperEntry   OBJECT-TYPE
            SYNTAX          HwBTSSTestedPortOperEntry
            MAX-ACCESS      not-accessible
            STATUS          current
            DESCRIPTION     
                "This table describes operation for tested port.
                 The index of this entry is ifIndex.
                "
            INDEX           
                { 
                ifIndex
                }
            ::= { hwBTSSTestedPortOperTable 1 }
  
        HwBTSSTestedPortOperEntry ::=
            SEQUENCE 
                {
                hwBTSSTestedPortOperType       INTEGER,
                hwBTSSTestedPortOperMode       INTEGER,
                hwBTSSTestedPortOperResult     INTEGER,
                hwBTSSTestedPortTestBusyFlag   INTEGER,
                hwBTSSTestedPortTestPOTSFlag   INTEGER
                }
        
        hwBTSSTestedPortOperType OBJECT-TYPE
            SYNTAX      INTEGER
                {
                capture(1),
                release(2),
                startmonitor(3),
                stopmonitor(4),
                resumeport(5),
		invalid(-1)
                }
            MAX-ACCESS  read-write
            STATUS      current
            DESCRIPTION
                "Operation type of BTSS tested port.
                 Options:
                 1. capture(1)      - Capture
                 2. release(2)      - Release
                 3. startmonitor(3) - Start monitor
                 4. stopmonitor(4)  - Stop monitor
                 5. resumeport(5)   - Resume port
		 6. invalid(-1)     - Invalid value
                "
            ::= { hwBTSSTestedPortOperEntry 1 }
            
        hwBTSSTestedPortOperMode OBJECT-TYPE
            SYNTAX      INTEGER
            {
            inline(1),
            outline(2),
            monitor(3),
            both(4),
            meltNoCutxDSL(5),
            meltForceCutxDSL(6),
            testLineLoopback(7),
            internalResistorLoopback(8),
            passthroughmode(9)
            }
            MAX-ACCESS  read-write
            STATUS      current
            DESCRIPTION
                "Operation mode of BTSS tested port.
                 Options:
                 1. inline(1)                   - BTSS tested port in test
                 2. outline(2)                  - BTSS tested port out test
                 3. monitor(3)                  - Monitoring BTSS tested port
                 4. both(4)                     - Capture for circuit and loop-line test 
                 5. meltNoCutxDSL(5)            - Capture for melt chip test with co and cpe connecting
                 6. meltForceCutxDSL(6)         - Capture for melt chip test with co and cpe disconnecting 
                 7. testLineLoopback(7)         - Capture for test line loopback
                 8. internalResistorLoopback(8) - Capture for internal resistor loopback
                 9. passthroughmode(9)          - No capture
                 Default: passthroughmode(9)
                "
            ::= { hwBTSSTestedPortOperEntry 2 }
            
        hwBTSSTestedPortOperResult OBJECT-TYPE
            SYNTAX      INTEGER
                {
                normal(1),
                fail(2),
                timeout(4)
                }
            MAX-ACCESS  accessible-for-notify
            STATUS      current
            DESCRIPTION
                "Test result of BTSS tested port.
                 Options:
                 1. normal(1)   - The test of BTSS tested port is successful
                 2. fail(2)     - Fail in test of BTSS tested port
                 3. timeout(4) - The test of BTSS tested port is timeout
                "
            ::= { hwBTSSTestedPortOperEntry 3 }

        hwBTSSTestedPortTestBusyFlag OBJECT-TYPE
            SYNTAX INTEGER
                {
                busyNoTest(1),
                busyTest(2),
                busystrenTest(3)
                }
            MAX-ACCESS  read-write
            STATUS current
            DESCRIPTION
                "Tested port force test.
                 Options:
                 1. busyNoTest(1)    - No test on busy
                 2. busyTest(2)      - Test on busy
                 3. busystrenTest(3) - Forced test on busy
                "
            ::= { hwBTSSTestedPortOperEntry 4 }

        hwBTSSTestedPortTestPOTSFlag OBJECT-TYPE
            SYNTAX INTEGER
                {
                noCutPOTS(1),
                busyNoTest(2),
                busyTest(3),
                busystrenTest(4)
                }
            MAX-ACCESS  read-write
            STATUS current
            DESCRIPTION
                "Tested port POTS service flag
                 Options:
                 1. noCutPOTS(1)     - No cut off POTS
                 2. busyNoTest(2)    - No test on POTS busy (Cut off POTS)
                 3. busyTest(3)      - Test on POTS busy (Cut off POTS)
                 4. busystrenTest(4) - Forced test on POTS busy (Cut off POTS)
                "
            ::= { hwBTSSTestedPortOperEntry 5 }

        hwBTSSCqtTransTestTable   OBJECT-TYPE
            SYNTAX          SEQUENCE OF HwBTSSCqtTransTestEntry
            MAX-ACCESS      not-accessible
            STATUS          current
            DESCRIPTION
                "This table describes CQT test by transparent command.
                 The index of this table is ifIndex.
                "
            ::= { hwBTestMIBObjects 19 }
        
        hwBTSSCqtTransTestEntry   OBJECT-TYPE
            SYNTAX          HwBTSSCqtTransTestEntry
            MAX-ACCESS      not-accessible
            STATUS          current
            DESCRIPTION     
                "This table describes CQT test by transparent command.
                 The index of this entry is ifIndex.
                "
            INDEX           { ifIndex }
            ::= { hwBTSSCqtTransTestTable 1 }
        
        HwBTSSCqtTransTestEntry ::=
            SEQUENCE 
                {      
                hwBTSSCqtTransTestOperType       INTEGER,
                hwBTSSCqtTransTestCRCMode        INTEGER,
                hwBTSSCqtTransTestOperResult     INTEGER,
                hwBTSSCqtTransTestTxCmd          OCTET STRING,       
                hwBTSSCqtTransTestResultNo       Integer32,
                hwBTSSCqtTransTestResultLastFlag INTEGER,
                hwBTSSCqtTransTestResult         OCTET STRING     
                }
        
        hwBTSSCqtTransTestOperType OBJECT-TYPE
            SYNTAX      INTEGER
                {
                stop(1),
                start(2)
                }
            MAX-ACCESS  read-write
            STATUS      current
            DESCRIPTION
                "CQT transparent Operation type
                 Options:
                 1. stop(1)  - Stop CQT transparent test
                 2. start(2) - Start CQT transparent test
                "
            ::= { hwBTSSCqtTransTestEntry 1 }
  
        hwBTSSCqtTransTestCRCMode OBJECT-TYPE
            SYNTAX      INTEGER
                {
                disable(1),
                enable(2)
                }
            MAX-ACCESS  read-write
            STATUS      current
            DESCRIPTION
                "CRC Operation type of CQT transparent.
                 Options:
                 1. disable(1) - Disable CQT transparent 
                 2. enable(2)  - Enable CQT transparent 
                 Default: disable(1)
                "
            DEFVAL      { 1 }
            ::= { hwBTSSCqtTransTestEntry 2 }
            
        hwBTSSCqtTransTestOperResult OBJECT-TYPE
            SYNTAX      INTEGER
                {
                normal(1),
                fail(2),
                abort(3),
                powerfeed(4)
                }
            MAX-ACCESS  accessible-for-notify
            STATUS      current
            DESCRIPTION
                "CQT transparent Operation result.
                 Options:
                 1. normal(1)    - The CQT transparent test is successful
                 2. fail(2)      - The CQT transparent test fails
                 3. abort(3)     - The CQT transparent test aborts
                 4. powerfeed(4) - The CQT transparent test power feeds                
                "
            ::= { hwBTSSCqtTransTestEntry 3 }
            
        hwBTSSCqtTransTestTxCmd OBJECT-TYPE
            SYNTAX      OCTET STRING(SIZE(0..251))
            MAX-ACCESS  read-write
            STATUS      current
            DESCRIPTION
                "Sending command string in TL1 format."
            ::= { hwBTSSCqtTransTestEntry 4 }
            
        hwBTSSCqtTransTestResultNo OBJECT-TYPE
            SYNTAX      Integer32(1..255)
            MAX-ACCESS  accessible-for-notify
            STATUS      current
            DESCRIPTION
                "Test result No.
                 Range: 1-255
                "
            ::= { hwBTSSCqtTransTestEntry 5 }
            
        hwBTSSCqtTransTestResultLastFlag OBJECT-TYPE
            SYNTAX      INTEGER{false(0), true(1)}
            MAX-ACCESS  accessible-for-notify
            STATUS      current
            DESCRIPTION
                "Last package flag for test result.
                 Options:
                 1. false(0) - This is not the last package
                 2. true(1)  - The last package
                "
            ::= { hwBTSSCqtTransTestEntry 6 }
            
        hwBTSSCqtTransTestResult OBJECT-TYPE
            SYNTAX      OCTET STRING(SIZE(0..231))
            MAX-ACCESS  accessible-for-notify
            STATUS      current
            DESCRIPTION
                "CQT transparent Test result."
            ::= { hwBTSSCqtTransTestEntry 7 }
            
        
        hwBTSSMultiFrameMiscOperTable   OBJECT-TYPE
            SYNTAX          SEQUENCE OF HwBTSSMultiFrameMiscOperEntry
            MAX-ACCESS      not-accessible
            STATUS          current
            DESCRIPTION
                "This table describes test relatived operation for multi-frame.
                 The index of this table is ifIndex.
                "
            ::= { hwBTestMIBObjects 20 }
        
        hwBTSSMultiFrameMiscOperEntry   OBJECT-TYPE
            SYNTAX          HwBTSSMultiFrameMiscOperEntry
            MAX-ACCESS      not-accessible
            STATUS          current
            DESCRIPTION     
                "This table describes test relatived operation for multi-frame.
                 The index of this entry is ifIndex.
                "
            INDEX           
                { 
                ifIndex
                }
            ::= { hwBTSSMultiFrameMiscOperTable 1 }
  
        HwBTSSMultiFrameMiscOperEntry ::=
            SEQUENCE 
                {
                hwBTSSMultiFrameMiscCleanTest            INTEGER,
                hwBTSSMultiFrameMiscTestedFrame          Integer32,
                hwBTSSMultiFrameMiscTestedPortType       HWPortType,
                hwBTSSMultiFrameMiscTestedLineType       HWBTSSxDslLineOverLap             
                }
        
        hwBTSSMultiFrameMiscCleanTest OBJECT-TYPE
            SYNTAX      INTEGER{start(1)}
            MAX-ACCESS  read-write
            STATUS      current
            DESCRIPTION
                "Clean current test on specified frame.
                 Options:
                 1. start(1)  - Start clean current test
                "
            ::= { hwBTSSMultiFrameMiscOperEntry 1 }
        
        hwBTSSMultiFrameMiscTestedFrame OBJECT-TYPE
            SYNTAX      Integer32
            MAX-ACCESS  read-write
            STATUS      current
            DESCRIPTION
                "Tested frame of BTSS multi-frame.
                 Default:  0
                "
            DEFVAL      { 0 }
            ::= { hwBTSSMultiFrameMiscOperEntry 2 }
                
        hwBTSSMultiFrameMiscTestedPortType OBJECT-TYPE
            SYNTAX      HWPortType
            MAX-ACCESS  read-write
            STATUS      current
            DESCRIPTION
                "Tested port type of BTSS multi-frame."            
            ::= { hwBTSSMultiFrameMiscOperEntry 3 }
            
        hwBTSSMultiFrameMiscTestedLineType OBJECT-TYPE
            SYNTAX      HWBTSSxDslLineOverLap
            MAX-ACCESS  read-write
            STATUS      current
            DESCRIPTION
                "Tested line type of BTSS multi-frame."
            ::= { hwBTSSMultiFrameMiscOperEntry 4 }
                    
        hwBTSSAdslSeltTestTable   OBJECT-TYPE
            SYNTAX          SEQUENCE OF HWBTSSAdslSeltTestEntry
            MAX-ACCESS      not-accessible
            STATUS          current
            DESCRIPTION
                "This table describes selt test for adsl2+.
                 The index of this table is ifIndex.
                "
            ::= { hwBTestMIBObjects 21 }       
        hwBTSSAdslSeltTestEntry   OBJECT-TYPE
            SYNTAX          HWBTSSAdslSeltTestEntry
            MAX-ACCESS      not-accessible
            STATUS          current
            DESCRIPTION     
                "This table describes selt test for adsl2+.
                 The index of this entry is ifIndex.
                "
            INDEX           
                { 
                ifIndex
                }
            ::= { hwBTSSAdslSeltTestTable 1 }
  
        HWBTSSAdslSeltTestEntry ::=
            SEQUENCE 
                {
                hwBTSSAdslSeltTestOperType       INTEGER  ,
                hwBTSSAdslSeltTestOperResult     INTEGER ,
                hwBTSSAdslSeltTestResultNo       Integer32  ,
                hwBTSSAdslSeltTestResultLastFlag INTEGER ,
                hwBTSSAdslSeltTestResult         OCTET STRING ,
                hwBTSSAdslSeltTestParamLoopLength Integer32 ,
                hwBTSSAdslSeltTestParamLoopTermin INTEGER ,
                hwBTSSAdslSeltTestParamLoopGauge  INTEGER ,
                hwBTSSAdslSeltTestParamUpShnCap   Integer32 ,
                hwBTSSAdslSeltTestParamDwnShnCap  Integer32 ,
                hwBTSSAdslSeltTestParamInbandNoise OCTET STRING ,
                hwBTSSAdslSeltTestParamTerminResp OCTET STRING ,
                hwBTSSAdslSeltTestParamUpMgnAtRate   OCTET STRING ,
                hwBTSSAdslSeltTestParamDwnMgnAtRate  OCTET STRING ,
                hwBTSSAdslSeltTestParamUpRateAtMgn   OCTET STRING ,  
                hwBTSSAdslSeltTestParamDwnRateAtMgn  OCTET STRING ,
                hwBTSSAdslSeltTestParamLoopAttenAtFreq  OCTET STRING,
                hwBTSSAdslSeltTestParamUnCalibLineScale Unsigned32,
                hwBTSSAdslSeltTestParamUnCalibEchoRespReal OCTET STRING,
                hwBTSSAdslSeltTestParamUnCalibEchoRespImg OCTET STRING,
                hwBTSSAdslSeltTestParamCalibLineScale Unsigned32,
                hwBTSSAdslSeltTestParamCalibEchoRespReal OCTET STRING,
                hwBTSSAdslSeltTestParamCalibEchoRespImg OCTET STRING,
                hwBTSSAdslSeltTestParamVarUerC OCTET STRING,
                hwBTSSAdslSeltTestParamUerMmdC Unsigned32,
                hwBTSSAdslSeltTestParamQlnMmdC Unsigned32,
                hwBTSSAdslSeltTestParamUmeC INTEGER,
                hwBTSSAdslSeltTestParamQmeC INTEGER,
                hwBTSSAdslSeltTestParamUerStatus  INTEGER,
                hwBTSSAdslSeltTestParamQlnStatus  INTEGER, 
                hwBTSSAdslSeltTestParamCalcEnable    INTEGER,
                hwBTSSAdslSeltTestParamAttnAt180KHZ  Integer32,
                hwBTSSAdslSeltTestParamAttnAt300KHZ  Integer32,
                hwBTSSAdslSeltTestParamQSPsdValue    OCTET STRING 
                }
                
        hwBTSSAdslSeltTestOperType OBJECT-TYPE
            SYNTAX      INTEGER
                {
                stop(1),
                start(2),
                invalid(-1)
                }
            MAX-ACCESS  read-write
            STATUS      current
            DESCRIPTION
                "Selt test operation type.
                 Options:
                 1. stop(1)     - Stop selt test of BTSS
                 2. start(2)    - Start selt test of BTSS
                 3. invalid(-1) - No operation
                "         
            ::= { hwBTSSAdslSeltTestEntry 1 }    
        hwBTSSAdslSeltTestOperResult OBJECT-TYPE
            SYNTAX      INTEGER
                {
                normal(1),
                fail(2),
                abort(3)
                }
            MAX-ACCESS  accessible-for-notify
            STATUS      current
            DESCRIPTION
                "Selt test operation result.
                 Options:
                 1. normal(1) - Selt test of BTSS is successful
                 2. fail(2)   - Fail in selt test of BTSS
                 3. abort(3)  - Selt test of BTSS aborts
                "
            ::= { hwBTSSAdslSeltTestEntry 2 }
        hwBTSSAdslSeltTestResultNo OBJECT-TYPE
            SYNTAX      Integer32(1..255)
            MAX-ACCESS  accessible-for-notify
            STATUS      current
            DESCRIPTION
                "Selt test result serial number.
                 Range: 1-255
                "
            ::= { hwBTSSAdslSeltTestEntry 3 }
        hwBTSSAdslSeltTestResultLastFlag OBJECT-TYPE
            SYNTAX      INTEGER{false(0), true(1)}
            MAX-ACCESS  accessible-for-notify
            STATUS      current
            DESCRIPTION
                "Last package flag of test.
                 Options:
                 1. false(0) - This is not the last package  
                 2. true(1)  - The last package
                "
            ::= { hwBTSSAdslSeltTestEntry 4 }
        hwBTSSAdslSeltTestResult OBJECT-TYPE
            SYNTAX      OCTET STRING(SIZE(0..1500))
            MAX-ACCESS  accessible-for-notify
            STATUS      current
            DESCRIPTION
                "Selt test result data."
            ::= { hwBTSSAdslSeltTestEntry 5 }  
        hwBTSSAdslSeltTestParamLoopLength OBJECT-TYPE
            SYNTAX      Integer32
            MAX-ACCESS  read-only
            STATUS      current
            DESCRIPTION
                "Selt test parameter Loop Length. 
                 The invalid value is -1. If no SELT is performed, no SELT data is 
                 generated because the SELT is incomplete, or no SELT data can be 
                 obtained from the port because the SELT data is aged and cleared, 
                 the invalid value will be returned."
            ::= { hwBTSSAdslSeltTestEntry 6 }
        hwBTSSAdslSeltTestParamLoopTermin OBJECT-TYPE
            SYNTAX      INTEGER
                 {
                 open(0),
                 short(1),
                 unknow(2),
                 terminated(3),
                 invalid(-1)
                 }
            MAX-ACCESS  read-only
            STATUS      current
            DESCRIPTION
                "Selt test parameter Loop Termination state.
                 Options:
                 1. open(0)       - Indicates that the line terminal is started
                 2. short(1)      - Indicates that the line terminal is short-circuited
                 3. unknow(2)     - Indicates the unknown state
                 4. terminated(3) - Indicates that the line terminal is stopped
                 5. invalid(-1)   - Indicates the invalid state
                "
            ::= { hwBTSSAdslSeltTestEntry 7 }
        hwBTSSAdslSeltTestParamLoopGauge OBJECT-TYPE
            SYNTAX      INTEGER
                {
                greater26awg(1),
                equal26awg(2),
                equal24awg(3),
                less24awg(4),
                unknowawg(5),
                invalid(-1)
                }
            MAX-ACCESS  read-write
            STATUS      current
            DESCRIPTION
                "Selt test parameter Loop Gauge.
                 Options:
                 1. greater26awg(1) - Indicates that the line gauge is greater than 26
                 2. equal26awg(2)   - Indicates that the line gauge is 26
                 3. equal24awg(3)   - Indicates that the line gauge is 24
                 4. less24awg(4)    - Indicates that the line gauge is smaller than 24
                 5. unknowawg(5)    - Indicates an unknown line gauge.    
                 6. invalid(-1)     - Indicates an invalid value. 
                "
            ::= { hwBTSSAdslSeltTestEntry 8 }
        hwBTSSAdslSeltTestParamUpShnCap OBJECT-TYPE
            SYNTAX      Integer32
            MAX-ACCESS  read-only
            STATUS      current
            DESCRIPTION
                "Selt test parameter Upstream Shannon Capacity. 
                 The invalid value is -1. If no SELT is performed, no SELT data is 
                 generated because the SELT is incomplete, or no SELT data can be 
                 obtained from the port because the SELT data is aged and cleared, 
                 the invalid value will be returned."
            ::= { hwBTSSAdslSeltTestEntry 9 }
        hwBTSSAdslSeltTestParamDwnShnCap OBJECT-TYPE
            SYNTAX      Integer32
            MAX-ACCESS  read-only
            STATUS      current
            DESCRIPTION
                "Selt test parameter Downstream Shannon Capacity."
            ::= { hwBTSSAdslSeltTestEntry 10 }
        hwBTSSAdslSeltTestParamInbandNoise OBJECT-TYPE
            SYNTAX      OCTET STRING(SIZE(0..1500))
            MAX-ACCESS  read-only
            STATUS      current
            DESCRIPTION
                "Selt test parameter Inband Noise
                 512 values that indicate inband noise in dBm/Hz, 
                 covering ADSL, ADSL2, and ADSL2+ bands, from 0 to 2.2 MHz.
                "
            ::= { hwBTSSAdslSeltTestEntry 11 }
        hwBTSSAdslSeltTestParamTerminResp OBJECT-TYPE
            SYNTAX      OCTET STRING(SIZE(0..1500))
            MAX-ACCESS  read-only
            STATUS      current
            DESCRIPTION
                "Selt test parameter Termination Response
                 180 values that indicate termination response magnitude from 0 to 18 kft.
                "
            ::= { hwBTSSAdslSeltTestEntry 12 }
        hwBTSSAdslSeltTestParamUpMgnAtRate OBJECT-TYPE
            SYNTAX      OCTET STRING(SIZE(0..1500))
            MAX-ACCESS  read-only
            STATUS      current
            DESCRIPTION
                "Selt test parameter Upstream Ratevs. Margin.
                 This value is a measure of the quality of your upstream data 
                 signal relative to the noise on the line. Hundreds of values that 
                 indicate SNR margin in DB/Hz at a particular bit rate are provided, 
                 at a certain increments, up to 30 Mbps. This information may be plotted 
                 with the bit rate on the X-axis and the SNR margin on the Y-axis.
                "
            ::= { hwBTSSAdslSeltTestEntry 13 }
            
        hwBTSSAdslSeltTestParamDwnMgnAtRate OBJECT-TYPE
            SYNTAX      OCTET STRING(SIZE(0..1500))
            MAX-ACCESS  read-only
            STATUS      current
            DESCRIPTION
                "Selt test parameter Downstream Rate vs. Margin.                 
                 This value is a measure of the quality of your downstream data 
                 signal relative to the noise on the line. Hundreds of values that 
                 indicate SNR margin in DB/Hz at a particular bit rate are provided, 
                 at a certain increments, up to 30 Mbps. This information may be plotted 
                 with the bit rate on the X-axis and the SNR margin on the Y-axis.
                "
            ::= { hwBTSSAdslSeltTestEntry 14 }
            
        hwBTSSAdslSeltTestParamUpRateAtMgn OBJECT-TYPE
            SYNTAX      OCTET STRING(SIZE(0..1500))
            MAX-ACCESS  read-only
            STATUS      current
            DESCRIPTION
                "Selt test parameter Upstream Margin vs. Rate."
            ::= { hwBTSSAdslSeltTestEntry 15 }
            
        hwBTSSAdslSeltTestParamDwnRateAtMgn OBJECT-TYPE
            SYNTAX      OCTET STRING(SIZE(0..1500))
            MAX-ACCESS  read-only
            STATUS      current
            DESCRIPTION
                "Selt test parameter Downstream Margin vs. Rate."
            ::= { hwBTSSAdslSeltTestEntry 16 }
           
        hwBTSSAdslSeltTestParamLoopAttenAtFreq OBJECT-TYPE
            SYNTAX      OCTET STRING(SIZE(0..2048))
            MAX-ACCESS  read-only
            STATUS      current
            DESCRIPTION
                "Selt test parameter loop attenuation versus frequency.
                 Every four bytes constitute the result of a tone.
                 This information may be plotted with the bit frequency
                 on the X-axis and the loop attenuation on the Y-axis.
                "
            ::= { hwBTSSAdslSeltTestEntry 17 }
            
        hwBTSSAdslSeltTestParamUnCalibLineScale OBJECT-TYPE
            SYNTAX      Unsigned32
            MAX-ACCESS  read-only
            STATUS      current
            DESCRIPTION
                "The uncalibrated echo response, UER(i* UER_G*Df), shall be represented in linear format by a
                 scale factor and a normalized complex number a(i)+j*b(i), where i is a frequency index i ranging
                 from 0 to NSC-1, the subcarrier spacing, Df = 4.3125 kHz, and (NSC-1) * UER_G * Df is the
                 highest frequency supported by the SELT-PMD functionality. The UER granularity parameter,
                 UER_G, has two valid values: 1 and 2, indicating whether the measurements were performed using
                 a tone spacing of 4.3125 kHz or of 8.625 kHz. If the uncalibrated echo response is being reported
                 over a frequency range of 17.664 MHz or lower, UER_G shall be set to 1. If the uncalibrated echo
                 response is being reported over a frequency range that is greater than 17.664 MHz, UER_G shall be
                 set to 2.
                 The scale factor shall be coded as a 32-bit unsigned integer. Both a(i) and b(i) shall be coded as
                 32-bit 2's complement signed integers. The value of UER(i* UER_G*Df) shall be defined as:
                 UER(i* UER_G*Df) = (scale/2^31)*(a(i)+j*b(i))/2^31. In order to maximize precision, the scale factor
                 shall be chosen such that max(|a(i)|, |b(i)|) over all i is equal to 2^31-1.
                 NOTE - This data format supports an UER(f) granularity of 2^-31 and an UER(f) dynamic range of
                 approximately +6 dB to -186 dB, however it does not imply any future accuracy requirements.
                 An UER(i*UER_G* Df) value indicated as a(i) = b(i) = -2^31 is a special value. It indicates that no
                 measurement could be done for this subcarrier either because it is not supported by the SELT-PMD
                 function, or that the value is out of range to be represented.
                "
            ::= { hwBTSSAdslSeltTestEntry 18 }     
                   
        hwBTSSAdslSeltTestParamUnCalibEchoRespReal OBJECT-TYPE
            SYNTAX      OCTET STRING(SIZE(0..2048))
            MAX-ACCESS  read-only
            STATUS      current
            DESCRIPTION
                "The uncalibrated echo response, UER(i* UER_G*Df), shall be represented in linear format by a
                 scale factor and a normalized complex number a(i)+j*b(i), where i is a frequency index i ranging
                 from 0 to NSC-1, the subcarrier spacing, Df = 4.3125 kHz, and (NSC-1) * UER_G * Df is the
                 highest frequency supported by the SELT-PMD functionality. The UER granularity parameter,
                 UER_G, has two valid values: 1 and 2, indicating whether the measurements were performed using
                 a tone spacing of 4.3125 kHz or of 8.625 kHz. If the uncalibrated echo response is being reported
                 over a frequency range of 17.664 MHz or lower, UER_G shall be set to 1. If the uncalibrated echo
                 response is being reported over a frequency range that is greater than 17.664 MHz, UER_G shall be
                 set to 2.
                 The scale factor shall be coded as a 32-bit unsigned integer. Both a(i) and b(i) shall be coded as
                 32-bit 2's complement signed integers. The value of UER(i* UER_G*Df) shall be defined as:
                 UER(i* UER_G*Df) = (scale/2^31)*(a(i)+j*b(i))/2^31. In order to maximize precision, the scale factor
                 shall be chosen such that max(|a(i)|, |b(i)|) over all i is equal to 2^31-1.
                 NOTE - This data format supports an UER(f) granularity of 2^-31 and an UER(f) dynamic range of
                 approximately +6 dB to -186 dB, however it does not imply any future accuracy requirements.
                 An UER(i*UER_G* Df) value indicated as a(i) = b(i) = -2^31 is a special value. It indicates that no
                 measurement could be done for this subcarrier either because it is not supported by the SELT-PMD
                 function, or that the value is out of range to be represented.
                "
            ::= { hwBTSSAdslSeltTestEntry 19 }   
             
        hwBTSSAdslSeltTestParamUnCalibEchoRespImg OBJECT-TYPE
            SYNTAX      OCTET STRING(SIZE(0..2048))
            MAX-ACCESS  read-only
            STATUS      current
            DESCRIPTION
                "The uncalibrated echo response, UER(i* UER_G*Df), shall be represented in linear format by a
                 scale factor and a normalized complex number a(i)+j*b(i), where i is a frequency index i ranging
                 from 0 to NSC-1, the subcarrier spacing, Df = 4.3125 kHz, and (NSC-1) * UER_G * Df is the
                 highest frequency supported by the SELT-PMD functionality. The UER granularity parameter,
                 UER_G, has two valid values: 1 and 2, indicating whether the measurements were performed using
                 a tone spacing of 4.3125 kHz or of 8.625 kHz. If the uncalibrated echo response is being reported
                 over a frequency range of 17.664 MHz or lower, UER_G shall be set to 1. If the uncalibrated echo
                 response is being reported over a frequency range that is greater than 17.664 MHz, UER_G shall be
                 set to 2.
                 The scale factor shall be coded as a 32-bit unsigned integer. Both a(i) and b(i) shall be coded as
                 32-bit 2's complement signed integers. The value of UER(i* UER_G*Df) shall be defined as:
                 UER(i* UER_G*Df) = (scale/2^31)*(a(i)+j*b(i))/2^31. In order to maximize precision, the scale factor
                 shall be chosen such that max(|a(i)|, |b(i)|) over all i is equal to 2^31-1.
                 NOTE - This data format supports an UER(f) granularity of 2^-31 and an UER(f) dynamic range of
                 approximately +6 dB to -186 dB, however it does not imply any future accuracy requirements.
                 An UER(i*UER_G* Df) value indicated as a(i) = b(i) = -2^31 is a special value. It indicates that no
                 measurement could be done for this subcarrier either because it is not supported by the SELT-PMD
                 function, or that the value is out of range to be represented.
                " 
            ::= { hwBTSSAdslSeltTestEntry 20 }  
            
        hwBTSSAdslSeltTestParamCalibLineScale OBJECT-TYPE
            SYNTAX      Unsigned32
            MAX-ACCESS  read-only
            STATUS      current
            DESCRIPTION
                "The scale factor of calibrated echo response shall be coded as a 16 bit 
                 unsigned integer.
                "
            ::= { hwBTSSAdslSeltTestEntry 21 }     
                   
        hwBTSSAdslSeltTestParamCalibEchoRespReal OBJECT-TYPE
            SYNTAX      OCTET STRING(SIZE(0..2048))
            MAX-ACCESS  read-only
            STATUS      current
            DESCRIPTION
                "The calibrated echo response UER(i* f), shall be represented 
                 in linear format by a scale factor and a normalized complex number a(i)+j*b(i),
                 where i is the subcarrier index i ranging from 0 to NSC-1 and Df = 4.3125kHz 
                 and (NSC-1) * Df is the highest frequency supported by the SELT-PMD functionality. 
                 The scale factor shall be coded as a 16 bit unsigned integer. 
                 Both a(i) and b(i) shall be coded as a 16 bit 2's complement signed integer.
                 The value of UER(i* f) shall be defined as UER(i* f) = (scale/215)*(a(i)+j*b(i))/215. 
                 In order to maximize precision, the scale factor shall be chosen such that max(|a(i)|, |b(i)|) 
                 over all i is equal to 215-1. This data format supports an UER(f) granularity of 2-15 
                 and an UER(f) dynamic range of approximately +6 dB to -90 dB. 
                 An UER(i*Df) value indicated as a(i) = b(i) =  -215 is a special value. 
                 It indicates that no measurement could be done for this subcarrier because 
                 it is out of the PSD mask passband or that the value is out of range to be represented.
                "
            ::= { hwBTSSAdslSeltTestEntry 22 }   
             
        hwBTSSAdslSeltTestParamCalibEchoRespImg OBJECT-TYPE
            SYNTAX      OCTET STRING(SIZE(0..2048))
            MAX-ACCESS  read-only
            STATUS      current
            DESCRIPTION
                "The calibrated echo response UER(i* f), shall be represented 
                 in linear format by a scale factor and a normalized complex number a(i)+j*b(i),
                 where i is the subcarrier index i ranging from 0 to NSC-1 and Df = 4.3125kHz 
                 and (NSC-1) * Df is the highest frequency supported by the SELT-PMD functionality. 
                 The scale factor shall be coded as a 16 bit unsigned integer. 
                 Both a(i) and b(i) shall be coded as a 16 bit 2's complement signed integer.
                 The value of UER(i* f) shall be defined as UER(i* f) = (scale/215)*(a(i)+j*b(i))/215. 
                 In order to maximize precision, the scale factor shall be chosen such that max(|a(i)|, |b(i)|) 
                 over all i is equal to 215-1. This data format supports an UER(f) granularity of 2-15 
                 and an UER(f) dynamic range of approximately +6 dB to -90 dB. 
                 An UER(i*Df) value indicated as a(i) = b(i) =  -215 is a special value. 
                 It indicates that no measurement could be done for this subcarrier because 
                 it is out of the PSD mask passband or that the value is out of range to be represented.
                " 
            ::= { hwBTSSAdslSeltTestEntry 23 }                                 
            
        hwBTSSAdslSeltTestParamVarUerC OBJECT-TYPE
            SYNTAX      OCTET STRING(SIZE(0..2048))
            MAX-ACCESS  read-only
            STATUS      current  
            DESCRIPTION
                "The relative variance of the uncalibrated echo response REL_VAR_UER(i* UER_G *Df) shall be
                 represented as an 8-bit unsigned integer v(i), where i is the subcarrier index i = 0 to NSC-1. The
                 value of REL_VAR_UER(i* UER_G *Df) shall be defined as REL_VAR_UER(i* UER_G *Df) = 3 - v(i)/2 dB. 
                 The number v(i) is an 8-bit unsigned integer in the range 0 to 254. 
                 This data format supports a REL_VAR_UER(i) over a range from -124 dB to +3 dB for each carrier with a granularity from 0.5 dB. 
                 Out of range values shall be clamped to the closest range bound. 
                 The special value v(i) = 255 indicates that no measurement is available for that carrier.
                 Unit: 0.5dB
                "
            ::= { hwBTSSAdslSeltTestEntry 24 }    
             
        hwBTSSAdslSeltTestParamUerMmdC OBJECT-TYPE
            SYNTAX      Unsigned32
            MAX-ACCESS  read-write
            STATUS      current 
            DESCRIPTION
            	"This parameter is the maximum allowed time for SELT uncalibrated echo response measurement,
                 between the time of the start command written by the SELT-PMD-ME, and the time the result is
                 available for read operation by SELT-PMD-ME.
                 It is configurable between 5 seconds and 240 seconds, in steps of 1 second. 
                 The invalid value is 255. If data on the port cannot be queried, the invalid value will be returned.
                 Unit: 1 second
            	"  
            ::= { hwBTSSAdslSeltTestEntry 25 }     
             
        hwBTSSAdslSeltTestParamQlnMmdC OBJECT-TYPE
            SYNTAX      Unsigned32
            MAX-ACCESS  read-write
            STATUS      current 
            DESCRIPTION
            	"This parameter is the maximum allowed time for SELT quiet line noise measurement, between the
                 time of the start command written by the SELT-PMD-ME, and the time the result is available for
                 read operation by SELT-PMD-ME.
                 It is configurable between 1 second and 240 seconds, in steps of 1 second. 
                 The invalid value is 255. If data on the port cannot be queried, the invalid value will be returned.
                 Unit: 1 second
            	"     
            ::= { hwBTSSAdslSeltTestEntry 26 } 
            
        hwBTSSAdslSeltTestParamUmeC OBJECT-TYPE  
            SYNTAX      INTEGER{enable(1),disable(2),invalid(-1)}
            MAX-ACCESS  read-write
            STATUS      current  
            DESCRIPTION
            	"This parameter is a binary variable.
		 Options:
		 1.enable(1)          - Enable UER capture switch
		 2.disable(2)         - Disable UER capture switch
		 3.invalid(-1)        - Invalid value
            	"  
            ::= { hwBTSSAdslSeltTestEntry 27 }     	 
             
        hwBTSSAdslSeltTestParamQmeC OBJECT-TYPE
            SYNTAX      INTEGER{enable(1),disable(2),invalid(-1)}
            MAX-ACCESS  read-write
            STATUS      current  
            DESCRIPTION
            	"This parameter is a binary variable.
		 Options:
		 1.enable(1)          - Enable QLN capture switch
		 2.disable(2)         - Disable QLN capture switch
		 3.invalid(-1)        - Invalid value
            	"  
            ::= { hwBTSSAdslSeltTestEntry 28 }  
             
        hwBTSSAdslSeltTestParamUerStatus OBJECT-TYPE
            SYNTAX      INTEGER{off(1), running(2),completed(3),failed(4)}
            MAX-ACCESS  read-only
            STATUS      current  
            DESCRIPTION
            	"UerStatus.
		 Options:
		 1.off(1)             - The status is off.
		 2.running(2)         - The status is running.
		 3.completed(3)       - The status is completed.
		 4.failed(4)          - The status is failed.
            	"  
            ::= { hwBTSSAdslSeltTestEntry 29 }	
            
        hwBTSSAdslSeltTestParamQlnStatus OBJECT-TYPE
            SYNTAX      INTEGER{off(1), running(2),completed(3),failed(4)}
            MAX-ACCESS  read-only
            STATUS      current
            DESCRIPTION
            	"QlnStatus.
		 Options:
		 1.off(1)             - The status is off.
		 2.running(2)         - The status is running.
		 3.completed(3)       - The status is completed.
		 4.failed(4)          - The status is failed.
            	"  
            ::= { hwBTSSAdslSeltTestEntry 30 }
            			     		      	                     
        hwBTSSAdslSeltTestParamCalcEnable OBJECT-TYPE
            SYNTAX      INTEGER
            {
            enable(1),
            disable(2),
            invalid(-1)
            }
            MAX-ACCESS  read-write
            STATUS      current
            DESCRIPTION 
               "The status of calculation switch.
                Options:
                1. enable(1)       - Enable calculation switch
    	        2. disable(2)      - Disable calculation switch
    	        3. invalid(-1)     - Invalid value
    	        Default: enable(1)               
               "
            DEFVAL { enable }
            ::= { hwBTSSAdslSeltTestEntry 31 }    
            
        hwBTSSAdslSeltTestParamAttnAt180KHZ OBJECT-TYPE
            SYNTAX      Integer32 
            UNITS       "0.1dB"
            MAX-ACCESS  read-only
            STATUS      current
            DESCRIPTION
                "Selt test parameter attenuation at 180KHZ.
                 It ranges from -1100 to 0 units of 0.1dB(physical values
                 are -110 to 0 dB). 
                 The invalid value is -1. If no SELT is performed, no SELT data is 
                 generated because the SELT is incomplete, or no SELT data can be 
                 obtained from the port because the SELT data is aged and cleared, 
                 the invalid value will be returned.
                 Unit: 0.1dB
                " 
            ::= { hwBTSSAdslSeltTestEntry 65535 }
            
        hwBTSSAdslSeltTestParamAttnAt300KHZ OBJECT-TYPE
            SYNTAX      Integer32 
            UNITS       "0.1dB"
            MAX-ACCESS  read-only
            STATUS      current
            DESCRIPTION
                "Selt test parameter attenuation at 300KHZ.
                 It ranges from -1100 to 0 units of 0.1dB(physical values
                 are -110 to 0 dB). 
                 The invalid value is -1. If no SELT is performed, no SELT data is 
                 generated because the SELT is incomplete, or no SELT data can be 
                 obtained from the port because the SELT data is aged and cleared, 
                 the invalid value will be returned.
                 Unit: 0.1dB
                " 
            ::= { hwBTSSAdslSeltTestEntry 65536 }
            
        hwBTSSAdslSeltTestParamQSPsdValue OBJECT-TYPE
            SYNTAX      OCTET STRING(SIZE(0..1024)) 
            UNITS       "0.5dBm/Hz"
            MAX-ACCESS  read-only
            STATUS      current
            DESCRIPTION
                "The SELT quiet line noise provides the quiet line noise PSD as measured by the SELT-PMD
                 function (see clause A.1.1.2) for each sub-carrier frequency i * SELTQLN_G * Df where i ranges
                 from 0 to NSC-1, Df = 4.3125 kHz, and (NSC-1) * SELTQLN_G * Df is the highest frequency
                 supported by the SELT-PMD functionality. SELTQLN_G has two valid values: 1 and 2, indicating
                 whether the measurements were performed using a tone spacing of 4.3125 kHz or of 8.625 kHz. If
                 the SELT quiet line noise is being reported over a frequency range of 17.664 MHz or lower,
                 SELTQLN_G shall be set to 1. If the SELT quiet line noise is being reported over a frequency
                 range that is greater than 17.664 MHz, SELTQLN_G shall be set to 2.
                 SELT quiet line noise SELTQLN(i * SELTQLN_G * Df) shall be represented as an 8-bit unsigned
                 integer n(i), where i is the subcarrier index i = 0 to NSC-1. The value of
                 SELTQLN(i * SELTQLN_G * Df) shall be defined as SELTQLN(i * SELTQLN_G * Df ) =
                 -23 - (n(i)/2) dBm/Hz. This data format supports a SELTQLN(f) granularity of 0.5 dB and an
                 SELTQLN(f) dynamic range of -150 to -23 dBm/Hz.
                 Unit: 0.5dBm/Hz
                " 
            ::= { hwBTSSAdslSeltTestEntry 65537 }
                                
        hwBTSSAdslDeltTestTable   OBJECT-TYPE
            SYNTAX          SEQUENCE OF HWBTSSAdslDeltTestEntry
            MAX-ACCESS      not-accessible
            STATUS          current
            DESCRIPTION
                "This table describes Delt test for adsl2+.
                 The index of this table is ifIndex.
                "
            ::= { hwBTestMIBObjects 22 }       
        hwBTSSAdslDeltTestEntry   OBJECT-TYPE
            SYNTAX          HWBTSSAdslDeltTestEntry
            MAX-ACCESS      not-accessible
            STATUS          current
            DESCRIPTION     
                "This table describes Delt test for adsl2+.
                 The index of this entry is ifIndex.
                "
            INDEX           
                { 
                ifIndex
                }
            ::= { hwBTSSAdslDeltTestTable 1 }
        
        HWBTSSAdslDeltTestEntry ::=
            SEQUENCE 
                {
                hwBTSSAdslDeltTestOperType       INTEGER  ,
                hwBTSSAdslDeltTestOperResult     INTEGER ,
                hwBTSSAdslDeltTestResultNo       Integer32  ,
                hwBTSSAdslDeltTestResultLastFlag INTEGER ,
                hwBTSSAdslDeltTestResult         OCTET STRING 
                }
        
        hwBTSSAdslDeltTestOperType OBJECT-TYPE
            SYNTAX      INTEGER
                {
                stop(1),
                start(2),
                invalid(-1)
                }
            MAX-ACCESS  read-write
            STATUS      current
            DESCRIPTION
                "Delt test operation type.
                 Options:
                 1. stop(1)     - Delt test stop
                 2. start(2)    - Start delt test
                 3. invalid(-1) - No operation
                "         
            ::= { hwBTSSAdslDeltTestEntry 1 }    
        hwBTSSAdslDeltTestOperResult OBJECT-TYPE
            SYNTAX      INTEGER
                {
                normal(1),
                fail(2),
                abort(3)
                }
            MAX-ACCESS  accessible-for-notify
            STATUS      current
            DESCRIPTION
                "Delt test operation result.
                 Options:
                 1. normal(1) - Delt test is normal
                 2. fail(2)   - Fail in delt test
                 3. abort(3)  - Delt test aborts
                "
            ::= { hwBTSSAdslDeltTestEntry 2 }
        hwBTSSAdslDeltTestResultNo OBJECT-TYPE
            SYNTAX      Integer32(1..255)
            MAX-ACCESS  accessible-for-notify
            STATUS      current
            DESCRIPTION
                "Delt test result serial number.
                 Range: 1-255
                "
            ::= { hwBTSSAdslDeltTestEntry 3 }
        hwBTSSAdslDeltTestResultLastFlag OBJECT-TYPE
            SYNTAX      INTEGER{false(0), true(1)}
            MAX-ACCESS  accessible-for-notify
            STATUS      current
            DESCRIPTION
                "Last package flag for test result.
                 Options:
                 1. false(0)  - This is not the last package
                 2. true(1)   - The last package
                "
            ::= { hwBTSSAdslDeltTestEntry 4 }
        hwBTSSAdslDeltTestResult OBJECT-TYPE
            SYNTAX      OCTET STRING(SIZE(0..1500))
            MAX-ACCESS  accessible-for-notify
            STATUS      current
            DESCRIPTION
                "Delt test result data."
            ::= { hwBTSSAdslDeltTestEntry 5 }
             
        -- Loop line tone Begin
        hwBTSSLoopLineToneOprTable OBJECT-TYPE
            SYNTAX SEQUENCE OF HwBTSSLoopLineToneOprEntry
            MAX-ACCESS not-accessible
            STATUS current
            DESCRIPTION                      
                "The table hwBTSSLoopLineToneOprTable is used to Loop Line Tone.
                 The index of this table is ifIndex.
                "
            ::= { hwBTestMIBObjects 23 }
                                          
        hwBTSSLoopLineToneOprEntry OBJECT-TYPE
            SYNTAX HwBTSSLoopLineToneOprEntry
            MAX-ACCESS not-accessible
            STATUS current
            DESCRIPTION                      
                "The table hwBTSSLoopLineToneOprTable is used to Loop Line Tone. 
                 The index of this entry is ifIndex.
                "
            INDEX    
                {  
                ifIndex
                }
            ::= { hwBTSSLoopLineToneOprTable 1 }
                        
        HwBTSSLoopLineToneOprEntry ::=
            SEQUENCE 
                { 
                hwBTSSLoopLineToneOprType
                    INTEGER,
                hwBTSSLoopLineToneIntensity
                    INTEGER,
                hwBTSSLoopLineToneBusyFlag
                    INTEGER,
                hwBTSSLoopLineToneResult
                        INTEGER
                }
            
        hwBTSSLoopLineToneOprType OBJECT-TYPE
            SYNTAX INTEGER
                {
                check(1),
                send(2),
                stopsend(3)
                }
            MAX-ACCESS read-write
            STATUS current
            DESCRIPTION
                "Operation type of BTSS loop line tone
                 Options:
                 1. check(1)    - Indicates that checking the signal tone is started 
                 2. send(2)     - Indicates that sending the signal tone is started  
                 3. stopsend(3) - Indicates that stopping sending the signal tone is started
                "
            ::= { hwBTSSLoopLineToneOprEntry 1 }
                                
        hwBTSSLoopLineToneIntensity OBJECT-TYPE
            SYNTAX INTEGER
                {
                fivedB(1),
                tendB(2),
                fifteendB(3)
                }
            MAX-ACCESS read-write
            STATUS current
            DESCRIPTION
                "Tone intensity of BTSS loop line tone. 
                 Options:
                 1. fivedB(1)    - Tone intensity of BTSS is five dB  
                 2. tendB(2)     - Tone intensity of BTSS is ten dB
                 3. fifteendB(3) - Tone intensity of BTSS is fifteen dB
                "
            ::= { hwBTSSLoopLineToneOprEntry 2 }
                        
        hwBTSSLoopLineToneBusyFlag      OBJECT-TYPE
            SYNTAX INTEGER
                {
                busyNoTest(1),
                busyTest(2),
                busystrenTest(3)
                }
            MAX-ACCESS  read-write
            STATUS current
            DESCRIPTION
                "Tested port force test of BTSS loop line tone.
                 Options:
                 1. busyNoTest(1)    - No test on busy
                 2. busyTest(2)      - Test on busy
                 3. busystrenTest(3) - Forced test on busy
                "
            ::= { hwBTSSLoopLineToneOprEntry 3 }
                
        hwBTSSLoopLineToneResult        OBJECT-TYPE
            SYNTAX INTEGER
                {
                succeed(1),
                failed(2)
                }
            MAX-ACCESS read-only
            STATUS current
            DESCRIPTION
                "Operate result of BTSS loop line tone. 
                 Options:
                 1. succeed(1) - The test of BTSS loop line tone is successful
                 2. failed(2)  - Failed in BTSS loop line tone test
                "
            ::= { hwBTSSLoopLineToneOprEntry 4 }
                    
        --loop line tone End   
        hwBTSSSeltAuxPortCfgTable OBJECT-TYPE
            SYNTAX SEQUENCE OF HwBTSSSeltAuxPortCfgEntry
            MAX-ACCESS not-accessible
            STATUS current
            DESCRIPTION                      
                "This table sets assistance port for SELT.
                 The index of this table is hwBTSSSeltAuxedPortIfIndex.
                "
            ::= { hwBTestMIBObjects 24 }
                                
        hwBTSSSeltAuxPortCfgEntry OBJECT-TYPE
            SYNTAX HwBTSSSeltAuxPortCfgEntry
            MAX-ACCESS not-accessible
            STATUS current
            DESCRIPTION                      
                "This table sets assistance port for SELT.
                 The index of this entry is hwBTSSSeltAuxedPortIfIndex.
                "
            INDEX    
                {  
                hwBTSSSeltAuxedPortIfIndex
                }
            ::= { hwBTSSSeltAuxPortCfgTable 1 }
                        
        HwBTSSSeltAuxPortCfgEntry ::=
            SEQUENCE 
                { 
                hwBTSSSeltAuxedPortIfIndex
                    Integer32,
                hwBTSSSeltAuxPortIfIndex
                    Integer32,
                hwBTSSSeltAuxPortRowStatus
                    RowStatus
                }
                
        hwBTSSSeltAuxedPortIfIndex OBJECT-TYPE
            SYNTAX Integer32
            MAX-ACCESS not-accessible
            STATUS current
            DESCRIPTION
                "The ifindex of the Auxed port. If there is only one global Auxed port, 
                 the value is 65535.
                "
            ::= { hwBTSSSeltAuxPortCfgEntry 1 }
                                
        hwBTSSSeltAuxPortIfIndex OBJECT-TYPE
            SYNTAX Integer32
            MAX-ACCESS read-write
            STATUS current
            DESCRIPTION
                "Assistance port ifIndex"
            ::= { hwBTSSSeltAuxPortCfgEntry 2 }
                        
        hwBTSSSeltAuxPortRowStatus      OBJECT-TYPE
            SYNTAX RowStatus
            MAX-ACCESS  read-create
            STATUS current
            DESCRIPTION
                "Row status(add(4), delete(6)) of the Aux port."
            ::= { hwBTSSSeltAuxPortCfgEntry 3 }     
        
        -- 1.3.6.1.4.1.2011.6.21.3.1.1.25
        hwBTSSAdslSeltLevelTable OBJECT-TYPE
            SYNTAX SEQUENCE OF HwBTSSAdslSeltLevelEntry
            MAX-ACCESS not-accessible
            STATUS current
            DESCRIPTION
                "This table supports the configuration of adsl selt level.
                 The indexes of this table are hwFrameIndex and hwSlotIndex.
                "
            ::= { hwBTestMIBObjects 25 }
                
        -- 1.3.6.1.4.1.2011.6.21.3.1.1.25.1
        hwBTSSAdslSeltLevelEntry OBJECT-TYPE
            SYNTAX HwBTSSAdslSeltLevelEntry
            MAX-ACCESS not-accessible
            STATUS current
            DESCRIPTION                      
                "This table supports the configuration of adsl selt level.
                 The indexes of this entry are hwFrameIndex and hwSlotIndex.
                "
            INDEX { hwFrameIndex, hwSlotIndex }
            ::= { hwBTSSAdslSeltLevelTable 1 }
            
            HwBTSSAdslSeltLevelEntry ::=
            SEQUENCE 
                { 
                hwBTSSAdslSeltLevel
                    Integer32
                }
                    
        -- 1.3.6.1.4.1.2011.6.21.3.1.1.25.1.1
        hwBTSSAdslSeltLevel OBJECT-TYPE
            SYNTAX Integer32 (-1 | 1..4)
            MAX-ACCESS read-write
            STATUS current
            DESCRIPTION
                "The level of adsl SELT:
 	         1  Level0;
 	         2  Level1;
 	         3  Level2;
 	         4  Level3.
 	         A special value of -1 indicates the level of adsl SELT is invalid.
                "
            ::= { hwBTSSAdslSeltLevelEntry 1 }
            
        -- 1.3.6.1.4.1.2011.6.21.3.1.1.26
        hwBTSSAdslSeltCalibrationTable  OBJECT-TYPE
            SYNTAX          SEQUENCE OF HWBTSSAdslSeltCalibrationtEntry
            MAX-ACCESS      not-accessible
            STATUS          current
            DESCRIPTION
                "This table describes calibration data of selt test.
                 The index of this table is ifIndex.
                "
            ::= { hwBTestMIBObjects 26 }     
              
        hwBTSSAdslSeltCalibrationEntry   OBJECT-TYPE
            SYNTAX          HWBTSSAdslSeltCalibrationtEntry
            MAX-ACCESS      not-accessible
            STATUS          current
            DESCRIPTION     
                "This table describes calibration data of selt test.
                 The index of this entry is ifIndex.
                "
            INDEX           
                { 
                ifIndex
                }
            ::= { hwBTSSAdslSeltCalibrationTable 1 }
  
        HWBTSSAdslSeltCalibrationtEntry ::=
            SEQUENCE 
                {
                hwBTSSAdslSeltCalibrationInvVendorId  OCTET STRING,
                hwBTSSAdslSeltCalibrationDataSegment1 OCTET STRING,
                hwBTSSAdslSeltCalibrationDataSegment2 OCTET STRING
                }
                    
        -- 1.3.6.1.4.1.2011.6.21.3.1.1.26.1.1
        hwBTSSAdslSeltCalibrationInvVendorId OBJECT-TYPE
            SYNTAX      OCTET STRING  (SIZE(8))
            MAX-ACCESS  read-only
            STATUS       current
            DESCRIPTION
                "It consists of 8 binary octets, including a
                  provider code.
                "
            ::= { hwBTSSAdslSeltCalibrationEntry 1 }
            
        hwBTSSAdslSeltCalibrationDataSegment1 OBJECT-TYPE
            SYNTAX      OCTET STRING(SIZE(0..8192))
            MAX-ACCESS  read-only
            STATUS      current
            DESCRIPTION
                "The part 1 of selt calibration data.
                 The unit of selt calibration data is 0.00001.
                " 
            ::= { hwBTSSAdslSeltCalibrationEntry 2 }
            
        hwBTSSAdslSeltCalibrationDataSegment2 OBJECT-TYPE
            SYNTAX      OCTET STRING(SIZE(0..8192))
            MAX-ACCESS  read-only
            STATUS      current
            DESCRIPTION
                "The part 2 of selt calibration data.
                 The unit of selt calibration data is 0.00001.
                " 
            ::= { hwBTSSAdslSeltCalibrationEntry 3 }
                    
        hwBTestTraps OBJECT IDENTIFIER ::= { hwBtest 2 }
                
        hwBTestTrapVbOids OBJECT IDENTIFIER ::= { hwBTestTraps 1 }
                
        hwBTestVbOidsReason OBJECT IDENTIFIER ::= { hwBTestTrapVbOids 2 }
                
        hwBTSSCqtOfflineReason OBJECT-TYPE
            SYNTAX INTEGER
                {
                commFail(1),
                userReset(2)
                }
            MAX-ACCESS accessible-for-notify
            STATUS current
            DESCRIPTION
                "Cqt module offline reason.
                 Options:
                 1. commFail(1)  - CQT module communication fail. Resolving method:Check CQT module running normal
                 2. userReset(2) - User reset command 
                "
            ::= { hwBTestVbOidsReason 1 }
                        
        hwBTSSRequestID OBJECT-TYPE
            SYNTAX Integer32
            MAX-ACCESS accessible-for-notify
            STATUS current
            DESCRIPTION
                "NMS request ID."
            ::= { hwBTestVbOidsReason 2 }
                
        hwBTestAlarmTraps OBJECT IDENTIFIER ::= { hwBTestTraps 2 }
                
        hwBTestAlarmTrapsOIDs OBJECT IDENTIFIER ::= { hwBTestAlarmTraps 0 }
                
        hwBTSSCqtOnlineTrap NOTIFICATION-TYPE
            OBJECTS { ifIndex }
            STATUS current
            DESCRIPTION 
                "CQT unit online status trap.
                 This notification indicates alarm when CQT unit online. 
                 enumFirst:  
                 explain: CQT module communication OK
                 resolving method:NA.
                "
            ::= { hwBTestAlarmTrapsOIDs 1 }
                
        hwBTSSCqtOfflineTrap NOTIFICATION-TYPE
            OBJECTS { ifIndex, hwBTSSCqtOfflineReason }
            STATUS current
            DESCRIPTION 
                "CQT unit offline status trap.
                 This notification indicates alarm when CQT unit offline.
                "
            ::= { hwBTestAlarmTrapsOIDs 2 }
                
        hwBTestGeneralTraps OBJECT IDENTIFIER ::= { hwBTestTraps 3 }
                
        hwBTestGeneralTrapsOIDs OBJECT IDENTIFIER ::= { hwBTestGeneralTraps 0 }
                
        hwBTSSCoStartTrap NOTIFICATION-TYPE
            OBJECTS { ifIndex, hwBTSSCoOperType, hwBTSSCoTestResult }
            STATUS current
            DESCRIPTION 
                "Start Co test trap.
                 This notification indicates alarm when starting Co test.
                "
            ::= { hwBTestGeneralTrapsOIDs 1 }
                
        hwBTSSCoStopTrap NOTIFICATION-TYPE
            OBJECTS { ifIndex, hwBTSSCoOperType, hwBTSSCoTestResult }
            STATUS current
            DESCRIPTION 
                "Stop Co test trap.
                 This notification indicates alarm when stopping Co test.
                "
            ::= { hwBTestGeneralTrapsOIDs 2 }
                       
        hwBTSSTestedPortOperTrap NOTIFICATION-TYPE
            OBJECTS { ifIndex,hwBTSSTestedPortOperType,hwBTSSTestedPortOperMode,hwBTSSTestedPortOperResult } 
            STATUS current
            DESCRIPTION
                "Tested port operation trap.
                 This notification indicates alarm when tested port operation.
                "
            ::= { hwBTestGeneralTrapsOIDs 3 }
        
        hwBTSSCqtTransTestOperResultTrap NOTIFICATION-TYPE
            OBJECTS { ifIndex,hwBTSSCqtTransTestOperType,hwBTSSCqtTransTestOperResult }
            STATUS current
            DESCRIPTION
                "Cqt transparent test trap.
                 This notification indicates alarm when starting or stoping Cqt transparent test.                          
                "
            ::= { hwBTestGeneralTrapsOIDs 4 }
        
        hwBTSSCqtTransTestResultTrap NOTIFICATION-TYPE
            OBJECTS { ifIndex,hwBTSSCqtTransTestResultLastFlag,hwBTSSCqtTransTestResultNo,hwBTSSCqtTransTestResult }
            STATUS current
            DESCRIPTION
                "Cqt transparent test trap.
                 This notification indicates alarm when reporting the result after Cqt transparent test.
                "
            ::= { hwBTestGeneralTrapsOIDs 5 }
                
        hwBTSSLoopLineToneOperTrap NOTIFICATION-TYPE
            OBJECTS { hwBTSSLoopLineToneResult }
            STATUS current
            DESCRIPTION 
                "loop line tone test result trap: 1:hwBTSSLoopLineToneResult.
                 This notification indicates alarm when reporting the test result of Loop Line Tone. 
                "
            ::= { hwBTestGeneralTrapsOIDs 6 }  
                        
        hwBTSSCaptureTrap NOTIFICATION-TYPE
            OBJECTS 
                { 
                hwBTSSRequestID,
                ifIndex,                   
                hwBTSSTestedPortOperType,  
                hwBTSSTestedPortOperMode,  
                hwBTSSTestedPortOperResult
                }
            STATUS current
            DESCRIPTION 
                "BTSS capture trap.
                 This trap is sent when BTSS capture result reported.
                "
            ::= { hwBTestGeneralTrapsOIDs 7 }
                
        hwBTSSDeltResultDataTrap NOTIFICATION-TYPE
            OBJECTS 
                { 
                hwBTSSAdslDeltTestResultNo,
                hwBTSSRequestID,
                ifIndex,
                hwBTSSAdslDeltTestResultLastFlag,
                hwBTSSAdslDeltTestResult
                }
            STATUS current
            DESCRIPTION 
                "BTSS delt result trap.
                 This notification indicates alarm when captures result data of BTSS delt test.
                "
            ::= { hwBTestGeneralTrapsOIDs 8 }
                                          
	END
