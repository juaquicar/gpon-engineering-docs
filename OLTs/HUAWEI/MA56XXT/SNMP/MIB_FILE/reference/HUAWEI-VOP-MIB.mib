-- ============================================================================
-- Copyright (C) 2016 by  HUAWEI TECHNOLOGIES. All rights reserved.
-- Description:  The MIB is used for xDSL Configuration according to the Vector 
--               of Profiles (VoP) data model specified in Broadband Forum 
--               Technical Report TR-252
--               (http://www.broadband-forum.org/technical/download/TR-252_Issue-3.pdf).
-- Reference:
-- Version: V1.33
--
-- ============================================================================

    HUAWEI-VOP-MIB DEFINITIONS ::= BEGIN

        IMPORTS
            enterprises, Integer32, Unsigned32, Gauge32, OBJECT-TYPE,
            MODULE-IDENTITY, OBJECT-IDENTITY, NOTIFICATION-TYPE
                FROM SNMPv2-SMI
            RowStatus, TruthValue, TEXTUAL-CONVENTION
                FROM SNMPv2-TC
            huaweiUtility
                FROM HUAWEI-MIB
            ifIndex
                FROM IF-MIB
            hwConfigChangeIP
                FROM HUAWEI-DEVICE-MIB;
             
            hwVOPGlobalModule MODULE-IDENTITY
            LAST-UPDATED "201606200000Z"
            ORGANIZATION
                "Huawei Technologies Co.,Ltd."                
            CONTACT-INFO                                        
                         "Huawei Industrial Base                
                          Bantian, Longgang                     
                          Shenzhen 518129                       
                          People's Republic of China            
                          Website: http://www.huawei.com        
                          Email: support@huawei.com             
                         "                                      
            DESCRIPTION
                "The MIB is used for xDSL Configuration according to the Vector 
                 of Profiles (VoP) data model specified in Broadband Forum 
                 Technical Report TR-252
                 (http://www.broadband-forum.org/technical/download/TR-252_Issue-3.pdf)."

            --  Revision history
            REVISION     "201606200000Z"
            DESCRIPTION  "V1.33, Modified the value range of hwVOPGfastLineSpectrumConfProfGfastFallbackFreq.                         
                         "
                         
            REVISION     "201606040000Z"
            DESCRIPTION  "V1.32, Add leaf node hwVOPGfastLineSpectrumConfProfGfastFallbackFreq,hwVOPGfastLineSpectrumConfProfLowFreqEdgeValueUs in hwVOPLineSpectrumConfProfTable.
                          Modify the name of these leaves: hwVOPGfastLineSpectrumConfProfLowFreqEdgeValue.                         
                         "

            REVISION     "201601140000Z"
            DESCRIPTION  "V1.31, Modified leaf node hwVOPGfastSNRMarginConfProfTargetSnrmRmcDs,hwVOPGfastSNRMarginConfProfTargetSnrmRmcUs"

            REVISION     "201511070000Z"
            DESCRIPTION  "V1.30,Added the definition of HWVOPGfastFraVendisc.
                          Add leaf node hwVOPGfastLineSpectrumConfProfGfastCarMaskDs,hwVOPGfastLineSpectrumConfProfGfastCarMaskUs in hwVOPLineSpectrumConfProfTable.
                          Modified the value range of the leaves: hwVOPGfastLineSpectrumConfProfLowFreqEdgeValue.
                          Add leaf node hwVOPGfastSosConfProfFraVenDiscDs, hwVOPGfastSosConfProfFraVenDiscUs in hwVOPSosConfProfTable.
                         "

            REVISION     "201509240000Z"
            DESCRIPTION  "V1.29,Add leaf node hwVOPGfastSNRMarginConfProfTaretSnrmRmcDs,hwVOPGfastSNRMarginConfProfTaretSnrmRmcUs,
	      hwVOPGfastSNRMarginConfProfMinSnrmRmcDs,hwVOPGfastSNRMarginConfProfMinSnrmRmcUs,hwVOPGfastSNRMarginConfProfMaxBLRmcDs,
	      hwVOPGfastSNRMarginConfProfMaxBLRmcUs in hwVOPSNRMarginConfProfTable."
			
            REVISION     "201508130000Z"
            DESCRIPTION  "V1.28,Modify the definition of Xdsl2LineClassMask."
            
            REVISION     "201507100000Z"
            DESCRIPTION  "V1.27,Modify the description of leaf node: hwVOPDPBOConfProfFMax."
            
            REVISION     "201506210000Z"
            DESCRIPTION  "V1.26,Modified the definition of textual conventions: Xdsl2LineProfiles, Xdsl2LineLimitMask, Xdsl2LineUs0Disable.
                         Modified the value range of the leaves: hwVOPDataRateConfProfMinDataRate, hwVOPDataRateConfProfMinResDataRate,
                         hwVOPDataRateConfProfMaxDataRate, hwVOPDataRateConfProfMinDataRateLowPwr, hwVOPDataRateConfProfUsDataRate,
                         hwVOPDataRateConfProfDsDataRate, hwVOPDataRateConfProfMinEtrRtx, hwVOPDataRateConfProfMaxEtrRtx, hwVOPDataRateConfProfMaxNdrRtx,
                         hwVOPDataRateConfProfMaxDataRateLowPwr, hwVOPDPBOConfProfFMax, hwVOPGfastDataRateConfProfDsDataRate.
                         "
            
            REVISION     "201506120000Z"
            DESCRIPTION  "V1.25,Modify the description of hwVOPGfastSosConfProfFraTimeDs(16) and hwVOPGfastSosConfProfFraTimeUs(17)."
                          
            REVISION     "201505180000Z"
            DESCRIPTION  "V1.24,Modify the status of the nodes to obsoleted:hwVOPGfastDataRateConfProfMaxEtr, hwVOPGfastSNRMarginConfProfSnrModeDs, 
                          hwVOPGfastSNRMarginConfProfSnrModeUs, hwVOPGfastSNRMarginConfProfRaModeDs, hwVOPGfastSNRMarginConfProfRaModeUs."
            
            REVISION     "201503180000Z"
            DESCRIPTION  "V1.23,Modified the SYNTAX BITS name of HWVOPGfastProfiles."
            
            REVISION     "201412050000Z"
            DESCRIPTION  "V1.22,Modified the default value of these leaf nodes:hwVOPGfastINPDelayConfProfMaxDelayRtxDs,hwVOPGfastINPDelayConfProfMaxDelayRtxUs.
                          "
                          
            REVISION     "201411130000Z"
            DESCRIPTION  "V1.21,Modified the definition of Xdsl2TransmissionModeType.
                          Added the definition of HWVOPGfastProfiles,HWVOPGfastIarBands,HWVOPGfastRaMode and HWVOPGfastPsdMask.
                          Added the definition of these leaf nodes:hwVOPGfastDataRateConfProfMinEtr,hwVOPGfastDataRateConfProfMaxEtr,hwVOPGfastDataRateConfProfMaxNdr,
                          hwVOPGfastDataRateConfProfUsDataRate,hwVOPGfastDataRateConfProfDsDataRate,hwVOPGfastLineSpectrumConfProfGfastProfiles,hwVOPGfastLineSpectrumConfProfLowFreqEdgeValue,
                          hwVOPGfastLineSpectrumConfProfGfastCarMask,hwVOPGfastModeSpecificPSDConfProfPsdMaskDs,hwVOPGfastModeSpecificPSDConfProfPsdMaskUs,hwVOPGfastModeSpecificPSDConfProfMaxNomAtpDs,
                          hwVOPGfastModeSpecificPSDConfProfMaxNomAtpUs,hwVOPGfastUPBOConfProfUpboKL,hwVOPGfastUPBOConfProfUpboKLF,hwVOPGfastUPBOConfProfKlAuto,hwVOPGfastUPBOConfProfUpboKLREF,
                          hwVOPGfastUPBOConfProfPsdA,hwVOPGfastUPBOConfProfPsdB,hwVOPGfastRFIConfProfRfiBands,hwVOPGfastRFIConfProfIarBands,hwVOPGfastSNRMarginConfProfMinSnrmDs,
                          hwVOPGfastSNRMarginConfProfMinSnrmUs,hwVOPGfastSNRMarginConfProfTargetSnrmDs,hwVOPGfastSNRMarginConfProfTargetSnrmUs,hwVOPGfastSNRMarginConfProfMaxSnrmDs,
                          hwVOPGfastSNRMarginConfProfMaxSnrmUs,hwVOPGfastSNRMarginConfProfSnrModeDs,hwVOPGfastSNRMarginConfProfSnrModeUs,hwVOPGfastSNRMarginConfProfRaModeDs,hwVOPGfastSNRMarginConfProfRaModeUs,
                          hwVOPGfastSNRMarginConfProfRaUsNrmDs,hwVOPGfastSNRMarginConfProfRaUsNrmUs,hwVOPGfastSNRMarginConfProfRaDsNrmDs,hwVOPGfastSNRMarginConfProfRaDsNrmUs,hwVOPGfastSNRMarginConfProfUsTimeDs,
                          hwVOPGfastSNRMarginConfProfUsTimeUs,hwVOPGfastSNRMarginConfProfDsTimeDs,hwVOPGfastSNRMarginConfProfDsTimeUs,hwVOPGfastINPDelayConfProfMaxDelayRtxDs,hwVOPGfastINPDelayConfProfMaxDelayRtxUs,
                          hwVOPGfastINPDelayConfProfMinInpShineRtxDs,hwVOPGfastINPDelayConfProfMinInpShineRtxUs,hwVOPGfastINPDelayConfProfShineRatioRtxDs,hwVOPGfastINPDelayConfProfShineRatioRtxUs,
                          hwVOPGfastINPDelayConfProfMinInpReinRtxDs,hwVOPGfastINPDelayConfProfMinInpReinRtxUs,hwVOPGfastINPDelayConfProfIatReinRtxDs,hwVOPGfastINPDelayConfProfIatReinRtxUs,
                          hwVOPGfastINPDelayConfProfMinRNRatioRtxDs,hwVOPGfastINPDelayConfProfMinRNRatioRtxUs,hwVOPGfastSosConfProfFraTimeDs,hwVOPGfastSosConfProfFraTimeUs,hwVOPGfastSosConfProfFraNtonesDs,
                          hwVOPGfastSosConfProfFraNtonesUs,hwVOPGfastSosConfProfFraMinRtxUcDs,hwVOPGfastSosConfProfFraMinRtxUcUs."
            
            REVISION     "201410130000Z"
            DESCRIPTION  "V1.20,modified the value range of hwVOPSetupSosProfId."

            REVISION     "201408180000Z"
            DESCRIPTION  "V1.19,modified the definition of Xdsl2RaMode."
            
            REVISION     "201406300000Z"
            DESCRIPTION  "V1.18, Modify the version of the mib."
         
            REVISION     "201405230000Z" 
            DESCRIPTION  "V1.17, modify the reference from TR-165 to TR-252 and the reference paragraph.
                          Add the leaves hwVOPDataRateConfProfMaxDataRateLowPwr, hwVOPDataRateConfProfL2MinDataRateToL0ActDataRate  
                          in hwVOPDataRateConfProfTable.
                          "
                          
            REVISION     "201405050000Z" 
            DESCRIPTION  "V1.16, modify the reference from TR-165 to TR-252 and the reference paragraph.
                          Add the leave hwVOPDataRateConfProfMinSosBr in hwVOPDataRateConfProfTable.
                          Add the definition of the table hwVOPSosConfProfTable and these leaf nodes hwVOPSosProfileIndexNext, 
                          hwVOPSetupSosProfId, hwVOPSetupSosProfDescription, hwVOPActSetupSosProfId, hwVOPActSetupSosProfDescription
                          for the Save our Showtime Profile.
                          Modified the leaf nodes hwVOPProfileIDChangeTrap for supporting the Save our Showtime Profile.
                          Modified the description of leaf nodes Xdsl2LineClassMask.
                          Delete the reference of hwVOPLineSpectrumConfProfXtuTransSysEna.
                          Add leaf nodes hwVOPINPDelayConfProfMaxDelayOctetSplit in hwVOPINPDelayConfProfTable.
                          "
                          
            REVISION     "201308010000Z" 
            DESCRIPTION  "V1.15, added hwOntVdsl2VOPSetupTable.
                         "            
            REVISION     "201302230000Z" 
            DESCRIPTION  "V1.14, Modified leaf node hwVOPModeSpecificPSDConfProfMaxNomAtpDs and hwVOPModeSpecificPSDConfProfMaxNomAtpUs value 
                          range from  (0..255) to  (0..510).
                         "
                         
            REVISION     "201112020000Z" 
            DESCRIPTION  "V1.13, added the definition of these leaf nodes:hwVOPUPBOConfProfAeleMode, hwVOPUPBOConfProfUpboElmt.
                         "
            REVISION     "201107200000Z" 
            DESCRIPTION  "V1.12, added the the definition of these leaf nodes:hwVOPSetupUsDataRateProf1Description,hwVOPSetupDsDataRateProf1Description,hwVOPSetupInpDelayProf1Description,
                          hwVOPSetupUsDataRateProf2Description,hwVOPSetupDsDataRateProf2Description,hwVOPSetupInpDelayProf2Description,hwVOPSetupLSpectrumProfDescription,
                          hwVOPSetupUpboProfDescription,hwVOPSetupDpboProfDescription,hwVOPSetupRfiProfDescription,hwVOPSetupNoiseMarginProfDescription,hwVOPSetupVNoiseProfDescription,
                          hwVOPSetupInmProfDescription,hwVOPActSetupUsDataRateProf1Description,hwVOPActSetupDsDataRateProf1Description,hwVOPActSetupInpDelayProf1Description,
                          hwVOPActSetupUsDataRateProf2Description,hwVOPActSetupDsDataRateProf2Description,hwVOPActSetupInpDelayProf2Description,hwVOPActSetupLSpectrumProfDescription,
                          hwVOPActSetupUpboProfDescription,hwVOPActSetupDpboProfDescription,hwVOPActSetupRfiProfDescription,hwVOPActSetupNoiseMarginProfDescription,
                          hwVOPActSetupVNoiseProfDescription,hwVOPActSetupInmProfDescription.
                          Modified the range of these leaf nodes: hwVOPDataRateConfProfIndex, hwVOPLineSpectrumConfProfIndex, hwVOPLineSpectrumConfProfModeSpecificPSDProfilesUsed,
                          hwVOPModeSpecificPSDConfProfIndex, hwVOPUPBOConfProfIndex, hwVOPDPBOConfProfIndex, hwVOPRFIConfProfIndex, hwVOPSNRMarginConfProfIndex, hwVOPINPDelayConfProfIndex,
                          hwVOPVirtualNoiseConfProfIndex, hwVOPINMConfProfIndex, hwVOPSetupUsDataRateProfId1, hwVOPSetupDsDataRateProfId1, hwVOPSetupInpDelayProfId1, 
                          hwVOPSetupUsDataRateProfId2, hwVOPSetupDsDataRateProfId2, hwVOPSetupInpDelayProfId2, hwVOPSetupUsDataRateProfId3, hwVOPSetupDsDataRateProfId3, 
                          hwVOPSetupInpDelayProfId3, hwVOPSetupUsDataRateProfId4, hwVOPSetupDsDataRateProfId4, hwVOPSetupInpDelayProfId4, hwVOPSetupLSpectrumProfId, hwVOPSetupUpboProfId,
                          hwVOPSetupDpboProfId, hwVOPSetupRfiProfId, hwVOPSetupNoiseMarginProfId, hwVOPSetupVNoiseProfId, hwVOPSetupInmProfId, hwVOPActSetupUsDataRateProfId1, 
                          hwVOPActSetupDsDataRateProfId1, hwVOPActSetupInpDelayProfId1, hwVOPActSetupUsDataRateProfId2, hwVOPActSetupDsDataRateProfId2, hwVOPActSetupInpDelayProfId2, 
                          hwVOPActSetupUsDataRateProfId3, hwVOPActSetupDsDataRateProfId3, hwVOPActSetupInpDelayProfId3, hwVOPActSetupUsDataRateProfId4, hwVOPActSetupDsDataRateProfId4,
                          hwVOPActSetupInpDelayProfId4, hwVOPActSetupLSpectrumProfId, hwVOPActSetupNoiseMarginProfId, hwVOPActSetupVNoiseProfId, hwVOPActSetupUpboProfId, 
                          hwVOPActSetupDpboProfId, hwVOPActSetupRfiProfId, hwVOPActSetupInmProfId.
                          Modify the status of the nodes to deprecated:hwVOPModeSpecificPSDConfProfXdslMode.
                         "
            REVISION     "201106080000Z" 
            DESCRIPTION  "V1.11, modified the description of leaf node:hwVOPINPDelayConfProfInitPolicy.
                          Modified the range of the Xdsl2ChInitPolicy type.
                          Add the range of the leaf node:hwVOPDataRateConfProfMinDataRate,hwVOPDataRateConfProfMinResDataRate,hwVOPDataRateConfProfMaxDataRate,hwVOPDataRateConfProfMinDataRateLowPwr,
                          hwVOPDataRateConfProfUsDataRate,hwVOPDataRateConfProfDsDataRate,hwVOPDataRateConfProfMinEtrRtx,hwVOPDataRateConfProfMaxEtrRtx,hwVOPDataRateConfProfMaxNdrRtx.
                         "
            REVISION     "201105030000Z" 
            DESCRIPTION  "V1.10, add the definition of the table hwVOPINMConfProfTable and these leaf nodes hwVOPINMProfileIndexNext,hwVOPSetupInmProfIdhwVOPActSetupInmProfId
                          for the Impulse Noise Monitoring Profile.
                          Modified the leaf nodes hwVOPProfileIDChangeTrap for supporting the Impulse Noise Monitoring Profile.                          
                          Modified the default value of the leaf node:hwVOPModeSpecificPSDConfProfMaxNomPsdUs.
                          Modified the units of the leaf node:hwVOPDPBOConfProfMus.
                         "             
            REVISION     "201102210000Z" 
            DESCRIPTION  "V1.09, modified the description of these leaf nodes about default value:hwVOPLineSpectrumConfProfL2Time,hwVOPLineSpectrumConfProfL2Atpr,hwVOPLineSpectrumConfProfL2Atprt,
                          hwVOPLineSpectrumConfProfBitSwapDs,hwVOPLineSpectrumConfProfBitSwapUs,hwVOPModeSpecificPSDConfProfMaxNomPsdDs,hwVOPModeSpecificPSDConfProfMaxNomPsdUs,
                          hwVOPModeSpecificPSDConfProfMaxNomAtpDs,hwVOPModeSpecificPSDConfProfMaxNomAtpUs,hwVOPModeSpecificPSDConfProfaxAggRxPwrUs,hwVOPModeSpecificPSDConfProfClassMask,
                          hwVOPUPBOConfProfPsdAUs1,hwVOPUPBOConfProfPsdBUs1,hwVOPUPBOConfProfPsdAUs2,hwVOPUPBOConfProfPsdBUs2,hwVOPDPBOConfProfCableModelA,hwVOPDPBOConfProfCableModelB,
                          hwVOPDPBOConfProfCableModelC,hwVOPDPBOConfProfMus,hwVOPDPBOConfProfFMin,hwVOPDPBOConfProfFMax,hwVOPSNRMarginConfProfMinSnrmDs,hwVOPSNRMarginConfProfMinSnrmUs,
                          hwVOPSNRMarginConfProfMinSnrmUs,hwVOPSNRMarginConfProfMaxSnrmDs,hwVOPSNRMarginConfProfMaxSnrmUs,hwVOPSNRMarginConfProfRaModeDs,hwVOPSNRMarginConfProfRaModeUs,
                          hwVOPSNRMarginConfProfRaUsNrmDs,hwVOPSNRMarginConfProfRaUsNrmUs.
                         " 
            
            REVISION     "201012220000Z" 
            DESCRIPTION  "V1.08, modified the definition of these leaf nodes:hwVOPDataRateConfProfMinDataRate,hwVOPDataRateConfProfMaxDataRate,
                          hwVOPDataRateConfProfUsDataRate,hwVOPDataRateConfProfDsDataRate,hwVOPLineSpectrumConfProfForceInpDs,hwVOPLineSpectrumConfProfForceInpUs,  
                          hwVOPINPDelayConfProfMinProtectionDs,hwVOPINPDelayConfProfMinProtection8Ds,hwVOPINPDelayConfProfMaxDelayDs,hwVOPINPDelayConfProfMinProtectionUs,
                          hwVOPINPDelayConfProfMinProtection8Us,hwVOPINPDelayConfProfMaxDelayUs and hwVOPINPDelayConfProfInitPolicy.  
                          add these leaf nodes:hwadsl2LineAlarmConfProfileXtucThresh15MinLeftrs,hwVOPDataRateConfProfMinEtrRtx,hwVOPDataRateConfProfMaxEtrRtx,
                          hwVOPDataRateConfProfMaxNdrRtx,hwVOPLineSpectrumConfProfRtxModeDs,hwVOPLineSpectrumConfProfRtxModeUs,hwVOPLineSpectrumConfProfLeftrThreshDs,
                          hwVOPLineSpectrumConfProfLeftrThreshUs,hwVOPINPDelayConfProfMaxDelayRtxDs,hwVOPINPDelayConfProfMaxDelayRtxUs,hwVOPINPDelayConfProfMinDelayRtxDs,
                          hwVOPINPDelayConfProfMinDelayRtxUs,hwVOPINPDelayConfProfMinInpShineRtxDs,hwVOPINPDelayConfProfMinInpShineRtxUs,hwVOPINPDelayConfProfMinInp8ShineRtxDs,
                          hwVOPINPDelayConfProfMinInp8ShineRtxUs,hwVOPINPDelayConfProfShineRatioRtxDs,hwVOPINPDelayConfProfShineRatioRtxUs,hwVOPINPDelayConfProfMinInpReinRtxDs,  
                          hwVOPINPDelayConfProfMinInpReinRtxUs,hwVOPINPDelayConfProfMinInp8ReinRtxDs,hwVOPINPDelayConfProfMinInp8ReinRtxUs,hwVOPINPDelayConfProfIatReinRtxDs,
                          hwVOPINPDelayConfProfIatReinRtxUs.
                         "
            REVISION     "201012100000Z" 
            DESCRIPTION  "V1.07, Modified the range of the leaf node:hwVOPSetupUpboProfId, hwVOPActSetupUpboProfId." 

            REVISION     "201009150000Z" 
            DESCRIPTION  "V1.06, modified the definition of hwVOPVirtualNoiseConfProfTxRefVnDs and hwVOPVirtualNoiseConfProfTxRefVnUs.
                                 Modified the range of the leaf node:hwVOPDataRateConfProfIndex, hwVOPLineSpectrumConfProfIndex,
                                 hwVOPModeSpecificPSDConfProfIndex, hwVOPUPBOConfProfIndex, hwVOPDPBOConfProfIndex, hwVOPRFIConfProfIndex,
                                 hwVOPSNRMarginConfProfIndex, hwVOPINPDelayConfProfIndex, hwVOPVirtualNoiseConfProfIndex and related leaf." 

            REVISION     "201007010000Z" 
            DESCRIPTION  "V1.05, modified the definition of the trap node hwVOPProfileIDChangeTrap for trap optimization.
                                 Added the definition of the leaf node hwVOPDPBOConfFEXTFactor in hwVOPDPBOConfProfEntry." 
      
            REVISION     "201005170000Z" 
            DESCRIPTION  "V1.04, modified the hwVOPLineSpectrumConfProfL3Time ranges from 0 to 65535 seconds.
                                 Deleted adlu128Eu128(10) in Xdsl2LinePsdMaskSelectUs for standard." 
      
            REVISION     "201004150000Z" 
            DESCRIPTION  "V1.03, modified the range of the Xdsl2LinePsdMaskSelectUs type.
                                 Modified the range of the Xdsl2RfiBands type." 
                                 
            REVISION     "201003300000Z" 
            DESCRIPTION  "V1.02, modified the range of the hwVOPLineSpectrumConfProfModeSpecificPSDProfilesUsed." 
                                 
            REVISION     "201003150000Z" 
            DESCRIPTION  "V1.01, add MIB for Vector of Profiles (VoP) management."    
                                          
            REVISION     "201001250000Z"                                                 
            DESCRIPTION  "V1.00, initial version" 
            
            ::= { huaweiUtility 144 }

--
-- Textual conventions
--

        Xdsl2MaxBer ::= TEXTUAL-CONVENTION
            STATUS current
            DESCRIPTION
                "Objects with this syntax are configuration parameters
                 that reference the maximum Bit Error Rate (BER).
                 Options:
                 1. eminus3 (1)  - Maximum BER=E^-3
                 2. eminus5 (2)  - Maximum BER=E^-5
                 3. eminus7 (3)  - Maximum BER=E^-7
                "
            SYNTAX INTEGER {
                eminus3(1),
                eminus5(2),
                eminus7(3)
            }

        Xdsl2TransmissionModeType ::= TEXTUAL-CONVENTION
            STATUS current
            DESCRIPTION
                "A set of xDSL line transmission modes, with one bit
                 per mode.  The notes (F) and (L) denote Full-Rate and
                 Lite/splitterless respectively.
                 Options:
                 Bit 00 : Regional Std. (ANSI T1.413) (F)
                 Bit 01 : Regional Std. (ETSI DTS/TM06006) (F)
                 Bit 02 : G.992.1 POTS non-overlapped (F)
                 Bit 03 : G.992.1 POTS overlapped (F)
                 Bit 04 : G.992.1 ISDN non-overlapped (F)
                 Bit 05 : G.992.1 ISDN overlapped (F)
                 Bit 06 : G.992.1 TCM-ISDN non-overlapped (F)
                 Bit 07 : G.992.1 TCM-ISDN overlapped (F)
                 Bit 08 : G.992.2 POTS non-overlapped (L)
                 Bit 09 : G.992.2 POTS overlapped (L)
                 Bit 10 : G.992.2 with TCM-ISDN non-overlapped (L)
                 Bit 11 : G.992.2 with TCM-ISDN overlapped (L)
                 Bit 12 : G.992.1 TCM-ISDN symmetric (F) -- not in G.997.1
                 Bit 13-17: Reserved
                 Bit 18 : G.992.3 POTS non-overlapped (F)
                 Bit 19 : G.992.3 POTS overlapped (F)
                 Bit 20 : G.992.3 ISDN non-overlapped (F)
                 Bit 21 : G.992.3 ISDN overlapped (F)
                 Bit 22-23: Reserved
                 Bit 24 : G.992.4 POTS non-overlapped (L)
                 Bit 25 : G.992.4 POTS overlapped (L)
                 Bit 26-27: Reserved
                 Bit 28 : G.992.3 Annex I All-Digital non-overlapped (F)
                 Bit 29 : G.992.3 Annex I All-Digital overlapped (F)
                 Bit 30 : G.992.3 Annex J All-Digital non-overlapped (F)
                 Bit 31 : G.992.3 Annex J All-Digital overlapped (F)
                 Bit 32 : G.992.4 Annex I All-Digital non-overlapped (L)
                 Bit 33 : G.992.4 Annex I All-Digital overlapped (L)
                 Bit 34 : G.992.3 Annex L POTS non-overlapped, mode 1,
                                        wide U/S (F)
                 Bit 35 : G.992.3 Annex L POTS non-overlapped, mode 2,
                                          narrow U/S(F)
                 Bit 36 : G.992.3 Annex L POTS overlapped, mode 3,
                                          wide U/S (F)
                 Bit 37 : G.992.3 Annex L POTS overlapped, mode 4,
                                           narrow U/S (F)
                 Bit 38 : G.992.3 Annex M POTS non-overlapped (F)
                 Bit 39 : G.992.3 Annex M POTS overlapped (F)
                 Bit 40 : G.992.5 POTS non-overlapped (F)
                 Bit 41 : G.992.5 POTS overlapped (F)
                 Bit 42 : G.992.5 ISDN non-overlapped (F)
                 Bit 43 : G.992.5 ISDN overlapped (F)
                 Bit 44-45: Reserved
                 Bit 46 : G.992.5 Annex I All-Digital non-overlapped (F)
                 Bit 47 : G.992.5 Annex I All-Digital overlapped (F)
                 Bit 48 : G.992.5 Annex J All-Digital non-overlapped (F)
                 Bit 49 : G.992.5 Annex J All-Digital overlapped (F)
                 Bit 50 : G.992.5 Annex M POTS non-overlapped (F)
                 Bit 51 : G.992.5 Annex M POTS overlapped (F)
                 Bit 52-64: Reserved
                 Bit 65~71 (vdsl1 reserved)
                 Bit 72 : G.993.2 Annex A POTS (F)
                 Bit 73 : G.993.2 Annex A ISDN (F)
                 Bit 74 : G.993.2 Annex B POTS (F)
                 Bit 75 : G.993.2 Annex B ISDN (F)
                 Bit 76 : G.993.2 Annex C POTS (F)
                 Bit 77 : G.993.2 Annex C ISDN (F)
                 Bit 78~80 : Reserved
                 Bit 81 : G.9701 (F)
                 Bit 82-127: Reserved
                "
            SYNTAX BITS {
                 ansit1413(0),
                 etsi(1),
                 g9921PotsNonOverlapped(2),
                 g9921PotsOverlapped(3),
                 g9921IsdnNonOverlapped(4),
                 g9921isdnOverlapped(5),
                 g9921tcmIsdnNonOverlapped(6),
                 g9921tcmIsdnOverlapped(7),
                 g9922potsNonOverlapped(8),
                 g9922potsOverlapped(9),
                 g9922tcmIsdnNonOverlapped(10),
                 g9922tcmIsdnOverlapped(11),
                 g9921tcmIsdnSymmetric(12),
                 reserved1(13),
                 reserved2(14),
                 reserved3(15),
                 reserved4(16),
                 reserved5(17),
                 g9923PotsNonOverlapped(18),
                 g9923PotsOverlapped(19),
                 g9923IsdnNonOverlapped(20),
                 g9923isdnOverlapped(21),
                 reserved6(22),
                 reserved7(23),
                 g9924potsNonOverlapped(24),
                 g9924potsOverlapped(25),
                 reserved8(26),
                 reserved9(27),
                 g9923AnnexIAllDigNonOverlapped(28),
                 g9923AnnexIAllDigOverlapped(29),
                 g9923AnnexJAllDigNonOverlapped(30),
                 g9923AnnexJAllDigOverlapped(31),
                 g9924AnnexIAllDigNonOverlapped(32),
                 g9924AnnexIAllDigOverlapped(33),
                 g9923AnnexLMode1NonOverlapped(34),
                 g9923AnnexLMode2NonOverlapped(35),
                 g9923AnnexLMode3Overlapped(36),
                 g9923AnnexLMode4Overlapped(37),
                 g9923AnnexMPotsNonOverlapped(38),
                 g9923AnnexMPotsOverlapped(39),
                 g9925PotsNonOverlapped(40),
                 g9925PotsOverlapped(41),
                 g9925IsdnNonOverlapped(42),
                 g9925isdnOverlapped(43),
                 reserved10(44),
                 reserved11(45),
                 g9925AnnexIAllDigNonOverlapped(46),
                 g9925AnnexIAllDigOverlapped(47),
                 g9925AnnexJAllDigNonOverlapped(48),
                 g9925AnnexJAllDigOverlapped(49),
                 g9925AnnexMPotsNonOverlapped(50),
                 g9925AnnexMPotsOverlapped(51),
                 reserved12(52),
                 reserved13(53),
                 reserved14(54),
                 reserved15(55),
                 reserved16(56),
                 reserved17(57),
                 reserved18(58),
                 reserved19(59),
                 reserved20(60),
                 reserved21(61),
                 reserved22(62),
                 reserved23(63),
                 reserved24(64),
                 reserved25(65),
                 reserved26(66),
                 reserved27(67),
                 reserved28(68),
                 reserved29(69),
                 reserved30(70),
                 reserved31(71),
                 g9932AnnexAPots(72),
                 g9932AnnexAIsdn(73),
                 g9932AnnexBPots(74),
                 g9932AnnexBIsdn(75),
                 g9932AnnexCPots(76),
                 g9932AnnexCIsdn(77),
                 reserved32(78),
                 reserved33(79),
                 reserved34(80),
                 g9701(81),
                 reserved35(82),
                 reserved36(83),
                 reserved37(84),
                 reserved38(85),
                 reserved39(86),
                 reserved40(87),
                 reserved41(88),
                 reserved42(89),
                 reserved43(90),
                 reserved44(91),
                 reserved45(92),
                 reserved46(93),
                 reserved47(94),
                 reserved48(95),
                 reserved49(96),
                 reserved50(97),
                 reserved51(98),
                 reserved52(99),
                 reserved53(100),
                 reserved54(101),
                 reserved55(102),
                 reserved56(103),
                 reserved57(104),
                 reserved58(105),
                 reserved59(106),
                 reserved60(107),
                 reserved61(108),
                 reserved62(109),
                 reserved63(110),
                 reserved64(111),
                 reserved65(112),
                 reserved66(113),
                 reserved67(114),
                 reserved68(115),
                 reserved69(116),
                 reserved70(117),
                 reserved71(118),
                 reserved72(119),
                 reserved73(120),
                 reserved74(121),
                 reserved75(122),
                 reserved76(123),
                 reserved77(124),
                 reserved78(125),
                 reserved79(126),
                 reserved80(127)
              }

        Xdsl2LinePmMode ::= TEXTUAL-CONVENTION
            STATUS current
            DESCRIPTION
                "Objects with this syntax are configuration parameters
                 that reference the power modes/states into which the xTU-C or
                 xTU-R may autonomously transit.
                 It is a BITS structure that allows control of the following
                 transit options:
                 1. allowTransitionsToIdle (0)    - xTU may autonomously transit
                                                    to idle (L3) state.
                 2. allowTransitionsToLowPower (1)- xTU may autonomously transit
                                                    to low-power (L1/L2) state.
                "

            SYNTAX BITS {
                allowTransitionsToIdle(0),
                allowTransitionsToLowPower(1)
            }

        Xdsl2ScMaskDs ::= TEXTUAL-CONVENTION
            STATUS current
            DESCRIPTION
                "Each one of the 512 bits in this OCTET STRING array represents
                 the corresponding subcarrier in the downstream direction.
                 A bit value of one indicates that a subcarrier is masked.
                "
           SYNTAX OCTET STRING (SIZE(0..64))

        Xdsl2ScMaskUs ::= TEXTUAL-CONVENTION
            STATUS current
            DESCRIPTION
                "Each one of the 64 bits in this OCTET STRING array represents
                 the corresponding subcarrier in the upstream direction.
                 A bit value of one indicates that a subcarrier is masked.
                "
            SYNTAX OCTET STRING (SIZE (0..8))

        Xdsl2CarMask ::= TEXTUAL-CONVENTION
            STATUS current
            DESCRIPTION
                "This type defines an array of bands. Each band is represented
                 by 4 octets and there is a maximum of 32 bands allowed.
                 Each band consists of a 16 bit start subcarrier index followed by
                 a 16 bit stop subcarrier index.
                 Subcarrier index is an unsigned number in the range 0 to NSC-1.
                "
            SYNTAX OCTET STRING (SIZE(0..128))

        Xdsl2LineProfiles ::= TEXTUAL-CONVENTION
            STATUS current
            DESCRIPTION
                "Objects with this syntax reference the list of ITU-T G.993.2 implementation profiles
                 supported by an xTU, enabled on the VDSL2 line or active on that line.
                "
            SYNTAX BITS {
                profile8a(0),
                profile8b(1),
                profile8c(2),
                profile8d(3),
                profile12a(4),
                profile12b(5),
                profile17a(6),
                profile30a(7),
                --
                profile35b(8),
                reserved1(9),
                reserved2(10),
                reserved3(11),
                reserved4(12),
                reserved5(13),
                reserved6(14),
                reserved7(15),
                --
                reserved8(16),
                reserved9(17),
                reserved10(18),
                reserved11(19),
                reserved12(20),
                reserved13(21),
                reserved14(22),
                reserved15(23),
                --
                reserved16(24),
                reserved17(25),
                reserved18(26),
                reserved19(27),
                reserved20(28),
                reserved21(29),
                reserved22(30),
                reserved23(31)
            }

        Xdsl2LineUs0Mask ::= TEXTUAL-CONVENTION
            STATUS current
            DESCRIPTION
                "The US0 PSD masks to be allowed by the near-end xTU on the line.
                 This parameter is only defined for G.993.2 Annex A.
                 It is represented as a bitmap (0 if not allowed and 1 if allowed)
                 with the following definitions.
                "
            SYNTAX BITS {
                eu32(0),
                eu36(1),
                eu40(2),
                eu44(3),
                eu48(4),
                eu52(5),
                eu56(6),
                eu60(7),
                --
                eu64(8),
                eu128(9),
                reserved1(10),
                reserved2(11),
                reserved3(12),
                reserved4(13),
                reserved5(14),
                reserved6(15),
                --
                adlu32(16),
                adlu36(17),
                adlu40(18),
                adlu44(19),
                adlu48(20),
                adlu52(21),
                adlu56(22),
                adlu60(23),
                --
                adlu64(24),
                adlu128(25),
                reserved7(26),
                reserved8(27),
                reserved9(28),
                reserved10(29),
                reserved11(30),
                reserved12(31)
            }


        Xdsl2LineCeFlag ::= TEXTUAL-CONVENTION
            STATUS current
            DESCRIPTION
                "This type is used to enable the use of the optional
                 cyclic extension values. If the bit is set to 1, the optional
                 cyclic extension values may be used. Otherwise, the cyclic
                 extension shall be forced to the mandatory length (5N/32).
                 Options:
                 1. enableCyclicExtension (0) - Enable use of optional Cyclic Extension values.
                "
            SYNTAX BITS {
                enableCyclicExtension(0)
            }

        Xdsl2PsdMaskDs ::= TEXTUAL-CONVENTION
            STATUS current
            DESCRIPTION
                "This is a structure that represents up to 32 PSD Mask breakpoints.
                 Each breakpoint occupies 3 octets:
                 The first two octets hold the index of the subcarrier associated with the breakpoint.
                 The third octet holds the PSD reduction at the breakpoint
                 from 0 (0dBm/Hz) to 255 (-127.5 dBm/Hz) using units of 0.5dBm/Hz.
                 Subcarrier index is an unsigned number in the range 0 to NSCds-1.
                "
            SYNTAX OCTET STRING (SIZE(0..96))

        Xdsl2PsdMaskUs ::= TEXTUAL-CONVENTION
            STATUS current
            DESCRIPTION
                "This is a structure that represents up to 16 PSD Mask breakpoints.
                 Each breakpoint occupies 3 octets:
                 The first two octets hold the index of the subcarrier associated with the breakpoint.
                 The third octet holds the PSD reduction at the breakpoint
                 from 0 (0dBm/Hz) to 255 (-127.5 dBm/Hz) using units of 0.5dBm/Hz.
                 Subcarrier index is an unsigned number in the range 0 to NSCus-1.
                "
            SYNTAX OCTET STRING (SIZE(0..48))

        Xdsl2LinePsdMaskSelectUs ::= TEXTUAL-CONVENTION
            STATUS current
            DESCRIPTION
                "This type is used to define which upstream PSD mask is enabled.
                 This type is used only for Annexes J and M of ITU-T Recs G.992.3 and G.992.5.
                 Options:
                 1. adlu32Eu32 (1)    - ADLU-32 / EU-32
                 2. adlu36Eu36 (2)    - ADLU-36 / EU-36
                 3. adlu40Eu40 (3)    - ADLU-40 / EU-40
                 4. adlu44Eu44 (4)    - ADLU-44 / EU-44
                 5. adlu48Eu48 (5)    - ADLU-48 / EU-48
                 6. adlu52Eu52 (6)    - ADLU-52 / EU-52
                 7. adlu56Eu56 (7)    - ADLU-56 / EU-56
                 8. adlu60Eu60 (8)    - ADLU-60 / EU-60
                 9. adlu64Eu64 (9)    - ADLU-64 / EU-64
                "
            SYNTAX INTEGER {
                adlu32Eu32(1),
                adlu36Eu36(2),
                adlu40Eu40(3),
                adlu44Eu44(4),
                adlu48Eu48(5),
                adlu52Eu52(6),
                adlu56Eu56(7),
                adlu60Eu60(8),
                adlu64Eu64(9)
            }

        Xdsl2LineLimitMask ::= TEXTUAL-CONVENTION
            STATUS current
            DESCRIPTION
                "The G.993.2 limit PSD mask for each class of profile.
                 The profiles are grouped in following profile classes:
                 - Class 8: Profiles 8a, 8b, 8c, 8d
                 - Class 12: Profiles 12a, 12b
                 - Class 17: Profile 17a
                 - Class 30: Profile 30a
                 - Class 35: Profile 35b.
                "
            SYNTAX BITS {
                profile8Limit1(0),
                profile8Limit2(1),
                profile8Limit3(2),
                profile8Limit4(3),
                profile8Limit5(4),
                profile8Limit6(5),
                profile8Limit7(6),
                profile8Limit8(7),
                profile8Limit9(8),
                profile8Limit10(9),
                profile8Limit11(10),
                profile8Limit12(11),
                profile8Limit13(12),
                profile8Limit14(13),
                profile8Limit15(14),
                profile8Limit16(15),
                --
                profile12Limit1(16),
                profile12Limit2(17),
                profile12Limit3(18),
                profile12Limit4(19),
                profile12Limit5(20),
                profile12Limit6(21),
                profile12Limit7(22),
                profile12Limit8(23),
                profile12Limit9(24),
                profile12Limit10(25),
                profile12Limit11(26),
                profile12Limit12(27),
                profile12Limit13(28),
                profile12Limit14(29),
                profile12Limit15(30),
                profile12Limit16(31),
                --
                profile17Limit1(32),
                profile17Limit2(33),
                profile17Limit3(34),
                profile17Limit4(35),
                profile17Limit5(36),
                profile17Limit6(37),
                profile17Limit7(38),
                profile17Limit8(39),
                profile17Limit9(40),
                profile17Limit10(41),
                profile17Limit11(42),
                profile17Limit12(43),
                profile17Limit13(44),
                profile17Limit14(45),
                profile17Limit15(46),
                profile17Limit16(47),
                --
                profile30Limit1(48),
                profile30Limit2(49),
                profile30Limit3(50),
                profile30Limit4(51),
                profile30Limit5(52),
                profile30Limit6(53),
                profile30Limit7(54),
                profile30Limit8(55),
                profile30Limit9(56),
                profile30Limit10(57),
                profile30Limit11(58),
                profile30Limit12(59),
                profile30Limit13(60),
                profile30Limit14(61),
                profile30Limit15(62),
                profile30Limit16(63),
                --
                profile35Limit1(64),
                profile35Limit2(65),
                profile35Limit3(66),
                profile35Limit4(67),
                profile35Limit5(68),
                profile35Limit6(69),
                profile35Limit7(70),
                profile35Limit8(71),
                profile35Limit9(72),
                profile35Limit10(73),
                profile35Limit11(74),
                profile35Limit12(75),
                profile35Limit13(76),
                profile35Limit14(77),
                profile35Limit15(78),
                profile35Limit16(79)
            }

        Xdsl2LineUs0Disable ::= TEXTUAL-CONVENTION
            STATUS current
            DESCRIPTION
                "Indicates if US0 is disabled for each limit PSD mask.
                 The profiles are grouped in following profile classes:
                 - Class 8: Profiles 8a, 8b, 8c, 8d
                 - Class 12: Profiles 12a, 12b
                 - Class 17: Profile 17a
                 - Class 30: Profile 30a
                 - Class 35: Profile 35b.
                "
            SYNTAX BITS {
                profile8Us0Disable1(0),
                profile8Us0Disable2(1),
                profile8Us0Disable3(2),
                profile8Us0Disable4(3),
                profile8Us0Disable5(4),
                profile8Us0Disable6(5),
                profile8Us0Disable7(6),
                profile8Us0Disable8(7),
                profile8Us0Disable9(8),
                profile8Us0Disable10(9),
                profile8Us0Disable11(10),
                profile8Us0Disable12(11),
                profile8Us0Disable13(12),
                profile8Us0Disable14(13),
                profile8Us0Disable15(14),
                profile8Us0Disable16(15),
                profile12Us0Disable1(16),
                profile12Us0Disable2(17),
                profile12Us0Disable3(18),
                profile12Us0Disable4(19),
                profile12Us0Disable5(20),
                profile12Us0Disable6(21),
                profile12Us0Disable7(22),
                profile12Us0Disable8(23),
                profile12Us0Disable9(24),
                profile12Us0Disable10(25),
                profile12Us0Disable11(26),
                profile12Us0Disable12(27),
                profile12Us0Disable13(28),
                profile12Us0Disable14(29),
                profile12Us0Disable15(30),
                profile12Us0Disable16(31),
                profile17Us0Disable1(32),
                profile17Us0Disable2(33),
                profile17Us0Disable3(34),
                profile17Us0Disable4(35),
                profile17Us0Disable5(36),
                profile17Us0Disable6(37),
                profile17Us0Disable7(38),
                profile17Us0Disable8(39),
                profile17Us0Disable9(40),
                profile17Us0Disable10(41),
                profile17Us0Disable11(42),
                profile17Us0Disable12(43),
                profile17Us0Disable13(44),
                profile17Us0Disable14(45),
                profile17Us0Disable15(46),
                profile17Us0Disable16(47),
                profile30Us0Disable1(48),
                profile30Us0Disable2(49),
                profile30Us0Disable3(50),
                profile30Us0Disable4(51),
                profile30Us0Disable5(52),
                profile30Us0Disable6(53),
                profile30Us0Disable7(54),
                profile30Us0Disable8(55),
                profile30Us0Disable9(56),
                profile30Us0Disable10(57),
                profile30Us0Disable11(58),
                profile30Us0Disable12(59),
                profile30Us0Disable13(60),
                profile30Us0Disable14(61),
                profile30Us0Disable15(62),
                profile30Us0Disable16(63),
                profile35Us0Disable1(64),
                profile35Us0Disable2(65),
                profile35Us0Disable3(66),
                profile35Us0Disable4(67),
                profile35Us0Disable5(68),
                profile35Us0Disable6(69),
                profile35Us0Disable7(70),
                profile35Us0Disable8(71),
                profile35Us0Disable9(72),
                profile35Us0Disable10(73),
                profile35Us0Disable11(74),
                profile35Us0Disable12(75),
                profile35Us0Disable13(76),
                profile35Us0Disable14(77),
                profile35Us0Disable15(78),
                profile35Us0Disable16(79)
            }

        Xdsl2LineClassMask ::= TEXTUAL-CONVENTION
            STATUS current
            DESCRIPTION
                "VDSL2 PSD Mask Class.
                 The limit Power Spectral Density masks are grouped in
                 the following PSD mask classes:
                 Class 998     Annex A: D-32, D-48, D-64, D-128.
                 Class 997-M1c Annex B: 997-M1c-A-7.
                 Class 997-M1x Annex B: 997-M1x-M-8, 997-M1x-M.
                 Class 997-M2x Annex B: 997-M2x-M-8, 997-M2x-A, 997-M2x-M,
                                        997E17-M2x-NUS0, 997E30-M2x-NUS0.
                 Class 998-M1x Annex B: 998-M1x-A, 998-M1x-B, 998-M1x-NUS0.
                 Class 998-M2x Annex B: 998-M2x-A, 998-M2x-M, 998-M2x-B,
                                        998-M2x-NUS0, 998E17-M2x-NUS0,
                                        998E17-M2x-NUS0-M, 998E17-M2x-A, 
                                        998E30-M2x-NUS0, 998E30-M2x-NUS0-M.
                 Class 998ADE-M2x Annex B: Annex B: 998-M2x-A, 998-M2x-M,
                                           998-M2x-B, 998-M2x-NUS0,
                                           998ADE17-M2x-A, 998ADE17-M2x-B,
                                           998ADE17-M2x-NUS0-M,
                                           998ADE17-SPE-M2x-A,
                                           998ADE30-M2x-NUS0-A,
                                           998ADE30-M2x-NUS0-M.
                 Class 998-B   Annex C: POTS-138b, POTS-276b per C.2.1.1
                                        in G.993.2, TCM-ISDN per C.2.1.2
                                        in G.993.2.
                 Class 998-CO  Annex C: POTS-138co, POTS-276co per C.2.1.1
                                        in G.993.2.
                 Class HPE-M1  Annex B: HPE17-M1-NUS0, HPE30-M1-NUS0.
                 Class 998E35-M2X Annex B: E35-M2x-A.
                 Class 998ADE35-M2x Annex B: ADE35-M2x-A, ADE35-M2x-B, ADE35-M2x-M.
                "
            SYNTAX INTEGER {
                none(1),
                a998ORb997M1cORc998B(2),
                b997M1xOR998co(3),
                b997M2x(4),
                b998M1x(5),
                b998M2x(6),
                b998AdeM2x(7),
                bHpeM1(8),
                b998E35M2x(9),
                b998Ade35M2x(10)
            }

        Xdsl2UpboKLF ::= TEXTUAL-CONVENTION
            STATUS      current
            DESCRIPTION
                "Defines the upstream power backoff force mode (UPBOKLF).
                 Options:
                 1. auto(1)         - The VTUs will autonomously determine the
                                      electrical length.
                 2. override(2)     - Forces the VTU-R to use the electrical
                                      length, kl0, of the CO-MIB (UPBOKL) to
                                      compute the UPBO.
                 3. disableUpbo(3)  - Disables UPBO such that UPBO is not
                                      utilized.
                "
            SYNTAX INTEGER {
                 auto(1),
                 override(2),
                 disableUpbo(3)
             }

        Xdsl2BandUs ::= TEXTUAL-CONVENTION
            STATUS current
            DESCRIPTION
                "Each value identifies a specific band in the upstream
                 transmission direction (Excluding US0 band.).
                 The possible values which identify a band are as follows:
                 1. us1(5)          - Upstream band number 1 (US1).
                 2. us2(7)          - Upstream band number 2 (US2).
                 3. us3(9)          - Upstream band number 3 (US3).
                 4. us4(11)         - Upstream band number 4 (US4).
                "
            SYNTAX INTEGER {
                us1(5),
                us2(7),
                us3(9),
                us4(11)
            }

        Xdsl2RfiBands ::= TEXTUAL-CONVENTION
            STATUS current
            DESCRIPTION
                "This type defines a subset of downstream PSD mask breakpoints used to
                 notch radio frequency interference (RFI) bands.
                 Each RFI band is represented by 4 octets:
                 16 bit start subcarrier index followed by a 16 bit stop subcarrier index.
                 There is a maximum of 64 RFI bands allowed.
                 Subcarrier index is an unsigned number in the range 0 to NSC-1.
                "
            SYNTAX OCTET STRING (SIZE(0..256))

        Xdsl2LineSnrMode ::= TEXTUAL-CONVENTION
            STATUS current
            DESCRIPTION
                "This type is used to enable the transmitter referred virtual noise.
                 Options:
                 1. virtualNoiseDisabled (1) - Virtual noise is disabled.
                 2. virtualNoiseEnabled (2)  - Virtual noise is enabled.
                "
            SYNTAX INTEGER {
                virtualNoiseDisabled(1),
                virtualNoiseEnabled(2)
            }

        Xdsl2RaMode ::= TEXTUAL-CONVENTION
            STATUS current
            DESCRIPTION
                "Specifies the rate adaptation behavior for the line.
                 Options:
                 1. manual (1)       - No Rate-Adaptation. The initialization process
                                       attempts to synchronize to a specified rate.
                 2. raInit (2)       - Rate-Adaptation during initialization process only,
                                       which attempts to synchronize to a rate between minimum
                                       and maximum specified values.
                 3. dynamicRa (3)    - Dynamic Rate-Adaptation during initialization process
                                       as well as during Showtime.
                 4. dynamicwithsos(4)- Rate-Adaptation during show time by SOS and SRA.
 	                               In this mode, enabling of SOS and SRA is mandatory.
                  
                "
            SYNTAX INTEGER {
                manual(1),
                raInit(2),
                dynamicRa(3),
                dynamicwithsos(4)
            }

        Xdsl2SymbolProtection ::= TEXTUAL-CONVENTION
            STATUS current
            DESCRIPTION
                "This type specifies the minimum impulse noise protection for the bearer channel
                 if it is transported over DMT symbols with a subcarrier spacing of 4.3125 kHz.
                 The possible values are:
                 'noProtection' (i.e., INP not required), 'halfSymbol' (i.e., INP
                 length is 1/2 symbol), and 1-16 symbols in steps of 1 symbol.
                "
            SYNTAX INTEGER {
                noProtection (1),
                halfSymbol (2),
                singleSymbol (3),
                twoSymbols (4),
                threeSymbols (5),
                fourSymbols (6),
                fiveSymbols (7),
                sixSymbols (8),
                sevenSymbols (9),
                eightSymbols (10),
                nineSymbols (11),
                tenSymbols (12),
                elevenSymbols (13),
                twelveSymbols (14),
                thirteeSymbols (15),
                fourteenSymbols (16),
                fifteenSymbols (17),
                sixteenSymbols (18)
            }

        Xdsl2SymbolProtection8 ::= TEXTUAL-CONVENTION
            STATUS current
            DESCRIPTION
                "This type specifies the minimum impulse noise protection
                 for the bearer channel if it is transported over DMT symbols
                 with a subcarrier spacing of 8.625 kHz.
                 The possible values are:
                 'noProtection' (i.e., INP not required) and 1-16 symbols in
                 steps of 1 symbol.
                "
            SYNTAX INTEGER {
                noProtection (1),
                singleSymbol (2),
                twoSymbols (3),
                threeSymbols (4),
                fourSymbols (5),
                fiveSymbols (6),
                sixSymbols (7),
                sevenSymbols (8),
                eightSymbols (9),
                nineSymbols (10),
                tenSymbols (11),
                elevenSymbols (12),
                twelveSymbols (13),
                thirteeSymbols (14),
                fourteenSymbols (15),
                fifteenSymbols (16),
                sixteenSymbols (17)
            }

        Xdsl2ChInitPolicy ::= TEXTUAL-CONVENTION
            STATUS current
            DESCRIPTION
                "This syntax serves for channel configuration parameters
                 that reference the channel initialization policy.
                 Options:
                 1. policy0 (1)      - Policy 0 according to the applicable standard
                 2. policy1 (2)      - Policy 1 according to the applicable standard
                 3. policy2 (3)      - Policy 2 according to the applicable standard
                "
            SYNTAX INTEGER {
                policy0(1),
                policy1(2),
                policy2(3)
            }

        Xdsl2LineTxRefVnDs ::= TEXTUAL-CONVENTION
            STATUS current
            DESCRIPTION
                "This is a structure that represents up to 32 PSD Mask breakpoints.
                 Each breakpoint occupies 3 octets:
                 The first two octets hold the index of the subcarrier associated with the breakpoint.
                 The third octet holds the PSD reduction at the breakpoint from 0 (-140 dBm/Hz)
                 to 200 (-40 dBm/Hz) using units of 0.5dBm/Hz.
                 A special value of 255 indicates a noise level of 0 W/Hz.
                 Subcarrier index is an unsigned number in the range 0 to NSCds-1.
                "
            SYNTAX OCTET STRING (SIZE(0..96))

        Xdsl2LineTxRefVnUs ::= TEXTUAL-CONVENTION
            STATUS current
            DESCRIPTION
                "This is a structure that represents up to 16 PSD Mask breakpoints.
                 Each breakpoint occupies 3 octets:
                 The first two octets hold the index of the subcarrier associated with the breakpoint.
                 The third octet holds the PSD reduction at the breakpoint from 0 (-140 dBm/Hz)
                 to 200 (-40 dBm/Hz) using units of 0.5dBm/Hz.
                 A special value of 255 indicates a noise level of 0 W/Hz.
                 Subcarrier index is an unsigned number in the range 0 to NSCus-1.
                "
            SYNTAX OCTET STRING (SIZE(0..48))

        Xdsl2DataPathMode ::= TEXTUAL-CONVENTION
            STATUS current
            DESCRIPTION
                "The channel data path mode:
                 Options:
                 1. atm (1)  - Indicates the channel data path mode is ATM
                 2. ptm (2)  - Indicates the channel data path mode is PTM
                 3. both (3) - Indicates both ATM and PTM data path mode are supported
                "
            SYNTAX INTEGER {
                atm(1),
                ptm(2),
                both(3)
            }

        Xdsl2LineClockReferenceType ::= TEXTUAL-CONVENTION
            STATUS    current
            DESCRIPTION
                "The various clock references for the xDSL line, represented as an enumeration.
                 Options:
                 1. freeRun(1) - Clock references for the xDSL line is freeRun
                 2. system(2)  - Clock references for the xDSL line is system
                "
            SYNTAX    INTEGER {
                freeRun(1),
                system(2)
            }

        Xdsl2BitSwap ::= TEXTUAL-CONVENTION
            STATUS current
            DESCRIPTION
                "The bit swap upstream or downstream of a line.
                 Options:
                 1. disable (1)  - Disable the bit swap upstream or downstream of a line.
                 2. enable (2)   - Enable the bit swap upstream or downstream of a line.
                "
            SYNTAX INTEGER {
                disable(1),
                enable(2)
            }

        Xdsl2UpboBoostMode ::= TEXTUAL-CONVENTION
            STATUS current
            DESCRIPTION
                "The Equalized FEXT UPBO method.
                 Options:
                 1.disable(1) - The Equalized FEXT UPBO method is not supported.
                 2.enable(2)  - The Equalized FEXT UPBO method is supported.
                "
            SYNTAX INTEGER {
                disable(1),
                enable(2)
            }

        HWVOPProfileIndexOrZeroType ::= TEXTUAL-CONVENTION
            STATUS current
            DESCRIPTION
                "This type should be used as index parameter for vop profiles.
                 0 is a special value, which could only be used for profile assignment parameters
                 in case of optional profiles and is not a valid profile index inside profile tables.
                 A maximum number of valid profile indices will be set to vendor-specific value,
                 unless otherwise specified in this document.
                "
            SYNTAX Unsigned32 (0 | 1..4294967295)

        HWVOPSetupIndexOrZeroType ::= TEXTUAL-CONVENTION
            STATUS current
            DESCRIPTION
                "This type should be used as index parameter for Vector Of Profiles (VoP) setup
                 table (hwVOPSetupTable), when rows in that table are created by the management system.
                 0 is a special value, which is not a valid VoP setup index and serves solely as an indication,
                 e.g., may mark a situation in which no more rows can be supported in that table.
                 A maximum number of valid indices will be set to vendor-specific value,
                 unless otherwise specified in this document.
                "
            SYNTAX Unsigned32 (0 | 1..4294967295)

        HWVOPAttachmentMethods ::= TEXTUAL-CONVENTION
            STATUS current
            DESCRIPTION
                "This type should be used for objects that refer to methods of attaching
                 Vector Of configuration Profiles (VoP) to xDSL lines.
                 Two attachment methods are available.
                 The 'direct' method is associating each xDSL line with a dedicated VoP instance.
                 The 'indirect' method is creating a pool of VoP instances and associating each
                 xDSL line with one of the VoP instances in that pool. In 'indirect' attachment-method
                 associating an xDSL line with a VoP instance is performed by setting the
                 xdsl2LineConfTemplate object (VDSL2-LINE-MIB) of the related line to the identifier
                 of that VoP. The VoP instance currently used by the xDSL line is provided
                 by the xdsl2LineStatusActTemplate object (VDSL2-LINE-MIB) of the respective line.
                 The two objects mentioned above are unused in 'direct' attachment-method.
                "
            SYNTAX BITS
            {
                direct(0),
                indirect(1)
            }
            
        HWVOPGfastProfiles ::= TEXTUAL-CONVENTION
            STATUS      current
            DESCRIPTION
                "This type defines for each profile whether operation according to that profile is allowed or disallowed.
                 It is represented as a bitmap (0 if not allowed and 1 if allowed)with the following definitions.
                "
            SYNTAX BITS {
                fastProfile106(0),
                fastProfile212(1)
            }
            
        HWVOPGfastIarBands ::= TEXTUAL-CONVENTION
            STATUS      current
            DESCRIPTION
                "This type defines each International Amateur Radio (IAR) band whether transmit PSD reduction 
                 is enabled or disabled in that band.
                 It is represented as a bitmap (0 if not allowed and 1 if allowed)with the following definitions.
                "
            SYNTAX BITS {
                iarBand1800To2000(0),
                iarBand3500To4000(1),
                iarBand7000To7300(2),
                iarBand10100To10150(3),
                iarBand14000To14350(4),
                iarBand18068To18168(5),
                iarBand21000To21450(6),
                iarBand24890To24990(7),
                iarBand28000To29700(8),
                iarBand50000To54000(9),
                iarBand70000To70500(10),
                iarBand144000To148000(11)
            }
            
        HWVOPGfastRaMode ::= TEXTUAL-CONVENTION
            STATUS current
            DESCRIPTION
                "Specifies the rate adaptation behavior for the line.
                 Options:
                 1. manual (1)       - No Rate-Adaptation. The initialization process
                                       attempts to synchronize to a specified rate.
                 2. raInit (2)       - Rate-Adaptation during initialization process only,
                                       which attempts to synchronize to a rate between minimum
                                       and maximum specified values.
                 3. dynamicRa (3)    - Dynamic Rate-Adaptation during initialization process
                                       as well as during Showtime.
                 4. dynamicwithfra(4)- Rate-Adaptation during show time by FRA and SRA.
 	                               In this mode, enabling of FRA and SRA is mandatory.
                  
                "
            SYNTAX INTEGER {
                manual(1),
                raInit(2),
                dynamicRa(3),
                dynamicwithfra(4)
            }
            
        HWVOPGfastPsdMask ::= TEXTUAL-CONVENTION
            STATUS current
            DESCRIPTION
                "This is a structure that represents up to 32 PSD Mask breakpoints.
                 Each breakpoint occupies 3 octets:
                 The first two octets hold the index of the subcarrier associated with the breakpoint.
                 The third octet holds the PSD reduction at the breakpoint
                 from 0 (0dBm/Hz) to 255 (-127.5 dBm/Hz) using units of 0.5dBm/Hz.
                 Subcarrier index is an unsigned number in the range 0 to NSCds-1.
                "
            SYNTAX OCTET STRING (SIZE(0..96))
                                                

--
-- Node definitions
--
-- [MF] Needs to be switched to official IANA branch when approved by IETF
--

        hwVOPConformance OBJECT IDENTIFIER ::= { hwVOPGlobalModule 2 }

        hwVOPTraps OBJECT IDENTIFIER ::= { hwVOPGlobalModule 3 }

        hwVOPCommonTraps OBJECT IDENTIFIER ::= { hwVOPTraps 1 }

        hwVOPXdslPortTraps OBJECT IDENTIFIER ::= { hwVOPCommonTraps 1 }

        hwVOPAlarmTraps OBJECT IDENTIFIER ::= { hwVOPTraps 2 }

        hwVOPGroups OBJECT IDENTIFIER ::= { hwVOPConformance 1 }

        hwVOPObjects OBJECT IDENTIFIER ::= { hwVOPGlobalModule 1 }

        hwVOPProfiles OBJECT IDENTIFIER ::= { hwVOPObjects 1 }


        hwVOPDataRateProfileIndexNext OBJECT-TYPE
            SYNTAX HWVOPProfileIndexOrZeroType
            MAX-ACCESS read-only
            STATUS current
            DESCRIPTION
                "This object contains an appropriate value to be used for hwVOPDataRateConfProfIndex
                 when creating entries in the hwVOPDataRateConfProfTable.
                 The value '0' indicates that no unassigned entries are available.

                 To obtain the value of hwVOPDataRateConfProfIndex for a new entry in the table,
                 the manager issues a management protocol retrieval operation.
                 The agent will determine through its local policy when this index value will be
                 made available for reuse.
                "
            ::= { hwVOPProfiles 1 }

        hwVOPDataRateConfProfTable OBJECT-TYPE
            SYNTAX SEQUENCE OF HWVOPDataRateConfProfEntry
            MAX-ACCESS not-accessible
            STATUS current
            DESCRIPTION
                "The table hwVOPDataRateConfProfTable contains data rate configuration parameters
                 for the DSL channel(s).
                 Entries in this table MUST be maintained in a persistent manner.

                 Two default profiles with index numbers 1 and 2 will always exist and its parameters
                 will be set to vendor-specific values, unless otherwise specified in this document
                 The index of this table is hwVOPDataRateConfProfIndex.
                "
            REFERENCE
                "Broadband Forum TR-252, paragraph #5.5"
            ::= { hwVOPProfiles 2 }


        hwVOPDataRateConfProfEntry OBJECT-TYPE
            SYNTAX HWVOPDataRateConfProfEntry
            MAX-ACCESS not-accessible
            STATUS current
            DESCRIPTION
                "The table hwVOPDataRateConfProfTable contains data rate configuration parameters
                 for the DSL channel(s).
                 Entries in this table MUST be maintained in a persistent manner.

                 Two default profiles with index numbers 1 and 2 will always exist and its parameters
                 will be set to vendor-specific values, unless otherwise specified in this document
                 The index of this entry is hwVOPDataRateConfProfIndex.
                "
            INDEX { hwVOPDataRateConfProfIndex }
            ::= { hwVOPDataRateConfProfTable 1 }


        HWVOPDataRateConfProfEntry ::=
            SEQUENCE {
                hwVOPDataRateConfProfIndex                     Unsigned32,
                hwVOPDataRateConfProfRowStatus                 RowStatus,
                hwVOPDataRateConfProfDescription               OCTET STRING,
                hwVOPDataRateConfProfMinDataRate               Gauge32,
                hwVOPDataRateConfProfMinResDataRate            Gauge32,
                hwVOPDataRateConfProfMaxDataRate               Gauge32,
                hwVOPDataRateConfProfMinDataRateLowPwr         Gauge32,
                hwVOPDataRateConfProfMaxBer                    Xdsl2MaxBer,
                hwVOPDataRateConfProfUsDataRate                Gauge32,
                hwVOPDataRateConfProfDsDataRate                Gauge32,
                hwVOPDataRateConfProfDataPathMode              Xdsl2DataPathMode,
                hwVOPDataRateConfProfMinEtrRtx                 Gauge32,
                hwVOPDataRateConfProfMaxEtrRtx                 Gauge32, 
                hwVOPDataRateConfProfMaxNdrRtx                 Gauge32,
                hwVOPDataRateConfProfMaxDataRateLowPwr         Gauge32,
                hwVOPDataRateConfProfL2MinDataRateToL0ActDataRate Gauge32,
                hwVOPDataRateConfProfMinSosBr                  Unsigned32,
                hwVOPGfastDataRateConfProfMinEtr               Gauge32,
                hwVOPGfastDataRateConfProfMaxEtr               Gauge32,
                hwVOPGfastDataRateConfProfMaxNdr               Gauge32,
                hwVOPGfastDataRateConfProfUsDataRate           Gauge32,
                hwVOPGfastDataRateConfProfDsDataRate           Gauge32
            }


        hwVOPDataRateConfProfIndex OBJECT-TYPE
            SYNTAX Unsigned32 (1..4294967295)
            MAX-ACCESS accessible-for-notify
            STATUS current
            DESCRIPTION
                "The hwVOPDataRateConfProfIndex identifies a row in the hwVOPDataRateConfProfTable."
            ::= { hwVOPDataRateConfProfEntry 1 }


        hwVOPDataRateConfProfRowStatus OBJECT-TYPE
            SYNTAX RowStatus
            MAX-ACCESS read-create
            STATUS current
            DESCRIPTION
                "The hwVOPDataRateConfProfRowStatus is used to create a new row or to modify
                 or delete an existing row in this table.
                 A profile is activated by setting this object to 'active'.
                 Before a profile can be deleted or taken out of service (by setting this object to
                 'destroy' or 'notInService'), it MUST be first unreferenced from all associated DSL lines.

                 A row in hwVOPDataRateConfProfTable is said to be unreferenced
                 when there is no instance of hwVOPActSetupUsDataRateProfId1-4 and
                 hwVOPActSetupDsDataRateProfId1-4 in the hwVOPActSetupTable which refers to the row.
                "
            ::= { hwVOPDataRateConfProfEntry 2 }


        hwVOPDataRateConfProfDescription OBJECT-TYPE
            SYNTAX OCTET STRING (SIZE (0..128))
            MAX-ACCESS read-create
            STATUS current
            DESCRIPTION
                "The hwVOPDataRateConfProfDescription contains an optional human readable description for the profile."
            ::= { hwVOPDataRateConfProfEntry 3 }


        hwVOPDataRateConfProfMinDataRate OBJECT-TYPE
            SYNTAX Gauge32 (32000..500000000)
            UNITS "bit/s"
            MAX-ACCESS read-create
            STATUS current
            DESCRIPTION
                "If retransmission is not used in a given transmit direction,this parameter specifics
                minimum data rate for the bearer channel. The rate is coded in steps of 1000 bit/s."
            REFERENCE
                "ITU-T G.997.1, paragraph #7.3.2.1.1 (Minimum data rate)
                 Unit: bit/s.
                "
            ::= { hwVOPDataRateConfProfEntry 4 }


        hwVOPDataRateConfProfMinResDataRate OBJECT-TYPE
            SYNTAX Gauge32 (32000..500000000)
            UNITS "bit/s"
            MAX-ACCESS read-create
            STATUS current
            DESCRIPTION
                "The minimum reserved net data rate for the bearer channel, coded in bit/s.
                 This parameter is only used if the Rate Adaptation Mode in the direction
                 of the bearer channel (i.e., xdsl2LConfProfRaModeDs) is set to dynamicRa.
                 Unit: bit/s.
                "
            REFERENCE
                "ITU-T G.997.1, paragraph #7.3.2.1.2 (Minimum reserved data rate)"
            ::= { hwVOPDataRateConfProfEntry 5 }


        hwVOPDataRateConfProfMaxDataRate OBJECT-TYPE
            SYNTAX Gauge32 (32000..500000000)
            UNITS "bit/s"
            MAX-ACCESS read-create
            STATUS current
            DESCRIPTION
                "If retransmission is not used in a given transmit direction,this parameter specifics
                maximum data rate for the bearer channel. The rate is coded in steps of 1000 bit/s."                
            REFERENCE
                "ITU-T G.997.1, paragraph #7.3.2.1.3 (Maximum data rate)
                 Unit: bit/s.
                "
            ::= { hwVOPDataRateConfProfEntry 6 }


        hwVOPDataRateConfProfMinDataRateLowPwr OBJECT-TYPE
            SYNTAX Gauge32 (32000..500000000)
            UNITS "bit/s"
            MAX-ACCESS read-create
            STATUS current
            DESCRIPTION
                "This parameter specifies the minimum net data rate for the bearer channel
                 as desired by the operator of the system during the low power state (L1/L2).
                 The power management low power states L1 and L2 are defined in ITU-T Recs
                 G.992.2 and G.992.3 respectively.
                 The data rate is coded in steps of bit/s.
                 Unit: bit/s.
                "
            REFERENCE
                "ITU-T G.997.1, paragraph #7.3.2.1.5 (Minimum Data Rate in low power state)"
            ::= { hwVOPDataRateConfProfEntry 7 }


        hwVOPDataRateConfProfMaxBer OBJECT-TYPE
            SYNTAX Xdsl2MaxBer
            MAX-ACCESS read-create
            STATUS current
            DESCRIPTION
                "Maximum Bit Error Ratio of the bearer channel."
            REFERENCE
                "ITU-T G.997.1, paragraph #7.3.2.6 (Maximum bit error ratio)"
            DEFVAL { eminus5 }
            ::= { hwVOPDataRateConfProfEntry 8 }


        hwVOPDataRateConfProfUsDataRate OBJECT-TYPE
            SYNTAX Gauge32 (0..500000000)
            UNITS "bit/s"
            MAX-ACCESS read-create
            STATUS current
            DESCRIPTION
                "If retransmission is not used in a given transmit direction, This parameter is 
                a threshold on the net data rate upshift achieved over one or more bearer channel data 
                rate adaptations. An upshift rate change alarm (event) is triggered when the actual 
                data rate exceeds the data rate at the last entry into showtime by more than the threshold.
                The data rate threshold is coded in bit/s.
                Unit: bit/s.
                "
            REFERENCE
                "ITU-T G.997.1, paragraph #7.3.2.8.1 (Data rate threshold upshift)"
            ::= { hwVOPDataRateConfProfEntry 9 }


        hwVOPDataRateConfProfDsDataRate OBJECT-TYPE
            SYNTAX Gauge32 (0..500000000)
            UNITS "bit/s"
            MAX-ACCESS read-create
            STATUS current
            DESCRIPTION
                "If retransmission is not used in a given transmit direction, This parameter is 
                a threshold on the net data rate downshift achieved over one or more bearer channel data 
                rate adaptations. A downshift rate change alarm (event) is triggered when the actual 
                data rate is below the data rate at the last entry into showtime by more than the threshold. 
                The data rate threshold is coded in bit/s.
                Unit: bit/s.
                "
            REFERENCE
                "ITU-T G.997.1, paragraph #7.3.2.8.2 (Data rate threshold downshift)"
            ::= { hwVOPDataRateConfProfEntry 10 }


        hwVOPDataRateConfProfDataPathMode OBJECT-TYPE
            SYNTAX      Xdsl2DataPathMode
            MAX-ACCESS  read-create
            STATUS      current
            DESCRIPTION
                "The channel data path mode."
            DEFVAL       { both }
            ::= { hwVOPDataRateConfProfEntry 11 }
            
        hwVOPDataRateConfProfMinEtrRtx  OBJECT-TYPE
            SYNTAX      Gauge32 (32000..500000000)
            UNITS       "bit/s"
            MAX-ACCESS  read-create
            STATUS      current
            DESCRIPTION
               "If retransmission is used in a given transmit direction, this parameter specifies the
                minimum expected throughput for the bearer channel.The values range in steps of 1000 bit/s. 
                Unit: bit/s
               "
            REFERENCE    "ITU-T G.997.1, paragraph 7.3.2.1.8"
            ::= { hwVOPDataRateConfProfEntry 12 }               
            
        hwVOPDataRateConfProfMaxEtrRtx  OBJECT-TYPE
            SYNTAX      Gauge32 (32000..500000000)
            UNITS       "bit/s"
            MAX-ACCESS  read-create
            STATUS      current
            DESCRIPTION
               "If retransmission is used in a given transmit direction, this parameter specifies the
                maximum expected throughput for the bearer channel.The values range in steps of 1000 bit/s. 
                Unit: bit/s
               "
            REFERENCE    "ITU-T G.997.1, paragraph 7.3.2.1.9"
            ::= { hwVOPDataRateConfProfEntry 13 }  

        hwVOPDataRateConfProfMaxNdrRtx  OBJECT-TYPE
            SYNTAX      Gauge32 (32000..500000000)
            UNITS       "bit/s"
            MAX-ACCESS  read-create
            STATUS      current
            DESCRIPTION
               "If retransmission is used in a given transmit direction, this parameter specifies the
                maximum net data rate for the bearer channel. The values range in steps of 1000 bit/s.
                Unit: bit/s
               "
            REFERENCE    "ITU-T G.997.1, paragraph 7.3.2.1.10"
            ::= { hwVOPDataRateConfProfEntry 14 } 
            
        hwVOPDataRateConfProfMaxDataRateLowPwr  OBJECT-TYPE
            SYNTAX      Gauge32 (32000..500000000)
            UNITS       "bit/s"
            MAX-ACCESS  read-create
            STATUS      current
            DESCRIPTION
               "Indicates the maximum Data Rate in Low Power state.
                Unit: bits/second
               "
            REFERENCE    "ITU-T G.997.1, paragraph 7.3.2.1"
            ::= { hwVOPDataRateConfProfEntry 15 } 
            
        hwVOPDataRateConfProfL2MinDataRateToL0ActDataRate  OBJECT-TYPE
            SYNTAX      Gauge32(0..99)
            MAX-ACCESS  read-create
            STATUS      current
            DESCRIPTION
               "The ratio between data rate in low power state and data rate in normal state.
               "
            ::= { hwVOPDataRateConfProfEntry 16 }             

        hwVOPDataRateConfProfMinSosBr  OBJECT-TYPE
            SYNTAX      Unsigned32(0..65535)
            UNITS       "Kbps"
            MAX-ACCESS  read-create
            STATUS      current
            DESCRIPTION
               "This parameter specifies the minimum net data rate required for a valid SOS request.
                The valid range of values is from 0 to 65535 Kbps.
                Unit: Kbps
               "
            ::= { hwVOPDataRateConfProfEntry 17 }
            
        hwVOPGfastDataRateConfProfMinEtr  OBJECT-TYPE
            SYNTAX      Gauge32 (32000..2000000000)
            UNITS       "bit/s"
            MAX-ACCESS  read-create
            STATUS      current
            DESCRIPTION
               "This parameter specifies the minimum expected throughput for the bearer channel.
                The values range in steps of 1000 bit/s. 
                Unit: bit/s
               "
            DEFVAL { 32000 }
            ::= { hwVOPDataRateConfProfEntry 18 }               
            
        hwVOPGfastDataRateConfProfMaxEtr  OBJECT-TYPE
            SYNTAX      Gauge32 (32000..2000000000)
            UNITS       "bit/s"
            MAX-ACCESS  read-create
            STATUS      obsolete
            DESCRIPTION
               "This parameter specifies the G.fast maximum expected throughput for the bearer channel.
                The values range in steps of 1000 bit/s. 
                Unit: bit/s
               "
            DEFVAL { 2000000000 }               
            ::= { hwVOPDataRateConfProfEntry 19 }  

        hwVOPGfastDataRateConfProfMaxNdr  OBJECT-TYPE
            SYNTAX      Gauge32 (32000..2000000000)
            UNITS       "bit/s"
            MAX-ACCESS  read-create
            STATUS      current
            DESCRIPTION
               "This parameter specifies the G.fast maximum net data rate for the bearer channel. 
                The values range in steps of 1000 bit/s.
                Unit: bit/s
               "
            DEFVAL { 2000000000 }                              
            ::= { hwVOPDataRateConfProfEntry 20 }             
            
        hwVOPGfastDataRateConfProfUsDataRate OBJECT-TYPE
            SYNTAX Gauge32 (0..2000000000)
            UNITS "bit/s"
            MAX-ACCESS read-create
            STATUS current
            DESCRIPTION
                "This parameter is a threshold on the G.fast net data rate upshift achieved over one or more 
                 bearer channel data rate adaptations. An upshift rate change alarm (event) is triggered when 
                 the actual data rate exceeds the data rate at the last entry into showtime by more than the 
                 threshold.
                 The data rate threshold is coded in bit/s.
                 Unit: bit/s.
                "
            DEFVAL { 0 }                               
            ::= { hwVOPDataRateConfProfEntry 21 }


        hwVOPGfastDataRateConfProfDsDataRate OBJECT-TYPE
            SYNTAX Gauge32 (0..2000000000)
            UNITS "bit/s"
            MAX-ACCESS read-create
            STATUS current
            DESCRIPTION
                "This parameter is a threshold on the G.fast net data rate downshift achieved over one or more 
                 bearer channel data rate adaptations. A downshift rate change alarm (event) is triggered when 
                 the actual data rate is below the data rate at the last entry into showtime by more than the 
                 threshold. 
                 The data rate threshold is coded in bit/s.
                 Unit: bit/s.
                "
            DEFVAL { 0 }                
            ::= { hwVOPDataRateConfProfEntry 22 }                                      

        hwVOPLineSpectrumProfileIndexNext OBJECT-TYPE
            SYNTAX HWVOPProfileIndexOrZeroType
            MAX-ACCESS read-only
            STATUS current
            DESCRIPTION
                "This object contains an appropriate value to be used for hwVOPLineSpectrumConfProfIndex
                 when creating entries in the hwVOPLineSpectrumConfProfTable.
                 The value '0' indicates that no unassigned entries are available.

                 To obtain the value of hwVOPLineSpectrumConfProfIndex for a new entry in the table,
                 the manager issues a management protocol retrieval operation.
                 The agent will determine through its local policy
                 when this index value will be made available for reuse.
                "
            ::= { hwVOPProfiles 3 }


        hwVOPLineSpectrumConfProfTable OBJECT-TYPE
            SYNTAX SEQUENCE OF HWVOPLineSpectrumConfProfEntry
            MAX-ACCESS not-accessible
            STATUS current
            DESCRIPTION
                "The table hwVOPLineSpectrumConfProfTable contains the parameters that are mainly set
                 during the service delivery phase, independently for upstream and downstream.
                 Entries in this table MUST be maintained in a persistent manner.

                 A default profile with an index of '1' will always exist and its parameters will be set
                 to vendor-specific values, unless otherwise specified in this document.
                 The index of this table is hwVOPLineSpectrumConfProfIndex.
                "
            REFERENCE
                "Broadband Forum TR-252, paragraph #5.6"
            ::= { hwVOPProfiles 4 }


        hwVOPLineSpectrumConfProfEntry OBJECT-TYPE
            SYNTAX HWVOPLineSpectrumConfProfEntry
            MAX-ACCESS not-accessible
            STATUS current
            DESCRIPTION
                "The table hwVOPLineSpectrumConfProfTable contains the parameters that are mainly set
                 during the service delivery phase, independently for upstream and downstream.
                 Entries in this table MUST be maintained in a persistent manner.

                 A default profile with an index of '1' will always exist and its parameters will be set
                 to vendor-specific values, unless otherwise specified in this document.
                 The index of this entry is hwVOPLineSpectrumConfProfIndex.
                "
            INDEX { hwVOPLineSpectrumConfProfIndex }
            ::= { hwVOPLineSpectrumConfProfTable 1 }


        HWVOPLineSpectrumConfProfEntry ::=
            SEQUENCE {
                hwVOPLineSpectrumConfProfIndex                           Unsigned32,
                hwVOPLineSpectrumConfProfRowStatus                       RowStatus,
                hwVOPLineSpectrumConfProfDescription                     OCTET STRING,
                hwVOPLineSpectrumConfProfXtuTransSysEna                  Xdsl2TransmissionModeType,
                hwVOPLineSpectrumConfProfPmMode                          Xdsl2LinePmMode,
                hwVOPLineSpectrumConfProfL0Time                          Gauge32,
                hwVOPLineSpectrumConfProfL2Time                          Gauge32,
                hwVOPLineSpectrumConfProfL3Time                          Gauge32,
                hwVOPLineSpectrumConfProfL2Atpr                          Gauge32,
                hwVOPLineSpectrumConfProfL2Atprt                         Gauge32,
                hwVOPLineSpectrumConfProfReferenceClock                  Xdsl2LineClockReferenceType,
                hwVOPLineSpectrumConfProfBitSwapDs                       Xdsl2BitSwap,
                hwVOPLineSpectrumConfProfBitSwapUs                       Xdsl2BitSwap,
                hwVOPLineSpectrumConfProfScMaskDs                        Xdsl2ScMaskDs,
                hwVOPLineSpectrumConfProfScMaskUs                        Xdsl2ScMaskUs,
                hwVOPLineSpectrumConfProfVdsl2CarMask                    Xdsl2CarMask,
                hwVOPLineSpectrumConfProfMsgMinUs                        Gauge32,
                hwVOPLineSpectrumConfProfMsgMinDs                        Gauge32,
                hwVOPLineSpectrumConfProfProfiles                        Xdsl2LineProfiles,
                hwVOPLineSpectrumConfProfUs0Mask                         Xdsl2LineUs0Mask,
                hwVOPLineSpectrumConfProfCeFlag                          Xdsl2LineCeFlag,
                hwVOPLineSpectrumConfProfModeSpecificPSDProfilesUsed     OCTET STRING,
                hwVOPLineSpectrumConfProfForceInpDs                      TruthValue,
                hwVOPLineSpectrumConfProfForceInpUs                      TruthValue,
                hwVOPLineSpectrumConfProfRtxModeDs                       INTEGER,
                hwVOPLineSpectrumConfProfRtxModeUs                       INTEGER,
                hwVOPLineSpectrumConfProfLeftrThreshDs                   Gauge32,
                hwVOPLineSpectrumConfProfLeftrThreshUs                   Gauge32,
                hwVOPGfastLineSpectrumConfProfGfastProfiles              HWVOPGfastProfiles,
                hwVOPGfastLineSpectrumConfProfLowFreqEdgeValueDs         Gauge32,
                hwVOPGfastLineSpectrumConfProfGfastCarMaskDs             Xdsl2CarMask,
                hwVOPGfastLineSpectrumConfProfGfastCarMaskUs             Xdsl2CarMask,
                hwVOPGfastLineSpectrumConfProfGfastFallbackFreq          Gauge32,
                hwVOPGfastLineSpectrumConfProfLowFreqEdgeValueUs         Gauge32
            }


        hwVOPLineSpectrumConfProfIndex OBJECT-TYPE
            SYNTAX Unsigned32 (1..4294967295)
            MAX-ACCESS accessible-for-notify
            STATUS current
            DESCRIPTION
                "The hwVOPLineSpectrumConfProfIndex identifies a row in the hwVOPLineSpectrumConfProfTable."
            ::= { hwVOPLineSpectrumConfProfEntry 1 }


        hwVOPLineSpectrumConfProfRowStatus OBJECT-TYPE
            SYNTAX RowStatus
            MAX-ACCESS read-create
            STATUS current
            DESCRIPTION
                "The hwVOPLineSpectrumConfProfRowStatus is used to create a new row
                 or to modify or delete an existing row in this table.
                 A profile is activated by setting this object to 'active'.
                 Before a profile can be deleted or taken out of service (by setting this object
                 to 'destroy' or 'notInService'), it MUST be first unreferenced from all associated DSL lines.

                 A row in hwVOPLineSpectrumConfProfTable is said to be not referenced when there is no instance
                 of hwVOPActSetupLSpectrumProfId in the hwVOPActSetupTable which refers to the row.
                "
            ::= { hwVOPLineSpectrumConfProfEntry 2 }


        hwVOPLineSpectrumConfProfDescription OBJECT-TYPE
            SYNTAX OCTET STRING (SIZE (0..128))
            MAX-ACCESS read-create
            STATUS current
            DESCRIPTION
                "The hwVOPLineSpectrumConfProfDescription contains an optional human readable description for the profile."
            ::= { hwVOPLineSpectrumConfProfEntry 3 }


        hwVOPLineSpectrumConfProfXtuTransSysEna OBJECT-TYPE
            SYNTAX Xdsl2TransmissionModeType
            MAX-ACCESS read-create
            STATUS current
            DESCRIPTION
                "xTU Transmission System Enabling (XTSE).
                 A list of the different coding types enabled in this profile.
                 It is coded in a bit-map representation with 1 or more bits set.
                 A bit set to '1' means that the xTUs may apply the respective coding for the DSL line.
                 A bit set to '0' means that the xTUs cannot apply the respective coding for the xDSL line.
                 All 'reserved' bits should be set to '0'.
                "
            ::= { hwVOPLineSpectrumConfProfEntry 4 }


        hwVOPLineSpectrumConfProfPmMode OBJECT-TYPE
            SYNTAX Xdsl2LinePmMode
            MAX-ACCESS read-create
            STATUS current
            DESCRIPTION
                "Power management state Enabling (PMMode).
                 Defines the power states the xTU-C or xTU-R may autonomously transition to on this line.
                 This is a set of bits, where any bit with a '1' value means that the xTU is allowed
                 to transit into the respective state and any bit with a '0' value means
                 that the xTU is not allowed to transit into the respective state.
                "
            REFERENCE
                "ITU-T G.997.1, paragraph #7.3.1.1.4 (PMMode)"
            ::= { hwVOPLineSpectrumConfProfEntry 5 }


        hwVOPLineSpectrumConfProfL0Time OBJECT-TYPE
            SYNTAX Gauge32 (0..255)
            UNITS "seconds"
            MAX-ACCESS read-create
            STATUS current
            DESCRIPTION
                "The minimum time (in seconds) between an Exit from the L2 state
                 and the next Entry into the L2 state.
                 Unit: seconds.
                "
            REFERENCE
                "ITU-T G.997.1, paragraph #7.3.1.1.5 (L0-TIME)"
            DEFVAL { 255 }
            ::= { hwVOPLineSpectrumConfProfEntry 6 }


        hwVOPLineSpectrumConfProfL2Time OBJECT-TYPE
            SYNTAX Gauge32 (0..255)
            UNITS "seconds"
            MAX-ACCESS read-create
            STATUS current
            DESCRIPTION
                "The minimum time (in seconds) between an Entry into the L2 state
                 and the first Power Trim in the L2 state and between two consecutive Power Trims in the L2 State.
                 Unit: seconds
                "
            REFERENCE
                "ITU-T G.997.1, paragraph #7.3.1.1.6 (L2-TIME)"
            DEFVAL { 30 }
            ::= { hwVOPLineSpectrumConfProfEntry 7 }


        hwVOPLineSpectrumConfProfL3Time OBJECT-TYPE
            SYNTAX Gauge32 (0..65535)
            UNITS "seconds"
            MAX-ACCESS read-create
            STATUS current
            DESCRIPTION
                "This minimum time (in seconds) between an Entry into the L3 state and the L0 or L2 state.
                 Unit: seconds
                "
            DEFVAL { 255 }
            ::= { hwVOPLineSpectrumConfProfEntry 8 }


        hwVOPLineSpectrumConfProfL2Atpr OBJECT-TYPE
            SYNTAX Gauge32 (0..31)
            UNITS "dB"
            MAX-ACCESS read-create
            STATUS current
            DESCRIPTION
                "The maximum aggregate transmit power reduction (in dB) that can be performed at transition
                 of L0 to L2 state or through a single Power Trim in the L2 state.
                 Unit: dB.
                "
            REFERENCE
                "ITU-T G.997.1, paragraph #7.3.1.1.7 (L2-ATPR)"
            DEFVAL { 3 }
            ::= { hwVOPLineSpectrumConfProfEntry 9 }


        hwVOPLineSpectrumConfProfL2Atprt OBJECT-TYPE
            SYNTAX Gauge32 (0..31)
            UNITS "dB"
            MAX-ACCESS read-create
            STATUS current
            DESCRIPTION
                "The total maximum aggregate transmit power reduction (in dB)
                 that can be performed in an L2 state. This is the sum of all reductions
                 of L2 Request (i.e., at transition of L0 to L2 state) and Power Trims.
                 Unit: dB.
                "
            REFERENCE
                "ITU-T G.997.1, paragraph #7.3.1.1.9 (L2-ATPRT)"
            DEFVAL { 9 }
            ::= { hwVOPLineSpectrumConfProfEntry 10 }


        hwVOPLineSpectrumConfProfReferenceClock  OBJECT-TYPE
            SYNTAX      Xdsl2LineClockReferenceType
            MAX-ACCESS  read-create
            STATUS      current
            DESCRIPTION
                "This object configures the clock reference for the ATU-C in a VDSL Line."
            DEFVAL       { freeRun }
            ::= { hwVOPLineSpectrumConfProfEntry 11 }


        hwVOPLineSpectrumConfProfBitSwapDs  OBJECT-TYPE
            SYNTAX      Xdsl2BitSwap
            MAX-ACCESS  read-create
            STATUS      current
            DESCRIPTION
                "Enable or disable the bit swap downstream of a line."
            DEFVAL       { disable }
            ::= { hwVOPLineSpectrumConfProfEntry 12 }


        hwVOPLineSpectrumConfProfBitSwapUs  OBJECT-TYPE
            SYNTAX      Xdsl2BitSwap
            MAX-ACCESS  read-create
            STATUS      current
            DESCRIPTION
                "Enable or disable the bit swap upstream of a line."
            DEFVAL       { disable }
            ::= { hwVOPLineSpectrumConfProfEntry 13 }


        hwVOPLineSpectrumConfProfScMaskDs OBJECT-TYPE
            SYNTAX Xdsl2ScMaskDs
            MAX-ACCESS read-create
            STATUS current
            DESCRIPTION
                "Downstream subcarriers mask.
                 A bitmap of 512 bits that allows masking up to 512 downstream subcarriers.
                 If bit i (0 <= i < NSCds) is set to '1', the respective downstream subcarrier
                 is masked, and if set to '0', the respective subcarrier is unmasked.
                 Note that there should always be unmasked subcarriers (i.e.,this object cannot be all 1's).
                 Also note that if NSCds < 512, all bits i(NSCds < i <= 512) should be set to '1'.

                 NSCds is the highest subcarrier index that can be transmitted in the downstream direction.
                 For G.992.3, G.992.4, and G.992.5, it is defined in the corresponding Recommendations.
                 For G.992.1, NSCds = 256 and for G.992.2, NSCds = 128.
                "
            REFERENCE
                "ITU-T G.997.1, paragraph #7.3.1.2.6 (CARMASKds)"
            ::= { hwVOPLineSpectrumConfProfEntry 14 }


        hwVOPLineSpectrumConfProfScMaskUs OBJECT-TYPE
            SYNTAX Xdsl2ScMaskUs
            MAX-ACCESS read-create
            STATUS current
            DESCRIPTION
                "Upstream subcarriers mask.
                 A bitmap of 512 bits that allows masking up to 512 downstream subcarriers.
                 If bit i (0 <= i < NSCds) is set to '1', the respective downstream subcarrier
                 is masked, and if set to '0', the respective subcarrier is unmasked.
                 Note that there should always be unmasked subcarriers (i.e.,this object cannot be all 1's).
                 Also note that if NSCds < 512, all bits i(NSCds < i <= 512) should be set to '1'.

                 NSCus is the highest subcarrier index that can be transmitted in the upstream direction.
                 For G.992.3, G.992.4, and G.992.5, it is defined in the corresponding Recommendation.
                 For Annex A/G.992.1 and G.992.2, NSCus = 32 and for Annex B/G.992.1, NSCus = 64.
                "
            REFERENCE
                "ITU-T G.997.1, paragraph #7.3.1.2.7 (CARMASKus)"
            ::= { hwVOPLineSpectrumConfProfEntry 15 }


        hwVOPLineSpectrumConfProfVdsl2CarMask OBJECT-TYPE
            SYNTAX Xdsl2CarMask
            MAX-ACCESS read-create
            STATUS current
            DESCRIPTION
                "VDSL2 specific subcarriers mask.
                 This configuration parameter defines the restrictions, additional to the band plan, to determine
                 the set of subcarriers allowed for transmission in both upstream and downstream directions.
                 The parameter shall describe the not masked subcarriers as one or more frequency bands.
                 Each band is represented by start and stop subcarrier indices with a subcarrier spacing of 4.3125kHz.
                 The valid range of subcarrier indices runs from 0 to at least the index of the highest allowed
                 subcarrier in both transmission directions among all profiles enabled by the parameter
                 hwVOPLineSpectrumConfProfProfiles.
                 Up to 32 bands may be specified. Other subcarriers shall be masked.
                "
            REFERENCE
                "ITU-T G.997.1, paragraph #7.3.1.2.8 (VDSL2-CARMASK)"
            ::= { hwVOPLineSpectrumConfProfEntry 16 }


        hwVOPLineSpectrumConfProfMsgMinUs OBJECT-TYPE
            SYNTAX Gauge32 (4000..248000)
            UNITS "bits/second"
            MAX-ACCESS read-create
            STATUS current
            DESCRIPTION
                "Minimum Overhead Rate Upstream.
                 Defines the minimum rate of the message-based overhead
                 that shall be maintained by the xTU in upstream direction.
                 Expressed in bits per second and ranges from 4000 to 248000 bps.
                 Unit: bits/second.
                "
            REFERENCE
                "ITU-T G.997.1, paragraph #7.3.1.5.1 (MSGMINus)"
            DEFVAL { 4000 }
            ::= { hwVOPLineSpectrumConfProfEntry 17 }


        hwVOPLineSpectrumConfProfMsgMinDs OBJECT-TYPE
            SYNTAX Gauge32 (4000..248000)
            UNITS "bits/second"
            MAX-ACCESS read-create
            STATUS current
            DESCRIPTION
                "Minimum Overhead Rate Downstream.
                 Defines the minimum rate of the message-based overhead
                 that shall be maintained by the xTU in downstream direction.
                 Expressed in bits per second and ranges from 4000 to 248000 bps.
                 Unit: bits/second.
                "
            REFERENCE
                "ITU-T G.997.1, paragraph #7.3.1.5.2 (MSGMINds)"
            DEFVAL { 4000 }
            ::= { hwVOPLineSpectrumConfProfEntry 18 }


        hwVOPLineSpectrumConfProfProfiles OBJECT-TYPE
            SYNTAX Xdsl2LineProfiles
            MAX-ACCESS read-create
            STATUS current
            DESCRIPTION
                "The configuration parameter contains the G.993.2 profiles to
                 be allowed by the near-end xTU on this line.
                 It is coded in a bitmap representation (0 if not allowed, 1 if allowed).
                "
            REFERENCE
                "ITU-T G.997.1, paragraph #7.3.1.1.11 (PROFILES)"
            ::= { hwVOPLineSpectrumConfProfEntry 19 }


        hwVOPLineSpectrumConfProfUs0Mask OBJECT-TYPE
            SYNTAX Xdsl2LineUs0Mask
            MAX-ACCESS read-create
            STATUS current
            DESCRIPTION
                "The configuration parameter contains the US0 PSD masks to be allowed
                 by the near-end xTU on the line.
                 This parameter is only defined for G.993.2 Annex A.
                 It is represented as a  bitmap (0 if not allowed and 1 if allowed).
                "
            REFERENCE
                "ITU-T G.997.1 Amendment 1, paragraph #7.3.1.2.18 (US0MASK)"
            ::= { hwVOPLineSpectrumConfProfEntry 20 }


        hwVOPLineSpectrumConfProfCeFlag OBJECT-TYPE
            SYNTAX Xdsl2LineCeFlag
            MAX-ACCESS read-create
            STATUS current
            DESCRIPTION
                "This parameter is a bit that enables the use of the optional cyclic extension values."
            REFERENCE
                "ITU-T G.997.1, paragraph #7.3.1.6.1 (CEFLAG)"
            DEFVAL { 0 }
            ::= { hwVOPLineSpectrumConfProfEntry 21 }


        hwVOPLineSpectrumConfProfModeSpecificPSDProfilesUsed OBJECT-TYPE
            SYNTAX OCTET STRING (SIZE (512))
            MAX-ACCESS read-create
            STATUS current
            DESCRIPTION
                "The value of this object represents a pointer to one or more rows
                 in the hwVOPModeSpecificPSDConfProfTable. The number of pointers equals to the xDSL modes
                 enabled in hwVOPLineSpectrumConfProfXtuTransSysEna.
                 The following rule applies:
                 Every Octet addresses a xDSL mode (represented by one Bit in hwVOPLineSpectrumConfProfXtuTransSysEna).
                 The value identifies the specific profile in the hwVOPModeSpecificPSDConfProfTable
                 which applies for the specific mode.

                 The value '0' means that no profile applies because the respective mode is not enabled.
                 Each transmission mode enabled (hwVOPLineSpectrumConfProfXtuTransSysEna)
                 in the hwVOPLineSpectrumConfProfTable is covered by one and only one
                 of the Mode Specific PSD Profiles contained in that Line Spectrum Profile.
                "
            ::= { hwVOPLineSpectrumConfProfEntry 22 }


        hwVOPLineSpectrumConfProfForceInpDs OBJECT-TYPE
            SYNTAX TruthValue
            MAX-ACCESS read-create
            STATUS current
            DESCRIPTION
                "If retransmission is not used in a given transmit direction,this parameter indicates that the framer settings 
                 of the downstream bearer shall be selected such that the impulse noise protection computed according to the 
                 formula specified in the relevant Recommendation is greater than or equal to the minimal impulse noise protection 
                 requirement.
                 This flag shall have the same value for all the bearers of one line in the same direction.
                "
            REFERENCE
                "ITU-T G.997.1, paragraph #7.3.2.5 (FORCEINP)"
            DEFVAL { false }
            ::= { hwVOPLineSpectrumConfProfEntry 23 }


        hwVOPLineSpectrumConfProfForceInpUs OBJECT-TYPE
            SYNTAX TruthValue
            MAX-ACCESS read-create
            STATUS current
            DESCRIPTION
                "If retransmission is not used in a given transmit direction,this parameter indicates that the framer settings 
                 of the upstream bearer shall be selected such that the impulse noise protection computed according to the 
                 formula specified in the relevant Recommendation is greater than or equal to the minimal impulse noise protection 
                 requirement.
                 This flag shall have the same value for all the bearers of one line in the same direction.
                "
            REFERENCE
                "ITU-T G.997.1, paragraph #7.3.2.5 (FORCEINP)"
            DEFVAL { false }
            ::= { hwVOPLineSpectrumConfProfEntry 24 }
            
        hwVOPLineSpectrumConfProfRtxModeDs  OBJECT-TYPE
            SYNTAX      INTEGER
                        {
                         forbidden(0),
                         preferred(1),
                         forced(2),
                         testmode(3)
                        }            
            MAX-ACCESS  read-create
            STATUS      current
            DESCRIPTION
                "The mode of operation of G.998.4 retransmission in downstream direction. 
                 Options:          
                 1. forbidden (0)    - G.998.4 retransmission not allowed.
                 2. preferred (1)    - G.998.4 retransmission is preferred.
                 3. forced    (2)    - Force the use of the G.998.4 retransmission.               
                 4. testmode  (3)    - Force the use of the G.998.4 retransmission in test mode.
                "
            REFERENCE    "ITU-T G.997.1, paragraph 7.3.1.11"
            DEFVAL       { forbidden }
            ::= { hwVOPLineSpectrumConfProfEntry 25 }
            
        hwVOPLineSpectrumConfProfRtxModeUs  OBJECT-TYPE
            SYNTAX      INTEGER
                        {
                         forbidden(0),
                         preferred(1),
                         forced(2),
                         testmode(3)
                        }            
            MAX-ACCESS  read-create
            STATUS      current
            DESCRIPTION
                "The mode of operation of G.998.4 retransmission in upstream direction. 
                 Options:          
                 1. forbidden (0)    - G.998.4 retransmission not allowed.
                 2. preferred (1)    - G.998.4 retransmission is preferred.
                 3. forced    (2)    - Force the use of the G.998.4 retransmission.               
                 4. testmode  (3)    - Force the use of the G.998.4 retransmission in test mode.
                "
            REFERENCE    "ITU-T G.997.1, paragraph 7.3.1.11"
            DEFVAL       { forbidden }
            ::= { hwVOPLineSpectrumConfProfEntry 26 }            

        hwVOPLineSpectrumConfProfLeftrThreshDs  OBJECT-TYPE
            SYNTAX      Gauge32(0..99)
            UNITS       "0.01"
            MAX-ACCESS  read-create
            STATUS      current
            DESCRIPTION
                "If retransmission is used in downstream direction, this parameter specifies the 
                 threshold for declaring a near-end leftr defect. The value is coded as a fraction of the 
                 NDR with valid range from 0.01 to 0.99 with increments of 0.01. A special value means the
                 ETR shall be used as the default threshold for declaring a leftr defect.
                "
            REFERENCE    "ITU-T G.997.1, paragraph 7.3.1.12"
            DEFVAL       { 0 }
            ::= { hwVOPLineSpectrumConfProfEntry 27 }
            
        hwVOPLineSpectrumConfProfLeftrThreshUs  OBJECT-TYPE
            SYNTAX      Gauge32(0..99)
            UNITS       "0.01"
            MAX-ACCESS  read-create
            STATUS      current
            DESCRIPTION
                "If retransmission is used in upstream direction, this parameter specifies the 
                 threshold for declaring a near-end leftr defect. The value is coded as a fraction of the 
                 NDR with valid range from 0.01 to 0.99 with increments of 0.01. A special value means the
                 ETR shall be used as the default threshold for declaring a leftr defect.
                "
            REFERENCE    "ITU-T G.997.1, paragraph 7.3.1.12"
            DEFVAL       { 0 }
            ::= { hwVOPLineSpectrumConfProfEntry 28 }
            
        hwVOPGfastLineSpectrumConfProfGfastProfiles OBJECT-TYPE
            SYNTAX HWVOPGfastProfiles
            MAX-ACCESS read-create
            STATUS current
            DESCRIPTION
                "The configuration parameter contains the G.fast profiles to
                 be allowed by the near-end xTU on this line.
                 It is coded in a bitmap representation (0 if not allowed, 1 if allowed).
                 Bit representation:
                 0  G.fast profile 106
                 1  G.fast profile 212
                 Default value: All profiles allowed.
                "
            REFERENCE
                "ITU-T G.9701, paragraph 6"
            ::= { hwVOPLineSpectrumConfProfEntry 29 }
            
        hwVOPGfastLineSpectrumConfProfLowFreqEdgeValueDs OBJECT-TYPE
            SYNTAX Gauge32 (43..1023)
            MAX-ACCESS read-create
            STATUS current
            DESCRIPTION
                "Low-frequency Edge Stop-band Mask(LESM).
                 If a LESM is used, the LESM shall be specified with breakpoints.
                 These breakpoints are specified starting from ftr1, which is the start of the in-band PSD mask, as specified in [ITU-T G.9700]. 
                 This is not to be confused with ftr3,  which is the start of the in-band part of the LESM.
                "
            REFERENCE
                "ITU-T G.9701, paragraph 7.3.1.1.1"
            DEFVAL { 43 }
            ::= { hwVOPLineSpectrumConfProfEntry 30 }
	       
        hwVOPGfastLineSpectrumConfProfGfastCarMaskDs OBJECT-TYPE
            SYNTAX Xdsl2CarMask
            MAX-ACCESS read-create
            STATUS current
            DESCRIPTION
                "G.fast specific subcarriers mask.
                 This configuration parameter defines the restrictions, additional to the band plan, to determine
                 the set of subcarriers allowed for transmission in downstream directions.
                 The parameter shall describe the not masked subcarriers as one or more frequency bands.
                 Each band is represented by start and stop subcarrier indices with a subcarrier spacing of 51.75kHz.
                 The valid range of subcarrier indices runs from 0 to at least the index of the highest allowed
                 subcarrier in both transmission directions.
                 Up to 32 bands may be specified. Other subcarriers shall be masked.
                "
            REFERENCE
                "ITU-T G.9701, paragraph 7.3.1.3"
            ::= { hwVOPLineSpectrumConfProfEntry 31 }
            
        hwVOPGfastLineSpectrumConfProfGfastCarMaskUs OBJECT-TYPE
            SYNTAX Xdsl2CarMask
            MAX-ACCESS read-create
            STATUS current
            DESCRIPTION
                "G.fast specific subcarriers mask.
                 This configuration parameter defines the restrictions, additional to the band plan, to determine
                 the set of subcarriers allowed for transmission in upstream directions.
                 The parameter shall describe the not masked subcarriers as one or more frequency bands.
                 Each band is represented by start and stop subcarrier indices with a subcarrier spacing of 51.75kHz.
                 The valid range of subcarrier indices runs from 0 to at least the index of the highest allowed
                 subcarrier in both transmission directions.
                 Up to 32 bands may be specified. Other subcarriers shall be masked.
                "
            REFERENCE
                "ITU-T G.9701, paragraph 7.3.1.3"
            ::= { hwVOPLineSpectrumConfProfEntry 32 }
            
        hwVOPGfastLineSpectrumConfProfGfastFallbackFreq OBJECT-TYPE
            SYNTAX Gauge32 (43..2047)
            MAX-ACCESS read-create
            STATUS current
            DESCRIPTION
                "G.fast fallback to G.993.2 profile frequency.
                "
            DEFVAL { 43 }
            ::= { hwVOPLineSpectrumConfProfEntry 33 }                                                
            
        hwVOPGfastLineSpectrumConfProfLowFreqEdgeValueUs OBJECT-TYPE
            SYNTAX Gauge32 (43..1023)
            MAX-ACCESS read-create
            STATUS current
            DESCRIPTION
                "Low-frequency Edge Stop-band Mask(LESM).
                 If a LESM is used, the LESM shall be specified with breakpoints.
                 These breakpoints are specified starting from ftr1, which is the start of the in-band PSD mask, as specified in [ITU-T G.9700]. 
                 This is not to be confused with ftr3,  which is the start of the in-band part of the LESM.
                "
            REFERENCE
                "ITU-T G.9701, paragraph 7.3.1.1.1"
            DEFVAL { 43 }
            ::= { hwVOPLineSpectrumConfProfEntry 34 }
	       
        hwVOPModeSpecificPSDProfileIndexNext OBJECT-TYPE
            SYNTAX HWVOPProfileIndexOrZeroType
            MAX-ACCESS read-only
            STATUS current
            DESCRIPTION
                "This object contains an appropriate value to be used for hwVOPModeSpecificPSDConfProfIndex
                 when creating entries in the hwVOPModeSpecificPSDConfProfTable.
                 The value '0' indicates that no unassigned entries are available.
                 To obtain the value of hwVOPModeSpecificPSDConfProfIndex for a new entry in the table,
                 the manager issues a management protocol retrieval operation.
                 The agent will determine through its local policy when this index value will be made available for reuse.
                "
            ::= { hwVOPProfiles 5 }


        hwVOPModeSpecificPSDConfProfTable OBJECT-TYPE
            SYNTAX SEQUENCE OF HWVOPModeSpecificPSDConfProfEntry
            MAX-ACCESS not-accessible
            STATUS current
            DESCRIPTION
                "The table hwVOPModeSpecificPSDConfProfTable contains the parameters that define the downstream
                 and upstream PSDs for a specific xDSL mode.
                 Entries in this table MUST be maintained in a persistent manner.
                 A default profile with an index of '1' will always exist and its parameters will be set to
                 vendor-specific values, unless otherwise specified in this document.
                 The index of this table is hwVOPModeSpecificPSDConfProfIndex.
                "
            REFERENCE
                "Broadband Forum TR-252, paragraph #5.6"
            ::= { hwVOPProfiles 6 }


        hwVOPModeSpecificPSDConfProfEntry OBJECT-TYPE
            SYNTAX HWVOPModeSpecificPSDConfProfEntry
            MAX-ACCESS not-accessible
            STATUS current
            DESCRIPTION
                "The table hwVOPModeSpecificPSDConfProfTable contains the parameters that define the downstream
                 and upstream PSDs for a specific xDSL mode.
                 Entries in this table MUST be maintained in a persistent manner.
                 A default profile with an index of '1' will always exist and its parameters will be set to
                 vendor-specific values, unless otherwise specified in this document.
                 The index of this entry is hwVOPModeSpecificPSDConfProfIndex.
                "
            REFERENCE
                "Broadband Forum TR-252, paragraph #5.6"
            INDEX { hwVOPModeSpecificPSDConfProfIndex }
            ::= { hwVOPModeSpecificPSDConfProfTable 1 }


        HWVOPModeSpecificPSDConfProfEntry ::=
            SEQUENCE {
                hwVOPModeSpecificPSDConfProfIndex                       Unsigned32,
                hwVOPModeSpecificPSDConfProfRowStatus                   RowStatus,
                hwVOPModeSpecificPSDConfProfDescription                 OCTET STRING,
                hwVOPModeSpecificPSDConfProfXdslMode                    Xdsl2TransmissionModeType,      -- deprecated
                hwVOPModeSpecificPSDConfProfMaxNomPsdDs                 Integer32,
                hwVOPModeSpecificPSDConfProfMaxNomPsdUs                 Integer32,
                hwVOPModeSpecificPSDConfProfMaxNomAtpDs                 Gauge32,
                hwVOPModeSpecificPSDConfProfMaxNomAtpUs                 Gauge32,
                hwVOPModeSpecificPSDConfProfaxAggRxPwrUs                Integer32,
                hwVOPModeSpecificPSDConfProfPsdMaskDs                   Xdsl2PsdMaskDs,
                hwVOPModeSpecificPSDConfProfPsdMaskUs                   Xdsl2PsdMaskUs,
                hwVOPModeSpecificPSDConfProfPsdMaskSelectUs             Xdsl2LinePsdMaskSelectUs,
                hwVOPModeSpecificPSDConfProfLimitMask                   Xdsl2LineLimitMask,
                hwVOPModeSpecificPSDConfProfUs0Disable                  Xdsl2LineUs0Disable,
                hwVOPModeSpecificPSDConfProfClassMask                   Xdsl2LineClassMask,
                hwVOPGfastModeSpecificPSDConfProfPsdMaskDs              HWVOPGfastPsdMask,
                hwVOPGfastModeSpecificPSDConfProfPsdMaskUs              HWVOPGfastPsdMask,
                hwVOPGfastModeSpecificPSDConfProfMaxNomAtpDs            Gauge32,
                hwVOPGfastModeSpecificPSDConfProfMaxNomAtpUs            Gauge32
             }


        hwVOPModeSpecificPSDConfProfIndex OBJECT-TYPE
            SYNTAX Unsigned32 (1..4294967295)
            MAX-ACCESS not-accessible
            STATUS current
            DESCRIPTION
                "The hwVOPModeSpecificPSDConfProfIndex identifies a row in the hwVOPModeSpecificPSDConfProfTable."
            ::= { hwVOPModeSpecificPSDConfProfEntry 1 }


        hwVOPModeSpecificPSDConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy' or
                 'notInService'), it MUST be first unreferenced from all associated DSL lines.
                 A row in hwVOPModeSpecificPSDConfProfTable is said to be unreferenced when there is no instance of
                 hwVOPLineSpectrumConfProfModeSpecificPSDProfilesUsed in the hwVOPLineSpectrumConfProfTable
                 which refers to the row.
                "
            ::= { hwVOPModeSpecificPSDConfProfEntry 2 }


        hwVOPModeSpecificPSDConfProfDescription OBJECT-TYPE
            SYNTAX OCTET STRING (SIZE (0..128))
            MAX-ACCESS read-create
            STATUS current
            DESCRIPTION
                "The hwVOPModeSpecificPSDConfProfDescription contains an optional human readable description for the profile."
            ::= { hwVOPModeSpecificPSDConfProfEntry 3 }


        hwVOPModeSpecificPSDConfProfXdslMode OBJECT-TYPE
            SYNTAX Xdsl2TransmissionModeType
            MAX-ACCESS read-create
            STATUS deprecated
            DESCRIPTION
                "A list of the different xDSL modes enabled in this profile.
                 It is coded in a bit-map representation with 1 or more bits set.
                 A bit set to '1' means that the profile applies to the respective xDSL Mode.
                 A bit set to '0' means that the profile does not apply to the respective xDSL Mode.
                 All 'reserved' bits should be set to '0'.
                 
                 This object is deprecated in favour of hwVOPLineSpectrumConfProfXtuTransSysEna.
                "
            ::= { hwVOPModeSpecificPSDConfProfEntry 4 }


        hwVOPModeSpecificPSDConfProfMaxNomPsdDs OBJECT-TYPE
            SYNTAX Integer32 (-600..-300)
            UNITS "0.1 dBm/Hz"
            MAX-ACCESS read-create
            STATUS current
            DESCRIPTION
                "The maximum nominal transmit PSD in the downstream direction during initialization and Showtime.
                 It ranges from -600 to -300 units of 0.1 dBm/Hz (physical values are -60 to -30 dBm/Hz).
                 Unit: 0.1 dBm/Hz.
                "
            REFERENCE
                "ITU-T G.997.1, paragraph #7.3.1.2.1 (MAXNOMPSDds)"
            DEFVAL { -400 }
            ::= { hwVOPModeSpecificPSDConfProfEntry 5 }


        hwVOPModeSpecificPSDConfProfMaxNomPsdUs OBJECT-TYPE
            SYNTAX Integer32 (-600..-300)
            UNITS "0.1 dBm/Hz"
            MAX-ACCESS read-create
            STATUS current
            DESCRIPTION
                "The maximum nominal transmit PSD in the upstream direction during initialization and Showtime.
                 It ranges from -600 to -300 units of 0.1 dBm/Hz (physical values are -60 to -30 dBm/Hz).
                 Unit: 0.1 dBm/Hz.
                "
            REFERENCE
                "ITU-T G.997.1, paragraph #7.3.1.2.2 (MAXNOMPSDus)"
            DEFVAL { -380 }
            ::= { hwVOPModeSpecificPSDConfProfEntry 6 }


        hwVOPModeSpecificPSDConfProfMaxNomAtpDs OBJECT-TYPE
            SYNTAX Gauge32 (0..510)
            UNITS "0.1 dBm"
            MAX-ACCESS read-create
            STATUS current
            DESCRIPTION
                "The maximum nominal aggregate transmit power in the downstream direction during initialization and Showtime.
                 It ranges from 0 to 510 units of 0.1 dBm (0 to 255 physical values are 0 to 25.5 dBm, 256 to 510 physical values are -25.5 to -0.1 dBm).
                 Unit: 0.1 dBm.
                "
            REFERENCE
                "ITU-T G.997.1, paragraph #7.3.1.2.3 (MAXNOMATPds)"
            DEFVAL { 200 }
            ::= { hwVOPModeSpecificPSDConfProfEntry 7 }


        hwVOPModeSpecificPSDConfProfMaxNomAtpUs OBJECT-TYPE
            SYNTAX Gauge32 (0..510)
            UNITS "0.1 dBm"
            MAX-ACCESS read-create
            STATUS current
            DESCRIPTION
                "The maximum nominal aggregate transmit power in the upstream direction during initialization and Showtime.
                 It ranges from 0 to 510 units of 0.1 dBm (0 to 255 physical values are 0 to 25.5 dBm, 256 to 510 physical values are -25.5 to -0.1 dBm).
                 Unit: 0.1 dBm.
                "
            REFERENCE
                "ITU-T G.997.1, paragraph #7.3.1.2.4 (MAXNOMATPus)"
            DEFVAL { 125 }
            ::= { hwVOPModeSpecificPSDConfProfEntry 8 }


        hwVOPModeSpecificPSDConfProfaxAggRxPwrUs OBJECT-TYPE
            SYNTAX Integer32 (-255..255 | 2147483647)
            UNITS "0.1 dBm"
            MAX-ACCESS read-create
            STATUS current
            DESCRIPTION
                "The maximum upstream aggregate receive power over the relevant set of subcarriers.
                 The xTU-C should verify that the upstream power cutback is such that this maximum
                 aggregate receive power value is honored.
                 It ranges from -255 to 255 units of 0.1 dBm (physical values are -25.5 to 25.5 dBm).
                 A value of 0x7FFFFFFF (2147483647) means that there is no limit.
                 Unit: 0.1 dBm.
                "
            REFERENCE
                "ITU-T G.997.1, paragraph #7.3.1.2.5 (MAXRXPWRus)"
            DEFVAL { 125 }
            ::= { hwVOPModeSpecificPSDConfProfEntry 9 }


        hwVOPModeSpecificPSDConfProfPsdMaskDs OBJECT-TYPE
            SYNTAX Xdsl2PsdMaskDs
            MAX-ACCESS read-create
            STATUS current
            DESCRIPTION
                "The downstream PSD mask applicable at the U-R2 reference point.
                 This parameter may impose PSD restrictions (breakpoints) in addition to the Limit PSD mask
                 defined in the relevant Recommendation (e.g., ITU-T Recs G.992.5 and G.993.2).
                 This is a string of 32 pairs of values in the following structure:
                 Octets 0-1 - Index of 1st subcarrier used in the context of a first breakpoint.
                 Octet 2    - The PSD reduction for the subcarrier indicated in octets 0 and 1.
                 Octets 3-5 - Same, for a 2nd breakpoint.
                 Octets 6-8 - Same, for a 3rd breakpoint.
                 This architecture continues until octets 94-95, which are associated with a 32nd breakpoint.
                 Each subcarrier index is an unsigned number in the range 0 and NSCds-1.
                 Each PSD reduction value is in the range 0 (0dBm/Hz) to 255 (-127.5dBm/Hz) with steps of 0.5dBm/Hz.
                 Valid values are in the range 0 to 190 (0 to -95dBm/Hz).
                 When the number of breakpoints is less than 32, all remaining octets are set to the value 0.
                 Note that the content of this object should be correlated with the subcarriers mask and with the RFI setup.
                "
            REFERENCE
                "ITU-T G.997.1, paragraph #7.3.1.2.9 (PSDMASKds)"
            ::= { hwVOPModeSpecificPSDConfProfEntry 10 }


        hwVOPModeSpecificPSDConfProfPsdMaskUs OBJECT-TYPE
            SYNTAX Xdsl2PsdMaskUs
            MAX-ACCESS read-create
            STATUS current
            DESCRIPTION
                "The upstream PSD mask applicable at the U-R2 reference point.
                 This parameter may impose PSD restrictions (breakpoints) in addition to the Limit PSD mask
                 defined in the relevant Recommendation (e.g., ITU-T Recs G.992.5 and G.993.2).
                 This is a string of 16 pairs of values in the following structure:
                 Octets 0-1 - Index of 1st subcarrier used in the context of a first breakpoint.
                 Octet 2    - The PSD reduction for the subcarrier indicated in octets 0 and 1.
                 Octets 3-5 - Same, for a 2nd breakpoint.
                 Octets 6-8 - Same, for a 3rd breakpoint.
                 This architecture continues until octets 9-47, which are associated with a 16th breakpoint.
                 Each subcarrier index is an unsigned number in the range 0 and NSCus-1.
                 Each PSD reduction value is in the range 0 (0dBm/Hz) to 255 (-127.5dBm/Hz) with steps of 0.5dBm/Hz.
                 Valid values are in the range 0 to 190 (0 to -95dBm/Hz).
                 When the number of breakpoints is less than 16, all remaining octets are set to the value 0.
                 Note that the content of this object should be correlated with the subcarriers mask and with the RFI setup.
                "
            REFERENCE
                "ITU-T G.997.1, paragraph #7.3.1.2.12 (PSDMASKus)"
            ::= { hwVOPModeSpecificPSDConfProfEntry 11 }


        hwVOPModeSpecificPSDConfProfPsdMaskSelectUs OBJECT-TYPE
            SYNTAX Xdsl2LinePsdMaskSelectUs
            MAX-ACCESS read-create
            STATUS current
            DESCRIPTION
                "The selected upstream PSD mask.
                 This parameter is used only for Annexes J and M of G.992.3 and G.992.5, and the same
                 selection is used for all relevant enabled bits in hwVOPLineSpectrumConfProfXtuTransSysEna.
                "
            REFERENCE
                "ITU-T G.997.1, paragraph #7.3.1.2.11 (Upstream PSD mask selection)"
            DEFVAL { adlu32Eu32 }
            ::= { hwVOPModeSpecificPSDConfProfEntry 12 }


        hwVOPModeSpecificPSDConfProfLimitMask OBJECT-TYPE
            SYNTAX Xdsl2LineLimitMask
            MAX-ACCESS read-create
            STATUS current
            DESCRIPTION
                "This configuration parameter contains the G.993.2 limit PSD masks of the selected PSD mask class,
                 enabled by the near-end xTU on this line for each class of profiles.
                 This parameter is defined per VDSL2 Annex enabled in the xdsl2LConfProfXtuTransSysEna object.
                 Through this parameter, several limit PSD masks of the selected PSD mask class
                 (hwVOPModeSpecificPSDConfProfClassMask) may be enabled.
                 The enabling parameter is coded in a bitmap representation
                 (0 if the associated mask is not allowed, 1 if it is allowed).
                "
            REFERENCE
                "ITU-T G.997.1 Amendment 1, paragraph #7.3.1.2.16 (LIMITMASK)"
            ::= { hwVOPModeSpecificPSDConfProfEntry 13 }


        hwVOPModeSpecificPSDConfProfUs0Disable OBJECT-TYPE
            SYNTAX Xdsl2LineUs0Disable
            MAX-ACCESS read-create
            STATUS current
            DESCRIPTION
                "This configuration parameter indicates if the use of US0 is disabled for each limit PSD
                 mask enabled in the hwVOPModeSpecificPSDConfProfLimitMask parameter.
                 This parameter is defined per VDSL2 Annex enabled in the hwVOPLineSpectrumConfProfXtuTransSysEna object.
                 For each limit PSD mask enabled in hwVOPModeSpecificPSDConfProfLimitMask parameter,
                 a bit shall indicate if US0 is disabled.
                 The disabling parameter is coded as a bitmap. The bit is set to 1 if US0 is disabled
                 for the associated limit mask.
                 This parameter and the hwVOPModeSpecificPSDConfProfLimitMask parameter use the same structure.
                "
            REFERENCE
                "ITU-T G.997.1, paragraph #7.3.1.2.17 (US0DISABLE)"
            ::= { hwVOPModeSpecificPSDConfProfEntry 14 }


        hwVOPModeSpecificPSDConfProfClassMask OBJECT-TYPE
            SYNTAX Xdsl2LineClassMask
            MAX-ACCESS read-create
            STATUS current
            DESCRIPTION
                "In order to reduce the number of configuration possibilities, the limit Power Spectral Density
                 masks (see hwVOPModeSpecificPSDConfProfLimitMask) are grouped in PSD mask classes.
                 Each class is designed such that the PSD levels of each limit PSD mask of a specific
                 class are equal in their respective passband above 552 kHz.
                 This parameter is defined per VDSL2 Annex enabled in the hwVOPLineSpectrumConfProfXtuTransSysEna object.
                 It selects a single PSD mask class per Annex that is activated at the VTU-O.
                "
            REFERENCE
                "ITU-T G.997.1 Amendment 1, paragraph #7.3.1.2.15 (CLASSMASK)"
            DEFVAL { b998M2x  }
            ::= { hwVOPModeSpecificPSDConfProfEntry 15 }
            
        hwVOPGfastModeSpecificPSDConfProfPsdMaskDs OBJECT-TYPE
            SYNTAX HWVOPGfastPsdMask
            MAX-ACCESS read-create
            STATUS current
            DESCRIPTION
                "The downstream PSD mask applicable at the U-O2 reference point.
                 This parameter may impose PSD restrictions (breakpoints) in addition to the Limit PSD mask
                 defined in the relevant Recommendation (e.g., ITU-T Recs G.9701).
                 This is a string of 32 pairs of values in the following structure:
                 Octets 0-1 - Index of 1st subcarrier used in the context of a first breakpoint.
                 Octet 2    - The PSD reduction for the subcarrier indicated in octets 0 and 1.
                 Octets 3-5 - Same, for a 2nd breakpoint.
                 Octets 6-8 - Same, for a 3rd breakpoint.
                 This architecture continues until octets 94-95, which are associated with a 32nd breakpoint.
                 Each subcarrier index is an unsigned number in the range 0 and NSCds-1.
                 Each PSD reduction value is in the range 0 (0dBm/Hz) to 255 (-127.5dBm/Hz) with steps of 0.5dBm/Hz.
                 Valid values are in the range 0 to 190 (0 to -95dBm/Hz).
                 When the number of breakpoints is less than 32, all remaining octets are set to the value 0.
                 Note that the content of this object should be correlated with the subcarriers mask and with the RFI setup.
                "
            REFERENCE
                "ITU-T G.9701, paragraph #7.3.1.1"
            ::= { hwVOPModeSpecificPSDConfProfEntry 16 }


        hwVOPGfastModeSpecificPSDConfProfPsdMaskUs OBJECT-TYPE
            SYNTAX HWVOPGfastPsdMask
            MAX-ACCESS read-create
            STATUS current
            DESCRIPTION
                "The upstream PSD mask applicable at the U-R2 reference point.
                 This parameter may impose PSD restrictions (breakpoints) in addition to the Limit PSD mask
                 defined in the relevant Recommendation (e.g., ITU-T Recs G.9701).
                 This is a string of 16 pairs of values in the following structure:
                 Octets 0-1 - Index of 1st subcarrier used in the context of a first breakpoint.
                 Octet 2    - The PSD reduction for the subcarrier indicated in octets 0 and 1.
                 Octets 3-5 - Same, for a 2nd breakpoint.
                 Octets 6-8 - Same, for a 3rd breakpoint.
                 This architecture continues until octets 9-47, which are associated with a 16th breakpoint.
                 Each subcarrier index is an unsigned number in the range 0 and NSCus-1.
                 Each PSD reduction value is in the range 0 (0dBm/Hz) to 255 (-127.5dBm/Hz) with steps of 0.5dBm/Hz.
                 Valid values are in the range 0 to 190 (0 to -95dBm/Hz).
                 When the number of breakpoints is less than 16, all remaining octets are set to the value 0.
                 Note that the content of this object should be correlated with the subcarriers mask and with the RFI setup.
                "
            REFERENCE
               "ITU-T G.9701, paragraph #7.3.1.1"
            ::= { hwVOPModeSpecificPSDConfProfEntry 17 }
            
        hwVOPGfastModeSpecificPSDConfProfMaxNomAtpDs OBJECT-TYPE
            SYNTAX Gauge32 (0..510)
            UNITS "0.1 dBm"
            MAX-ACCESS read-create
            STATUS current
            DESCRIPTION
                "The G.fast maximum nominal aggregate transmit power in the downstream direction during initialization and Showtime.
                 It ranges from 0 to 510 units of 0.1 dBm (0 to 255 physical values are 0 to 25.5 dBm, 256 to 510 physical values are -25.5 to -0.1 dBm).
                 Unit: 0.1 dBm.
                "
            DEFVAL { 40 }
            ::= { hwVOPModeSpecificPSDConfProfEntry 18 }


        hwVOPGfastModeSpecificPSDConfProfMaxNomAtpUs OBJECT-TYPE
            SYNTAX Gauge32 (0..510)
            UNITS "0.1 dBm"
            MAX-ACCESS read-create
            STATUS current
            DESCRIPTION
                "The G.fast maximum nominal aggregate transmit power in the upstream direction during initialization and Showtime.
                 It ranges from 0 to 510 units of 0.1 dBm (0 to 255 physical values are 0 to 25.5 dBm, 256 to 510 physical values are -25.5 to -0.1 dBm).
                 Unit: 0.1 dBm.
                "
            DEFVAL { 40 }
            ::= { hwVOPModeSpecificPSDConfProfEntry 19 }                        


        hwVOPUPBOProfileIndexNext OBJECT-TYPE
            SYNTAX HWVOPProfileIndexOrZeroType
            MAX-ACCESS read-only
            STATUS current
            DESCRIPTION
                "This object contains an appropriate value to be used for hwVOPUPBOConfProfIndex
                 when creating entries in the hwVOPUPBOConfProfTable.
                 The value '0' indicates that no unassigned entries are available.
                 To obtain the value of hwVOPUPBOConfProfIndex for a new entry in the table,
                 the manager issues a management protocol retrieval operation.
                 The agent will determine through its local policy when this index value will be made available for reuse.
                "
            ::= { hwVOPProfiles 7 }


        hwVOPUPBOConfProfTable OBJECT-TYPE
            SYNTAX SEQUENCE OF HWVOPUPBOConfProfEntry
            MAX-ACCESS not-accessible
            STATUS current
            DESCRIPTION
                "The table hwVOPUPBOConfProfTable contains all the parameters related to upstream power back-off.
                 Entries in this table MUST be maintained in a persistent manner.
                 A default profile with an index of '1' will always exist and its parameters will be
                 set to vendor-specific values, unless otherwise specified in this document.
                 The index of this table is hwVOPUPBOConfProfIndex.
                "
            REFERENCE
                "Broadband Forum TR-252, paragraph #5.6"
            ::= { hwVOPProfiles 8 }
-- The UPBO Profile contains all the parameters related to upstream power back-off.

        hwVOPUPBOConfProfEntry OBJECT-TYPE
            SYNTAX HWVOPUPBOConfProfEntry
            MAX-ACCESS not-accessible
            STATUS current
            DESCRIPTION
                "The table hwVOPUPBOConfProfTable contains all the parameters related to upstream power back-off.
                 Entries in this table MUST be maintained in a persistent manner.
                 A default profile with an index of '1' will always exist and its parameters will be
                 set to vendor-specific values, unless otherwise specified in this document.
                 The index of this entry is hwVOPUPBOConfProfIndex.
                "
            INDEX { hwVOPUPBOConfProfIndex }
            ::= { hwVOPUPBOConfProfTable 1 }


        HWVOPUPBOConfProfEntry ::=
            SEQUENCE {
                hwVOPUPBOConfProfIndex                           Unsigned32,
                hwVOPUPBOConfProfRowStatus                       RowStatus,
                hwVOPUPBOConfProfDescription                     OCTET STRING,
                hwVOPUPBOConfProfUpboKL                          Gauge32,
                hwVOPUPBOConfProfUpboKLF                         Xdsl2UpboKLF,
                hwVOPUPBOConfProfKlAuto                          Unsigned32,
                hwVOPUPBOConfProfPsdAUs1                         Integer32,
                hwVOPUPBOConfProfPsdBUs1                         Integer32,
                hwVOPUPBOConfProfPsdAUs2                         Integer32,
                hwVOPUPBOConfProfPsdBUs2                         Integer32,
                hwVOPUPBOConfProfPsdAUs3                         Integer32,
                hwVOPUPBOConfProfPsdBUs3                         Integer32,
                hwVOPUPBOConfProfPsdAUs4                         Integer32,
                hwVOPUPBOConfProfPsdBUs4                         Integer32,
                hwVOPUPBOConfProfBoostMode                       Xdsl2UpboBoostMode,
                hwVOPUPBOConfProfUpboKLREFUs1                    Integer32,
                hwVOPUPBOConfProfUpboKLREFUs2                    Integer32,
                hwVOPUPBOConfProfUpboKLREFUs3                    Integer32,
                hwVOPUPBOConfProfUpboKLREFUs4                    Integer32,
                hwVOPUPBOConfProfAeleMode                        Unsigned32,
                hwVOPUPBOConfProfUpboElmt                        Unsigned32,
                hwVOPGfastUPBOConfProfUpboKL                     Gauge32,
                hwVOPGfastUPBOConfProfUpboKLF                    Xdsl2UpboKLF,
                hwVOPGfastUPBOConfProfKlAuto                     Unsigned32,
                hwVOPGfastUPBOConfProfUpboKLREF                  Integer32,
                hwVOPGfastUPBOConfProfPsdA                       Integer32,
                hwVOPGfastUPBOConfProfPsdB                       Integer32
                }


        hwVOPUPBOConfProfIndex OBJECT-TYPE
            SYNTAX Unsigned32 (1..4294967295)
            MAX-ACCESS accessible-for-notify
            STATUS current
            DESCRIPTION
                "The hwVOPUPBOConfProfIndex identifies a row in the hwVOPUPBOConfProfTable."
            ::= { hwVOPUPBOConfProfEntry 1 }


        hwVOPUPBOConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy' or
                 'notInService'), it MUST be first unreferenced from all associated DSL lines.
                 A row in hwVOPUPBOConfProfTable is said to be unreferenced when there is no instance of
                 hwVOPActSetupUpboProfId in the hwVOPActSetupTable which refers to the row.
                "
            ::= { hwVOPUPBOConfProfEntry 2 }


        hwVOPUPBOConfProfDescription OBJECT-TYPE
            SYNTAX OCTET STRING (SIZE (0..128))
            MAX-ACCESS read-create
            STATUS current
            DESCRIPTION
                "The hwVOPUPBOConfProfDescription contains an optional human readable description for the profile."
            ::= { hwVOPUPBOConfProfEntry 3 }


        hwVOPUPBOConfProfUpboKL OBJECT-TYPE
            SYNTAX Gauge32 (0..1280)
            UNITS "0.1 dB"
            MAX-ACCESS read-create
            STATUS current
            DESCRIPTION
                "This configuration parameter defines the electrical length expressed in dB at 1MHz, kl0,
                 configured by the CO-MIB.The value ranges from 0 (coded as 0) to 128 dB (coded as 1280) in steps of 0.1 dB.
                 This parameter is relevant only if hwVOPUPBOConfProfUpboKLF is set to override(2),
                 which indicates that this parameter's value will override the VTUs' determination of the electrical length.
                 If hwVOPUPBOConfProfUpboKLF is set either to auto(1) or disableUpbo(3), then this parameter will be ignored.
                 Unit: 0.1 dB.
                "
            REFERENCE
                "ITU-T G.997.1, paragraph #7.3.1.2.14 a.2 (UPBOKL)"
            DEFVAL { 0 }
            ::= { hwVOPUPBOConfProfEntry 4 }


        hwVOPUPBOConfProfUpboKLF OBJECT-TYPE
            SYNTAX Xdsl2UpboKLF
            MAX-ACCESS read-create
            STATUS current
            DESCRIPTION
                "Defines the upstream power backoff force mode."
            REFERENCE
                "ITU-T G.997.1, paragraph #7.3.1.2.14 a.3 (UPBOKLF)"
            DEFVAL { disableUpbo }
            ::= { hwVOPUPBOConfProfEntry 5 }


        hwVOPUPBOConfProfKlAuto  OBJECT-TYPE
          SYNTAX      Unsigned32(1..4)
          MAX-ACCESS  read-create
          STATUS      current
          DESCRIPTION
            "This parameter defines the mode in which kl0 is computed when hwVOPUPBOConfProfUpboKLF is auto.
             Options:
             1--max(kl0_CO,kl0_CPE)
             2--min(kl0_CO,kl0_CPE)
             3--kl0_CO
             4--kl0_CPE
            "
          DEFVAL       { 3 }
          ::= { hwVOPUPBOConfProfEntry 6 }


        hwVOPUPBOConfProfPsdAUs1 OBJECT-TYPE
            SYNTAX Integer32 (4000..8095)
            UNITS "0.01 dBm/Hz"
            MAX-ACCESS read-create
            STATUS current
            DESCRIPTION
                "This configuration parameter defines the 'a' reference parameter of the UPBO reference PSD
                 used to compute the upstream power back-off for the upstream band US1.
                 A UPBOPSD defined for each band shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPUPBOConfProfPsdAUs1 to 4000 and hwVOPUPBOConfProfPsdBUs1 to 0 is a special
                 configuration to disable UPBO in the respective upstream band.
                 Unit: 0.01 dBm/Hz.
                "
            REFERENCE
                "ITU-T G.997.1, paragraph #7.3.1.2.14 a.1 (UPBOPSD-pb)"
            DEFVAL { 5650 }
            ::= { hwVOPUPBOConfProfEntry 7 }


        hwVOPUPBOConfProfPsdBUs1 OBJECT-TYPE
            SYNTAX Integer32 (0..4095)
            UNITS "0.01 dBm/Hz"
            MAX-ACCESS read-create
            STATUS current
            DESCRIPTION
                "This configuration parameter defines the 'b' reference parameter of the UPBO reference PSD
                 used to compute the upstream power back-off for the upstream band US1.
                 A UPBOPSD defined for each band shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPUPBOConfProfPsdAUs1 to 4000 and hwVOPUPBOConfProfPsdBUs1 to 0 is a special
                 configuration to disable UPBO in the respective upstream band.
                 Unit: 0.01 dBm/Hz.
                "
            REFERENCE
                "ITU-T G.997.1, paragraph #7.3.1.2.14 a.1 (UPBOPSD-pb)"
            DEFVAL { 1020 }
            ::= { hwVOPUPBOConfProfEntry 8 }


        hwVOPUPBOConfProfPsdAUs2 OBJECT-TYPE
            SYNTAX Integer32 (4000..8095)
            UNITS "0.01 dBm/Hz"
            MAX-ACCESS read-create
            STATUS current
            DESCRIPTION
                "This configuration parameter defines the 'a' reference parameter of the UPBO reference PSD
                 used to compute the upstream power back-off for the upstream band US2.
                 A UPBOPSD defined for each band shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPUPBOConfProfPsdAUs2 to 4000 and hwVOPUPBOConfProfPsdBUs2 to 0 is a special
                 configuration to disable UPBO in the respective upstream band.
                 Unit: 0.01 dBm/Hz.
                "
            REFERENCE
                "ITU-T G.997.1, paragraph #7.3.1.2.14 a.1 (UPBOPSD-pb)"
            DEFVAL { 5650 }
            ::= { hwVOPUPBOConfProfEntry 9 }


        hwVOPUPBOConfProfPsdBUs2 OBJECT-TYPE
            SYNTAX Integer32 (0..4095)
            UNITS "0.01 dBm/Hz"
            MAX-ACCESS read-create
            STATUS current
            DESCRIPTION
                "This configuration parameter defines the 'b' reference parameter of the UPBO reference PSD
                 used to compute the upstream power back-off for the upstream band US2.
                 A UPBOPSD defined for each band shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPUPBOConfProfPsdAUs2 to 4000 and hwVOPUPBOConfProfPsdBUs2 to 0 is a special
                 configuration to disable UPBO in the respective upstream band.
                 Unit: 0.01 dBm/Hz.
                "
            REFERENCE
                "ITU-T G.997.1, paragraph #7.3.1.2.14 a.1 (UPBOPSD-pb)"
            DEFVAL { 615 }
            ::= { hwVOPUPBOConfProfEntry 10 }


        hwVOPUPBOConfProfPsdAUs3 OBJECT-TYPE
            SYNTAX Integer32 (4000..8095)
            UNITS "0.01 dBm/Hz"
            MAX-ACCESS read-create
            STATUS current
            DESCRIPTION
                "This configuration parameter defines the 'a' reference parameter of the UPBO reference PSD
                 used to compute the upstream power back-off for the upstream band US3.
                 A UPBOPSD defined for each band shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPUPBOConfProfPsdAUs3 to 4000 and hwVOPUPBOConfProfPsdBUs3 to 0 is a special
                 configuration to disable UPBO in the respective upstream band.
                 Unit: 0.01 dBm/Hz.
                "
            REFERENCE
                "ITU-T G.997.1, paragraph #7.3.1.2.14 a.1 (UPBOPSD-pb)"
            DEFVAL { 4000 }
            ::= { hwVOPUPBOConfProfEntry 11 }


        hwVOPUPBOConfProfPsdBUs3 OBJECT-TYPE
            SYNTAX Integer32 (0..4095)
            UNITS "0.01 dBm/Hz"
            MAX-ACCESS read-create
            STATUS current
            DESCRIPTION
                "This configuration parameter defines the 'b' reference parameter of the UPBO reference PSD
                 used to compute the upstream power back-off for the upstream band US3.
                 A UPBOPSD defined for each band shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPUPBOConfProfPsdAUs3 to 4000 and hwVOPUPBOConfProfPsdBUs3 to 0 is a special
                 configuration to disable UPBO in the respective upstream band.
                 Unit: 0.01 dBm/Hz.
                "
            REFERENCE
                "ITU-T G.997.1, paragraph #7.3.1.2.14 a.1 (UPBOPSD-pb)"
            DEFVAL { 0 }
            ::= { hwVOPUPBOConfProfEntry 12 }


        hwVOPUPBOConfProfPsdAUs4 OBJECT-TYPE
            SYNTAX Integer32 (4000..8095)
            UNITS "0.01 dBm/Hz"
            MAX-ACCESS read-create
            STATUS current
            DESCRIPTION
                "This configuration parameter defines the 'a' reference parameter of the UPBO reference PSD
                 used to compute the upstream power back-off for the upstream band US4.
                 A UPBOPSD defined for each band shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPUPBOConfProfPsdAUs4 to 4000 and hwVOPUPBOConfProfPsdBUs4 to 0 is a special
                 configuration to disable UPBO in the respective upstream band.
                 Unit: 0.01 dBm/Hz.
                "
            REFERENCE
                "ITU-T G.997.1, paragraph #7.3.1.2.14 a.1 (UPBOPSD-pb)"
            DEFVAL { 4000 }
            ::= { hwVOPUPBOConfProfEntry 13 }


        hwVOPUPBOConfProfPsdBUs4 OBJECT-TYPE
            SYNTAX Integer32 (0..4095)
            UNITS "0.01 dBm/Hz"
            MAX-ACCESS read-create
            STATUS current
            DESCRIPTION
                "This configuration parameter defines the 'b' reference parameter of the UPBO reference PSD
                 used to compute the upstream power back-off for the upstream band US4.
                 A UPBOPSD defined for each band shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPUPBOConfProfPsdAUs4 to 4000 and hwVOPUPBOConfProfPsdBUs4 to 0 is a special
                 configuration to disable UPBO in the respective upstream band.
                 Unit: 0.01 dBm/Hz.
                "
            REFERENCE
                "ITU-T G.997.1, paragraph #7.3.1.2.14 a.1 (UPBOPSD-pb)"
            DEFVAL { 0 }
            ::= { hwVOPUPBOConfProfEntry 14 }


        hwVOPUPBOConfProfBoostMode  OBJECT-TYPE
            SYNTAX      Xdsl2UpboBoostMode
            MAX-ACCESS  read-create
            STATUS      current
            DESCRIPTION
                "The Equalized FEXT UPBO method.
                 Options:
                 1. disable(1)   - The Equalized FEXT UPBO method is not supported.
                 2. enable(2)    - The Equalized FEXT UPBO method is supported.
                "
            DEFVAL       { enable }
            ::= { hwVOPUPBOConfProfEntry 15 }


        hwVOPUPBOConfProfUpboKLREFUs1 OBJECT-TYPE
            SYNTAX Integer32 (0 | 18..635)
            UNITS "0.1 dB"
            MAX-ACCESS read-create
            STATUS current
            DESCRIPTION
                "This parameter defines the UPBO reference electrical length used to compute the upstream
                 power back-off for the upstream band US1, for the optional Equalized FEXT UPBO method.
                 The value ranges from 1.8 to 63.5 dB in steps of 0.1 dB with special value 0.
                 The use of the special value 0 is described in 7.2.1.3.2/G.993.2.
                 Unit: 0.1 dB.
                "
            REFERENCE
                "ITU-T G.997.1, paragraph #7.3.1.2.14 a.4 (UPBOKLREF-pb)"
            DEFVAL { 0 }
            ::= { hwVOPUPBOConfProfEntry 16 }


        hwVOPUPBOConfProfUpboKLREFUs2 OBJECT-TYPE
            SYNTAX Integer32 (0 | 18..635)
            UNITS "0.1 dB"
            MAX-ACCESS read-create
            STATUS current
            DESCRIPTION
                "This parameter defines the UPBO reference electrical length used to compute the upstream
                 power back-off for the upstream band US2, for the optional Equalized FEXT UPBO method.
                 The value ranges from 1.8 to 63.5 dB in steps of 0.1 dB with special value 0.
                 The use of the special value 0 is described in 7.2.1.3.2/G.993.2.
                 Unit: 0.1 dB.
                "
            REFERENCE
                "ITU-T G.997.1, paragraph #7.3.1.2.14 a.4 (UPBOKLREF-pb)"
            DEFVAL { 0 }
            ::= { hwVOPUPBOConfProfEntry 17 }


        hwVOPUPBOConfProfUpboKLREFUs3 OBJECT-TYPE
            SYNTAX Integer32 (0 | 18..635)
            UNITS "0.1 dB"
            MAX-ACCESS read-create
            STATUS current
            DESCRIPTION
                "This parameter defines the UPBO reference electrical length used to compute the upstream
                 power back-off for the upstream band US3, for the optional Equalized FEXT UPBO method.
                 The value ranges from 1.8 to 63.5 dB in steps of 0.1 dB with special value 0.
                 The use of the special value 0 is described in 7.2.1.3.2/G.993.2.
                 Unit: 0.1 dB.
                "
            REFERENCE
                "ITU-T G.997.1, paragraph #7.3.1.2.14 a.4 (UPBOKLREF-pb)"
            DEFVAL { 0 }
            ::= { hwVOPUPBOConfProfEntry 18 }


        hwVOPUPBOConfProfUpboKLREFUs4 OBJECT-TYPE
            SYNTAX Integer32 (0 | 18..635)
            UNITS "0.1 dB"
            MAX-ACCESS read-create
            STATUS current
            DESCRIPTION
                "This parameter defines the UPBO reference electrical length used to compute the upstream
                 power back-off for the upstream band US4, for the optional Equalized FEXT UPBO method.
                 The value ranges from 1.8 to 63.5 dB in steps of 0.1 dB with special value 0.
                 The use of the special value 0 is described in 7.2.1.3.2/G.993.2.
                 Unit: 0.1 dB.
                "
            REFERENCE
                "ITU-T G.997.1, paragraph #7.3.1.2.14 a.4 (UPBOKLREF-pb)"
            DEFVAL { 0 }
            ::= { hwVOPUPBOConfProfEntry 19 }

        hwVOPUPBOConfProfAeleMode  OBJECT-TYPE
            SYNTAX      Unsigned32(0..3)
            MAX-ACCESS  read-create
            STATUS      current
            DESCRIPTION
                "This parameter defines the UPBO electrical length estimation mode to be used 
                 in the Alternative Electrical Length Estimation method (ELE-M1) in 7.2.1.3.2.2/G.993.2. 
                 The value of this parameter is 0, 1, 2 or 3.
                 0-ELE_M0, 1-ELE_DS, 2-ELE_PB, 3-ELE_MIN
                "
            REFERENCE    "ITU-T G.997.1, paragraph 7.3.1.2.14"
            DEFVAL       { 0 }
            ::= { hwVOPUPBOConfProfEntry 20 }
          
        hwVOPUPBOConfProfUpboElmt  OBJECT-TYPE
            SYNTAX      Unsigned32(0..15)
            MAX-ACCESS  read-create
            STATUS      current
            DESCRIPTION
                "This parameter defines the UPBO electrical length minimum threshold percentile 
                 in percent used in the Alternative Electrical Length Estimation method (ELE-M1) 
                 in clause 7.2.1.3.2.2/G.993.2.  It is set by network management via the CO-MIB. 
                 The parameter ranges from 0 to 15 percent in steps of 1 percent.
                 This value is communicated to the VTU-R via G.994.1 at start-up.
                "
            REFERENCE    "ITU-T G.997.1, paragraph 7.3.1.2.14"
            DEFVAL       { 10 }
          ::= { hwVOPUPBOConfProfEntry 21 }
          
        hwVOPGfastUPBOConfProfUpboKL OBJECT-TYPE
            SYNTAX Gauge32 (0..1280)
            UNITS "0.1 dB"
            MAX-ACCESS read-create
            STATUS current
            DESCRIPTION
                "This configuration parameter defines the G.fast electrical length expressed in dB at 1MHz, kl0,
                 configured by the DPU-MIB.The value ranges from 0 (coded as 0) to 128 dB (coded as 1280) in steps of 0.1 dB.
                 This parameter is relevant only if hwVOPGfastUPBOConfProfUpboKLF is set to override(2),
                 which indicates that this parameter's value will override the XTUs' determination of the electrical length.
                 If hwVOPGfastUPBOConfProfUpboKLF is set either to auto(1) or disableUpbo(3), then this parameter will be ignored.
                 Unit: 0.1 dB.
                "
            REFERENCE
                "ITU-T G.9701, paragraph 7.3.1.4.2.1"
            DEFVAL { 0 }
            ::= { hwVOPUPBOConfProfEntry 22 }


        hwVOPGfastUPBOConfProfUpboKLF OBJECT-TYPE
            SYNTAX Xdsl2UpboKLF
            MAX-ACCESS read-create
            STATUS current
            DESCRIPTION
                "Defines the G.fast upstream power backoff force mode."
            REFERENCE
                "ITU-T G.9701, paragraph 7.3.1.4.2.1"
            DEFVAL { disableUpbo }
            ::= { hwVOPUPBOConfProfEntry 23 }


        hwVOPGfastUPBOConfProfKlAuto  OBJECT-TYPE
          SYNTAX      Unsigned32(1..4)
          MAX-ACCESS  read-create
          STATUS      current
          DESCRIPTION
            "This parameter defines the mode in which kl0 is computed when hwVOPGfastUPBOConfProfUpboKLF is auto.
             Options:
             1--max(kl0_CO,kl0_CPE)
             2--min(kl0_CO,kl0_CPE)
             3--kl0_CO
             4--kl0_CPE
            "
          DEFVAL       { 3 }
          ::= { hwVOPUPBOConfProfEntry 24 }


        hwVOPGfastUPBOConfProfPsdA OBJECT-TYPE
            SYNTAX Integer32 (4000..8095)
            UNITS "0.01 dBm/Hz"
            MAX-ACCESS read-create
            STATUS current
            DESCRIPTION
                "This configuration parameter defines the 'a' reference parameter of the UPBO reference PSD
                 used to compute the upstream power back-off.A UPBOPSD shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPGfastUPBOConfProfPsdA to 4000 and hwVOPGfastUPBOConfProfPsdB to 0 is a special
                 configuration to disable UPBO.
                 Unit: 0.01 dBm/Hz.
                "
            REFERENCE
                "ITU-T G.9701, paragraph 7.3.1.4"
            DEFVAL { 5650 }
            ::= { hwVOPUPBOConfProfEntry 25 }


        hwVOPGfastUPBOConfProfPsdB OBJECT-TYPE
            SYNTAX Integer32 (0..4095)
            UNITS "0.01 dBm/Hz"
            MAX-ACCESS read-create
            STATUS current
            DESCRIPTION
                "This configuration parameter defines the 'b' reference parameter of the UPBO reference PSD
                 used to compute the upstream power back-off.A UPBOPSD shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPGfastUPBOConfProfPsdA to 4000 and hwVOPGfastUPBOConfProfPsdB to 0 is a special
                 configuration to disable UPBO.
                 Unit: 0.01 dBm/Hz.
                "
            REFERENCE
                "ITU-T G.9701, paragraph 7.3.1.4"
            DEFVAL { 1020 }
            ::= { hwVOPUPBOConfProfEntry 26 }
            
        hwVOPGfastUPBOConfProfUpboKLREF OBJECT-TYPE
            SYNTAX Integer32 (0 | 18..635)
            UNITS "0.1 dB"
            MAX-ACCESS read-create
            STATUS current
            DESCRIPTION
                "This parameter defines the UPBO reference electrical length used to compute the upstream
                 power back-off, for the optional Equalized FEXT UPBO method.
                 The value ranges from 1.8 to 63.5 dB in steps of 0.1 dB with special value 0.
                 Unit: 0.1 dB.
                "
            REFERENCE
                "ITU-T G.9701, paragraph 7.3.1.4.2.2"
            DEFVAL { 0 }
            ::= { hwVOPUPBOConfProfEntry 27 }                                

        hwVOPDPBOProfileIndexNext OBJECT-TYPE
            SYNTAX HWVOPProfileIndexOrZeroType
            MAX-ACCESS read-only
            STATUS current
            DESCRIPTION
                "This object contains an appropriate value to be used for hwVOPDPBOConfProfIndex
                 when creating entries in the hwVOPDPBOConfProfTable.
                 The value '0' indicates that no unassigned entries are available.
                 To obtain the value of hwVOPDPBOConfProfIndex for a new entry in the table,
                 the manager issues a management protocol retrieval operation.
                 The agent will determine through its local policy when this index value will be made available for reuse.
                "
            ::= { hwVOPProfiles 9 }


        hwVOPDPBOConfProfTable OBJECT-TYPE
            SYNTAX SEQUENCE OF HWVOPDPBOConfProfEntry
            MAX-ACCESS not-accessible
            STATUS current
            DESCRIPTION
                "The table hwVOPDPBOConfProfTable contains all the parameters related to downstream power back-off.
                 Entries in this table MUST be maintained in a persistent manner.
                 A default profile with an index of '1' will always exist and its parameters will be set to
                 vendor-specific values, unless otherwise specified in this document.
                 The index of this table is hwVOPDPBOConfProfIndex.
                "
            REFERENCE
                "Broadband Forum TR-252, paragraph #5.6"
            ::= { hwVOPProfiles 10 }


        hwVOPDPBOConfProfEntry OBJECT-TYPE
            SYNTAX HWVOPDPBOConfProfEntry
            MAX-ACCESS not-accessible
            STATUS current
            DESCRIPTION
                "The table hwVOPDPBOConfProfTable contains all the parameters related to downstream power back-off.
                 Entries in this table MUST be maintained in a persistent manner.
                 A default profile with an index of '1' will always exist and its parameters will be set to
                 vendor-specific values, unless otherwise specified in this document.
                 The index of this entry is hwVOPDPBOConfProfIndex.
                "
            INDEX { hwVOPDPBOConfProfIndex }
            ::= { hwVOPDPBOConfProfTable 1 }


        HWVOPDPBOConfProfEntry ::=
            SEQUENCE {
                hwVOPDPBOConfProfIndex                        Unsigned32,
                hwVOPDPBOConfProfRowStatus                    RowStatus,
                hwVOPDPBOConfProfProfDescription              OCTET STRING,
                hwVOPDPBOConfProfWkMdMask                     Unsigned32,
                hwVOPDPBOConfProfEsEL                         Gauge32,
                hwVOPDPBOConfProfEselMin                      Unsigned32,
                hwVOPDPBOConfProfEPsd                         Xdsl2PsdMaskDs,
                hwVOPDPBOConfProfCableModelA                  Gauge32,
                hwVOPDPBOConfProfCableModelB                  Gauge32,
                hwVOPDPBOConfProfCableModelC                  Gauge32,
                hwVOPDPBOConfProfMus                          Gauge32,
                hwVOPDPBOConfProfFMin                         Gauge32,
                hwVOPDPBOConfProfFMax                         Gauge32,
                hwVOPDPBOConfFEXTFactor                       INTEGER
             }


        hwVOPDPBOConfProfIndex OBJECT-TYPE
            SYNTAX Unsigned32 (1..4294967295)
            MAX-ACCESS accessible-for-notify
            STATUS current
            DESCRIPTION
                "The hwVOPDPBOConfProfIndex identifies a row in the hwVOPDPBOConfProfTable."
            ::= { hwVOPDPBOConfProfEntry 1 }


        hwVOPDPBOConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy' or
                 'notInService'), it MUST be first unreferenced from all associated DSL lines.
                 A row in hwVOPDPBOConfProfTable is said to be not referenced when there is no
                 instance of hwVOPActSetupDpboProfId in the hwVOPActSetupTable which refers to the row.
                "
            ::= { hwVOPDPBOConfProfEntry 2 }


        hwVOPDPBOConfProfProfDescription OBJECT-TYPE
            SYNTAX OCTET STRING (SIZE (0..128))
            MAX-ACCESS read-create
            STATUS current
            DESCRIPTION
                "The hwVOPDPBOConfProfProfDescription contains an optional human readable description for the profile."
            ::= { hwVOPDPBOConfProfEntry 3 }

        hwVOPDPBOConfProfWkMdMask  OBJECT-TYPE
            SYNTAX      Unsigned32 (0..511)
            MAX-ACCESS  read-create
            STATUS      current
            DESCRIPTION
                "This configuration parameter defines the current enabled DPBO working mode mask.
                 DPBO working mode enabling:1-ADSL, 2-ADSL2+ 3-VDSL2.
                 Options :
                 1--current enabled dpbo work mode:ADSL
                 2--current enabled dpbo work mode:ADSL2+
                 3--current enabled dpbo work mode:ADSL,ADSL2+
                 4--current enabled dpbo work mode:VDSL2
                 5--current enabled dpbo work mode:ADSL,VDSL2
                 6--current enabled dpbo work mode:ADSL2+,VDSL2
                 7--current enabled dpbo work mode:ADSL,ADSL2+,VDSL2
                "
            DEFVAL       { 7 }
            ::= { hwVOPDPBOConfProfEntry 4 }

        hwVOPDPBOConfProfEsEL OBJECT-TYPE
            SYNTAX Gauge32 (0..511)
            UNITS "0.5 dB"
            MAX-ACCESS read-create
            STATUS current
            DESCRIPTION
                "This configuration parameter defines the assumed electrical length of cables (E-side cables)
                 connecting exchange based DSL services to a remote flexibility point (cabinet), that hosts the xTU-C
                 that is subject to spectrally shaped downstream power back- off (DPBO) depending on this length.
                 The electrical length is defined as the loss (in dB) of an equivalent length of hypothetical
                 cable at a reference frequency defined by the network operator or in spectrum management regulations.
                 This parameter shall be coded as an unsigned integer representing an electrical length
                 from 0 dB (coded as 0) to 255.5 dB (coded as 511) in steps of 0.5 dB.
                 All values in the range are valid. If this parameter is set to zero, the DPBO shall be disabled.
                 Unit: 0.5dB.
                "
            REFERENCE
                "ITU-T G.997.1, paragraph #7.3.1.2.13 (DPBOESEL)"
            DEFVAL { 0 }
            ::= { hwVOPDPBOConfProfEntry 5 }

        hwVOPDPBOConfProfEselMin  OBJECT-TYPE
            SYNTAX      Unsigned32 (0..511)
            UNITS       "0.5dB"
            MAX-ACCESS  read-create
            STATUS      current
            DESCRIPTION
                "DPBOESELMIN in dB is the minimum of all main cable losses for the KVz supplied when using
                 the SOL model (expansion of a KVz and VDSL2 provision of additional KVz areas from this KVz
                 using cross-cables to additional KVz), including the KVz at the MSAN site. This value must
                 be adjustable as the minimum requirement via the SNMP interface in the configuration profile
                 for each VDSL2 port, and is set individually for each MSAN site and usage. As an option,
                 As an option, adjustment can be done for each MSAN or line card, thus taking effect for
                 entire port groups. It is used only for determining the MUF.
                 Unit: 0.5dB.
                "
            ::= { hwVOPDPBOConfProfEntry 6 }

        hwVOPDPBOConfProfEPsd OBJECT-TYPE
            SYNTAX Xdsl2PsdMaskDs
            MAX-ACCESS read-create
            STATUS current
            DESCRIPTION
                "This configuration parameter defines the PSD mask that is assumed to be permitted at the exchange.
                 This parameter shall use the same format as xdsl2LConfProfPsdMaskDs (PSDMASKds).
                 The maximum number of breakpoints for xdsl2LConfProfDpboEPsd is 16.
                "
            REFERENCE
                "ITU-T G.997.1, paragraph #7.3.1.2.13 (DPBOEPSD)"
            ::= { hwVOPDPBOConfProfEntry 7 }


        hwVOPDPBOConfProfCableModelA OBJECT-TYPE
            SYNTAX Gauge32 (0..640)
            UNITS "2^-8"
            MAX-ACCESS read-create
            STATUS current
            DESCRIPTION
                "The E-side Cable Model parameter A (DPBOESCMA) of the cable model (DPBOESCM) for cables
                 connecting exchange based DSL services to a remote flexibility point (cabinet), that hosts the
                 xTU-C that is subject to spectrally shaped downstream power back-off (DPBO) depending on this value.
                 The cable model is in terms of three scalars xdsl2LConfProfDpboEsCableModelA (DPBOESCMA),
                 xdsl2LConfProfDpboEsCableModelB(DPBOESCMB), and xdsl2LConfProfDpboEsCableModelC (DPBOESCMC),
                 that are used to estimate the frequency dependent loss of E-side cables calculated
                 from the xdsl2LConfProfDpboEsEL (DPBOESEL) parameter.
                 Possible values shall be coded as unsigned integers representing a scalar value
                 from -1 (coded as 0) to 1.5 (coded as 640) in steps of 2^-8.
                 All values in the range are valid. This parameter is used only for G.993.2.
                 Unit: 2^-8.
                "
            REFERENCE
                "ITU-T G.997.1, paragraph #7.3.1.2.13 (DPBOESCMA)"
            DEFVAL { 256 }
            ::= { hwVOPDPBOConfProfEntry 8 }


        hwVOPDPBOConfProfCableModelB OBJECT-TYPE
            SYNTAX Gauge32 (0..640)
            UNITS "2^-8"
            MAX-ACCESS read-create
            STATUS current
            DESCRIPTION
                "The E-side Cable Model parameter B (DPBOESCMB) of the cable model (DPBOESCM) for cables
                 connecting exchange based DSL services to a remote flexibility point (cabinet), that hosts the xTU-C
                 that is subject to spectrally shaped downstream power back-off (DPBO) depending on this value.
                 The cable model is in terms of three scalars dsl2LConfProfDpboEsCableModelA (DPBOESCMA),
                 xdsl2LConfProfDpboEsCableModelB(DPBOESCMB), and xdsl2LConfProfDpboEsCableModelC (DPBOESCMC),
                 that are used to estimate the frequency dependent loss of E-side cables calculated
                 from the xdsl2LConfProfDpboEsEL (DPBOESEL) parameter.
                 Possible values shall be coded as unsigned integers representing a scalar value
                 from -1 (coded as 0) to 1.5 (coded as 640) in steps of 2^-8.
                 All values in the range are valid. This parameter is used only for G.993.2.
                 Unit: 2^-8.
                "
            REFERENCE
                "ITU-T G.997.1, paragraph #7.3.1.2.13 (DPBOESCMB)"
            DEFVAL { 512 }
            ::= { hwVOPDPBOConfProfEntry 9 }


        hwVOPDPBOConfProfCableModelC OBJECT-TYPE
            SYNTAX Gauge32 (0..640)
            UNITS "2^-8"
            MAX-ACCESS read-create
            STATUS current
            DESCRIPTION
                "The E-side Cable Model parameter C (DPBOESCMC) of the cable model (DPBOESCM) for cables
                 connecting exchange based DSL services to a remote flexibility point (cabinet), that hosts the
                 xTU-C that is subject to spectrally shaped downstream power back-off (DPBO) depending on this value.
                 The cable model is in terms of three scalars xdsl2LConfProfDpboEsCableModelA (DPBOESCMA),
                 xdsl2LConfProfDpboEsCableModelB(DPBOESCMB), and  xdsl2LConfProfDpboEsCableModelC (DPBOESCMC),
                 that are used to estimate the frequency dependent loss of E-side cables calculated
                 from the xdsl2LConfProfDpboEsEL (DPBOESEL) parameter.
                 Possible values shall be coded as unsigned integers representing a scalar value
                 from -1 (coded as 0) to 1.5 (coded as 640) in steps of 2^-8.
                 All values in the range are valid. This parameter is used only for G.993.2.
                 Unit: 2^-8.
                "
            REFERENCE
                "ITU-T G.997.1, paragraph #7.3.1.2.13 (DPBOESCMC)"
            DEFVAL { 256 }
            ::= { hwVOPDPBOConfProfEntry 10 }


        hwVOPDPBOConfProfMus OBJECT-TYPE
            SYNTAX Gauge32 (0..255)
            UNITS "-0.5 dBm/Hz"
            MAX-ACCESS read-create
            STATUS current
            DESCRIPTION
                "This configuration parameter defines the assumed Minimum Usable receive PSD mask (in dBm/Hz)
                 for exchange based services, used to modify parameter xdsl2LConfProfDpboFMax (DPBOFMAX)
                 defined below [to determine the DPBO]. It shall be coded as an unsigned integer representing
                 a PSD mask level from 0 dBm/Hz (coded as 0) to -127.5 dBm/Hz (coded as 255) in steps of 0.5 dBm/Hz.
                 All values in the range are valid.
                 NOTE - The PSD mask level is 3.5 dB above the signal PSD level.
                 This parameter is used only for G.993.2.
                 Unit: -0.5 dBm/Hz.
                "
            REFERENCE
                "ITU-T G.997.1, paragraph #7.3.1.2.13 (DPBOMUS)"
            DEFVAL { 180 }
            ::= { hwVOPDPBOConfProfEntry 11 }


        hwVOPDPBOConfProfFMin OBJECT-TYPE
            SYNTAX Gauge32 (0..2048)
            UNITS "4.3125 kHz"
            MAX-ACCESS read-create
            STATUS current
            DESCRIPTION
                "This configuration parameter defines the minimum frequency from which the DPBO shall be applied.
                 It ranges from 0 kHz (coded as 0) to 8832 kHz (coded as 2048) in steps of 4.3125 kHz.
                 This parameter is used only for G.993.2.
                 Unit: 4.3125 kHz.
                "
            REFERENCE
                "ITU-T G.997.1, paragraph #7.3.1.2.13 (DPBOFMIN)"
            DEFVAL { 0 }
            ::= { hwVOPDPBOConfProfEntry 12 }


        hwVOPDPBOConfProfFMax OBJECT-TYPE
            SYNTAX Gauge32 (32..8191)
            UNITS "4.3125 kHz"
            MAX-ACCESS read-create
            STATUS current
            DESCRIPTION
                "This configuration parameter defines the maximum frequency at which DPBO may be applied.
                 It ranges from 138 kHz (coded as 32) to 35323.6875 kHz (coded as 8191) in steps of 4.3125 kHz.
                 This parameter is used only for G.993.2.
                 Unit: 4.3125 kHz.
                "
            REFERENCE
                "ITU-T G.997.1, paragraph #7.3.1.2.13 (DPBOFMAX)"
            DEFVAL { 511 }
            ::= { hwVOPDPBOConfProfEntry 13 }
            
        hwVOPDPBOConfFEXTFactor OBJECT-TYPE
            SYNTAX INTEGER {
                               disable(1),
                               enable(2)
                           } 
            MAX-ACCESS read-create
            STATUS current
            DESCRIPTION
                "This configuration parameter defines the switch of the delta FEXT-factor.
                 Options:
                 1. disable(1) - The switch of the delta FEXT-factor is disabled
                 2. enable(2)  - The switch of the delta FEXT-factor is enabled
                "
            DEFVAL { 1 }
            ::= { hwVOPDPBOConfProfEntry 14 }    


        hwVOPRFIProfileIndexNext OBJECT-TYPE
            SYNTAX HWVOPProfileIndexOrZeroType
            MAX-ACCESS read-only
            STATUS current
            DESCRIPTION
                "This object contains an appropriate value to be used for hwVOPRFIConfProfIndex
                 when creating entries in the hwVOPRFIConfProfTable.
                 The value '0' indicates that no unassigned entries are available.
                 To obtain the value of hwVOPRFIConfProfIndex for a new entry in the table,
                 the manager issues a management protocol retrieval operation.
                 The agent will determine through its local policy when this index value will be made available for reuse.
                "
            ::= { hwVOPProfiles 11 }


        hwVOPRFIConfProfTable OBJECT-TYPE
            SYNTAX SEQUENCE OF HWVOPRFIConfProfEntry
            MAX-ACCESS not-accessible
            STATUS current
            DESCRIPTION
                "RFI notches are necessary only when radio services may be disturbed during operation,
                 therefore this parameter should be separated from all other profiles.
                 Entries in this table MUST be maintained in a persistent manner.
                 A default profile with an index of '1' will always exist and its parameters will be set to
                 vendor-specific values, unless otherwise specified in this document.
                 The index of this table is hwVOPRFIConfProfIndex.
                "
            REFERENCE
                "Broadband Forum TR-252, paragraph #5.6"
            ::= { hwVOPProfiles 12 }


        hwVOPRFIConfProfEntry OBJECT-TYPE
            SYNTAX HWVOPRFIConfProfEntry
            MAX-ACCESS not-accessible
            STATUS current
            DESCRIPTION
                "RFI notches are necessary only when radio services may be disturbed during operation,
                 therefore this parameter should be separated from all other profiles.
                 Entries in this table MUST be maintained in a persistent manner.
                 A default profile with an index of '1' will always exist and its parameters will be set to
                 vendor-specific values, unless otherwise specified in this document.
                 The index of this entry is hwVOPRFIConfProfIndex.
                "
            INDEX { hwVOPRFIConfProfIndex }
            ::= { hwVOPRFIConfProfTable 1 }


        HWVOPRFIConfProfEntry ::=
            SEQUENCE {
                hwVOPRFIConfProfIndex                        Unsigned32,
                hwVOPRFIConfProfRowStatus                    RowStatus,
                hwVOPRFIConfProfDescription                  OCTET STRING,
                hwVOPRFIConfProfRfiBands                     Xdsl2RfiBands,
                hwVOPGfastRFIConfProfRfiBands                Xdsl2RfiBands,
                hwVOPGfastRFIConfProfIarBands                HWVOPGfastIarBands                
             }


        hwVOPRFIConfProfIndex OBJECT-TYPE
            SYNTAX Unsigned32 (1..4294967295)
            MAX-ACCESS accessible-for-notify
            STATUS current
            DESCRIPTION
                "The hwVOPRFIConfProfIndex identifies a row in the hwVOPRFIConfProfTable."
            ::= { hwVOPRFIConfProfEntry 1 }


        hwVOPRFIConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy' or
                 'notInService'), it MUST be first unreferenced from all associated DSL lines.
                 A row in hwVOPRFIConfProfTable is said to be unreferenced when there is no instance of
                 hwVOPActSetupRfiProfId in the hwVOPActSetupTable which refers to the row.
                "
            ::= { hwVOPRFIConfProfEntry 2 }


        hwVOPRFIConfProfDescription OBJECT-TYPE
            SYNTAX OCTET STRING (SIZE (0..128))
            MAX-ACCESS read-create
            STATUS current
            DESCRIPTION
                "The hwVOPRFIConfProfDescription contains an optional human readable description for the profile."
            ::= { hwVOPRFIConfProfEntry 3 }


        hwVOPRFIConfProfRfiBands OBJECT-TYPE
            SYNTAX Xdsl2RfiBands
            MAX-ACCESS read-create
            STATUS current
            DESCRIPTION
                "For ADSL2plus operation mode, this configuration parameter defines the subset of downstream PSD mask
                 breakpoints, as specified in hwVOPModeSpecificPSDConfProfPsdMaskDs (PSDMASKds), that shall be
                 used to notch an RFI band. This subset consists of pairs of consecutive subcarrier indices
                 belonging to breakpoints: [ti; ti + 1], corresponding to the low level of the notch.
                 The specific interpolation around these points is defined in ITU-T Rec. G.992.5.

                 For VDSL2 operation mode, this configuration parameter defines the bands where the PSD shall be reduced
                 as specified in ITU-T Rec. G.993.2 #7.2.1.2. Each band shall be represented by a start and stop subcarrier
                 indices with a subcarrier spacing of 4.3125 kHz.

                 Up to 16 bands may be specified.
                 This parameter defines the RFI bands for both upstream and downstream directions.
                "
            REFERENCE
                "ITU-T G.997.1, paragraph #7.3.1.2.10 (RFIBANDS)"
            ::= { hwVOPRFIConfProfEntry 4 }
            
        hwVOPGfastRFIConfProfRfiBands OBJECT-TYPE
            SYNTAX Xdsl2RfiBands
            MAX-ACCESS read-create
            STATUS current
            DESCRIPTION
                "This configuration parameter defines the bands where the PSD shall be reduced as specified in ITU-T G.9701 #7.3.1.2. 
                 Each band shall be represented by a start and stop subcarrier indices with a subcarrier spacing of 51.75 kHz.
                 Up to 16 bands may be specified.
                 This parameter defines the RFI bands for both upstream and downstream directions.
                 Default value: No RFI bands.
                "
            REFERENCE
                "ITU-T G.9701, paragraph 7.3.1.2 and 12.3.2.1.1"
            ::= { hwVOPRFIConfProfEntry 5 }
            
        hwVOPGfastRFIConfProfIarBands OBJECT-TYPE
            SYNTAX HWVOPGfastIarBands
            MAX-ACCESS read-create
            STATUS current
            DESCRIPTION
                "Defines for each International Amateur Radio (IAR) band whether transmit PSD reduction is enabled or disabled in that band.
                 It is represented as a bitmap (0 if not allowed and 1 if allowed)with the following definitions.
                 Bit representation:
                 0	International amateur radio band 1800 2000 kHz
                 1	International amateur radio band 3500 4000 kHz
                 2	International amateur radio band 7000 7300 kHz
                 3	International amateur radio band 10100 10150 kHz 
                 4	International amateur radio band 14000 14350 kHz
                 5	International amateur radio band 18068 18168 kHz
                 6	International amateur radio band 21000 21450 kHz
                 7	International amateur radio band 24890 24990 kHz
                 8	International amateur radio band 28000 29700 kHz
                 9	International amateur radio band 50000 54000 kHz
                 10	International amateur radio band 70000 70500 kHz
                 11	International amateur radio band 144000 148000 kHz
                 Default value: All IAR bands disabled (no PSD reduction).
                "
            REFERENCE
                "ITU-T G.9701, paragraph 7.3.1.2 and 12.3.2.1.1, G.994.1 Table 11.70.8 and 11.70.8.1"
            ::= { hwVOPRFIConfProfEntry 6 }                        


        hwVOPSNRMarginProfileIndexNext OBJECT-TYPE
            SYNTAX HWVOPProfileIndexOrZeroType
            MAX-ACCESS read-only
            STATUS current
            DESCRIPTION
                "This object contains an appropriate value to be used for hwVOPSNRMarginConfProfIndex
                 when creating entries in the hwVOPSNRMarginConfProfTable.
                 The value '0' indicates that no unassigned entries are available.
                 To obtain the value of hwVOPSNRMarginConfProfIndex for a new entry in the table,
                 the manager issues a management protocol retrieval operation.
                 The agent will determine through its local policy when this index value will be made available for reuse.
                "
            ::= { hwVOPProfiles 13 }


        hwVOPSNRMarginConfProfTable OBJECT-TYPE
            SYNTAX SEQUENCE OF HWVOPSNRMarginConfProfEntry
            MAX-ACCESS not-accessible
            STATUS current
            DESCRIPTION
                "Noise margins are important for line robustness and need to be configured independently
                 from other spectrum related parameters to reduce the amount of combinations.
                 These parameters may be adjusted because of the changed disturber's impact while data rates aren't changed.
                 Entries in this table MUST be maintained in a persistent manner.
                 A default profile with an index of '1' will always exist and its parameters will be set to
                 vendor-specific values, unless otherwise specified in this document.
                 The index of this table is hwVOPSNRMarginConfProfIndex.
                "
            REFERENCE
                "Broadband Forum TR-252, paragraph #5.7"
            ::= { hwVOPProfiles 14 }


        hwVOPSNRMarginConfProfEntry OBJECT-TYPE
            SYNTAX HWVOPSNRMarginConfProfEntry
            MAX-ACCESS not-accessible
            STATUS current
            DESCRIPTION
                "Noise margins are important for line robustness and need to be configured independently
                 from other spectrum related parameters to reduce the amount of combinations.
                 These parameters may be adjusted because of the changed disturber's impact while data rates aren't changed.
                 Entries in this table MUST be maintained in a persistent manner.
                 A default profile with an index of '1' will always exist and its parameters will be set to
                 vendor-specific values, unless otherwise specified in this document.
                 The index of this entry is hwVOPSNRMarginConfProfIndex.
                "
            INDEX { hwVOPSNRMarginConfProfIndex }
            ::= { hwVOPSNRMarginConfProfTable 1 }


        HWVOPSNRMarginConfProfEntry ::=
            SEQUENCE {
                hwVOPSNRMarginConfProfIndex                       Unsigned32,
                hwVOPSNRMarginConfProfRowStatus                   RowStatus,
                hwVOPSNRMarginConfProfDescription                 OCTET STRING,
                hwVOPSNRMarginConfProfMinSnrmDs                   Gauge32,
                hwVOPSNRMarginConfProfMinSnrmUs                   Gauge32,
                hwVOPSNRMarginConfProfTargetSnrmDs                Gauge32,
                hwVOPSNRMarginConfProfTargetSnrmUs                Gauge32,
                hwVOPSNRMarginConfProfMaxSnrmDs                   Gauge32,
                hwVOPSNRMarginConfProfMaxSnrmUs                   Gauge32,
                hwVOPSNRMarginConfProfSnrModeDs                   Xdsl2LineSnrMode,
                hwVOPSNRMarginConfProfSnrModeUs                   Xdsl2LineSnrMode,
                hwVOPSNRMarginConfProfRaModeDs                    Xdsl2RaMode,
                hwVOPSNRMarginConfProfRaModeUs                    Xdsl2RaMode,
                hwVOPSNRMarginConfProfRaUsNrmDs                   Gauge32,
                hwVOPSNRMarginConfProfRaUsNrmUs                   Gauge32,
                hwVOPSNRMarginConfProfRaDsNrmDs                   Gauge32,
                hwVOPSNRMarginConfProfRaDsNrmUs                   Gauge32,
                hwVOPSNRMarginConfProfUsTimeDs                    Gauge32,
                hwVOPSNRMarginConfProfUsTimeUs                    Gauge32,
                hwVOPSNRMarginConfProfDsTimeDs                    Gauge32,
                hwVOPSNRMarginConfProfDsTimeUs                    Gauge32,
                hwVOPGfastSNRMarginConfProfMinSnrmDs              Gauge32,
                hwVOPGfastSNRMarginConfProfMinSnrmUs              Gauge32,
                hwVOPGfastSNRMarginConfProfTargetSnrmDs           Gauge32,
                hwVOPGfastSNRMarginConfProfTargetSnrmUs           Gauge32,
                hwVOPGfastSNRMarginConfProfMaxSnrmDs              Gauge32,
                hwVOPGfastSNRMarginConfProfMaxSnrmUs              Gauge32,
                hwVOPGfastSNRMarginConfProfSnrModeDs              Xdsl2LineSnrMode,
                hwVOPGfastSNRMarginConfProfSnrModeUs              Xdsl2LineSnrMode,
                hwVOPGfastSNRMarginConfProfRaModeDs               HWVOPGfastRaMode,
                hwVOPGfastSNRMarginConfProfRaModeUs               HWVOPGfastRaMode,
                hwVOPGfastSNRMarginConfProfRaUsNrmDs              Gauge32,
                hwVOPGfastSNRMarginConfProfRaUsNrmUs              Gauge32,
                hwVOPGfastSNRMarginConfProfRaDsNrmDs              Gauge32,
                hwVOPGfastSNRMarginConfProfRaDsNrmUs              Gauge32,
                hwVOPGfastSNRMarginConfProfUsTimeDs               Gauge32,
                hwVOPGfastSNRMarginConfProfUsTimeUs               Gauge32,
                hwVOPGfastSNRMarginConfProfDsTimeDs               Gauge32,
                hwVOPGfastSNRMarginConfProfDsTimeUs               Gauge32,
                hwVOPGfastSNRMarginConfProfTargetSnrmRmcDs         Gauge32,
                hwVOPGfastSNRMarginConfProfTargetSnrmRmcUs         Gauge32,
                hwVOPGfastSNRMarginConfProfMinSnrmRmcDs           Gauge32,
                hwVOPGfastSNRMarginConfProfMinSnrmRmcUs           Gauge32,
                hwVOPGfastSNRMarginConfProfMaxBLRmcDs             Gauge32,
                hwVOPGfastSNRMarginConfProfMaxBLRmcUs             Gauge32
             }


        hwVOPSNRMarginConfProfIndex OBJECT-TYPE
            SYNTAX Unsigned32 (1..4294967295)
            MAX-ACCESS accessible-for-notify
            STATUS current
            DESCRIPTION
                "The hwVOPSNRMarginConfProfIndex identifies a row in the hwVOPSNRMarginConfProfTable."
            ::= { hwVOPSNRMarginConfProfEntry 1 }


        hwVOPSNRMarginConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy' or
                 'notInService'), it MUST be first unreferenced from all associated DSL lines.
                 A row in hwVOPSNRMarginConfProfTable is said to be unreferenced when there is no instance of
                 hwVOPActSetupNoiseMarginProfId in the hwVOPActSetupTable which refers to the row.
                "
            ::= { hwVOPSNRMarginConfProfEntry 2 }


        hwVOPSNRMarginConfProfDescription OBJECT-TYPE
            SYNTAX OCTET STRING (SIZE (0..128))
            MAX-ACCESS read-create
            STATUS current
            DESCRIPTION
                "The hwVOPSNRMarginConfProfDescription contains an optional human readable description for the profile."
            ::= { hwVOPSNRMarginConfProfEntry 3 }


        hwVOPSNRMarginConfProfMinSnrmDs OBJECT-TYPE
            SYNTAX Gauge32 (0..310)
            UNITS "0.1 dB"
            MAX-ACCESS read-create
            STATUS current
            DESCRIPTION
                "The minimum Noise Margin the xTU-R receiver shall tolerate.
                 If the noise margin falls below this level, the xTU-R shall request that the xTU-C increase
                 the xTU-C transmit power.
                 If an increase of xTU-C transmit power is not possible, a loss-of-margin (LOM) defect occurs,
                 the xTU-R shall fail and attempt to re-initialize and the NMS shall be notified.
                 The minimum noise margin ranges from 0 to 310 units of 0.1 dB (Physical values are 0 to 31 dB).
                 A value of 0 means that there is no minimum.
                 Unit: 0.1 dB.
                "
            REFERENCE
                "ITU-T G.997.1, paragraph #7.3.1.3.5 (MINSNRMds)"
            DEFVAL { 10 }
            ::= { hwVOPSNRMarginConfProfEntry 4 }


        hwVOPSNRMarginConfProfMinSnrmUs OBJECT-TYPE
            SYNTAX Gauge32 (0..310)
            UNITS "0.1 dB"
            MAX-ACCESS read-create
            STATUS current
            DESCRIPTION
                "The minimum Noise Margin the xTU-C receiver shall tolerate.
                 If the noise margin falls below this level, the xTU-C shall request that the xTU-R increase
                 the xTU-R transmit power.
                 If an increase of xTU-R transmit power is not possible, a loss-of-margin (LOM) defect occurs,
                 the xTU-C shall fail and attempt to re-initialize and the NMS shall be notified.
                 The minimum noise margin ranges from 0 to 310 units of 0.1 dB (Physical values are 0 to 31 dB).
                 A value of 0 means that there is no minimum.
                 Unit: 0.1 dB.
                "
            REFERENCE
                "ITU-T G.997.1, paragraph #7.3.1.3.6 (MINSNRMus)"
            DEFVAL { 10 }
            ::= { hwVOPSNRMarginConfProfEntry 5 }


        hwVOPSNRMarginConfProfTargetSnrmDs OBJECT-TYPE
            SYNTAX Gauge32 (0..310)
            UNITS "0.1 dB"
            MAX-ACCESS read-create
            STATUS current
            DESCRIPTION
                "The minimum Noise Margin the xTU-R receiver shall achieve, relative to the BER requirement
                 for each of the downstream bearer channels, to successfully complete initialization.
                 The target noise margin ranges from 0 to 310 units of 0.1 dB (Physical values are 0 to 31 dB).
                 Unit: 0.1 dB.
                "
            REFERENCE
                "ITU-T G.997.1, paragraph #7.3.1.3.1 (TARSNRMds)"
            DEFVAL { 60 }
            ::= { hwVOPSNRMarginConfProfEntry 6 }


        hwVOPSNRMarginConfProfTargetSnrmUs OBJECT-TYPE
            SYNTAX Gauge32 (0..310)
            UNITS "0.1 dB"
            MAX-ACCESS read-create
            STATUS current
            DESCRIPTION
                "The minimum Noise Margin the xTU-C receiver shall achieve, relative to the BER requirement
                 for each of the upstream bearer channels, to successfully complete initialization.
                 The target noise margin ranges from 0 to 310 units of 0.1 dB (Physical values are 0 to 31 dB).
                 Unit: 0.1 dB.
                "
            REFERENCE
                "ITU-T G.997.1, paragraph #7.3.1.3.2 (TARSNRMus)"
            DEFVAL { 60 }
            ::= { hwVOPSNRMarginConfProfEntry 7 }


        hwVOPSNRMarginConfProfMaxSnrmDs OBJECT-TYPE
            SYNTAX Gauge32 (0..310 | 2147483647)
            UNITS "0.1 dB"
            MAX-ACCESS read-create
            STATUS current
            DESCRIPTION
                "The maximum Noise Margin the xTU-R receiver shall try to sustain.
                 If the Noise Margin is above this level, the xTU-R shall request that the xTU-C reduce
                 the xTU-C transmit power to get a noise margin below this limit (if this functionality is supported).
                 The maximum noise margin ranges from 0 to 310 units of 0.1 dB (Physical values are 0 to 31 dB).
                 A value of 0x7FFFFFFF (2147483647) means that there is no maximum.
                 Unit: 0.1 dB.
                "
            REFERENCE
                "ITU-T G.997.1, paragraph #7.3.1.3.3 (MAXSNRMds)"
            DEFVAL { 310 }
            ::= { hwVOPSNRMarginConfProfEntry 8 }


        hwVOPSNRMarginConfProfMaxSnrmUs OBJECT-TYPE
            SYNTAX Gauge32 (0..310 | 2147483647)
            UNITS "0.1 dB"
            MAX-ACCESS read-create
            STATUS current
            DESCRIPTION
                "The maximum Noise Margin the xTU-C receiver shall try to sustain.
                 If the Noise Margin is above this level, the xTU-C shall request that the xTU-R reduce
                 the xTU-R transmit power to get a noise margin below this limit (if this functionality is supported).
                 The maximum noise margin ranges from 0 to 310 units of 0.1 dB (Physical values are 0 to 31 dB).
                 A value of 0x7FFFFFFF (2147483647) means that there is no maximum.
                 Unit: 0.1 dB.
                "
            REFERENCE
                "ITU-T G.997.1, paragraph #7.3.1.3.4 (MAXSNRMus)"
            DEFVAL { 310 }
            ::= { hwVOPSNRMarginConfProfEntry 9 }


        hwVOPSNRMarginConfProfSnrModeDs OBJECT-TYPE
            SYNTAX Xdsl2LineSnrMode
            MAX-ACCESS read-create
            STATUS current
            DESCRIPTION
                "This parameter enables the transmitter referred virtual noise in the downstream direction.
                 The configuration parameters for virtual noise are in the hwVOPVirtualNoiseConfProfTable.
                "
            REFERENCE
                "ITU-T G.997.1, paragraph #7.3.1.7.1 (SNRMODEds)"
            DEFVAL { virtualNoiseDisabled }
            ::= { hwVOPSNRMarginConfProfEntry 10 }


        hwVOPSNRMarginConfProfSnrModeUs OBJECT-TYPE
            SYNTAX Xdsl2LineSnrMode
            MAX-ACCESS read-create
            STATUS current
            DESCRIPTION
                "This parameter enables the transmitter referred virtual noise in the upstream direction.
                 The configuration parameters for virtual noise are in the hwVOPVirtualNoiseConfProfTable.
                "
            REFERENCE
                "ITU-T G.997.1, paragraph #7.3.1.7.2 (SNRMODEus)"
            DEFVAL { virtualNoiseDisabled }
            ::= { hwVOPSNRMarginConfProfEntry 11 }


        hwVOPSNRMarginConfProfRaModeDs OBJECT-TYPE
            SYNTAX Xdsl2RaMode
            MAX-ACCESS read-create
            STATUS current
            DESCRIPTION
                "The mode of operation of a rate-adaptive xTU-C in the transmit direction."
            REFERENCE
                "ITU-T G.997.1, paragraph #7.3.1.4.1 (RA-MODEds)"
            DEFVAL { raInit }
            ::= { hwVOPSNRMarginConfProfEntry 12 }


        hwVOPSNRMarginConfProfRaModeUs OBJECT-TYPE
            SYNTAX Xdsl2RaMode
            MAX-ACCESS read-create
            STATUS current
            DESCRIPTION
                "The mode of operation of a rate-adaptive xTU-R in the transmit direction."
            REFERENCE
                "ITU-T G.997.1, paragraph #7.3.1.4.2 (RA-MODEus)"
            DEFVAL { raInit }
            ::= { hwVOPSNRMarginConfProfEntry 13 }


        hwVOPSNRMarginConfProfRaUsNrmDs OBJECT-TYPE
            SYNTAX Gauge32 (0..310)
            UNITS "0.1 dB"
            MAX-ACCESS read-create
            STATUS current
            DESCRIPTION
                "The Downstream Up-Shift Noise Margin value, to be used when hwVOPSNRMarginConfProfRaModeDs is set to dynamicRa.
                 If the downstream noise margin is above this value, and stays above it for more than the time specified by the
                 hwVOPSNRMarginConfProfUsTimeDs, the xTU-R shall attempt to increase the downstream net data rate.
                 The Downstream Up-Shift Noise Margin ranges from 0 to 310 units of 0.1 dB (Physical values are 0 to 31 dB).
                 Unit: 0.1 dB.
                "
            REFERENCE
                "ITU-T G.997.1, paragraph #7.3.1.4.3 (RA-USNRMds)"
            DEFVAL { 310 }
            ::= { hwVOPSNRMarginConfProfEntry 14 }


        hwVOPSNRMarginConfProfRaUsNrmUs OBJECT-TYPE
            SYNTAX Gauge32 (0..310)
            UNITS "0.1 dB"
            MAX-ACCESS read-create
            STATUS current
            DESCRIPTION
                "The Upstream Up-Shift Noise Margin value, to be used when hwVOPSNRMarginConfProfRaModeUs is set to dynamicRa.
                 If the upstream noise margin is above this value, and stays above it for more than the time specified by the
                 hwVOPSNRMarginConfProfUsTimeUs, the xTU-C shall attempt to increase the upstream net data rate.
                 The Upstream Up-Shift Noise Margin ranges from 0 to 310 units of 0.1 dB (Physical values are 0 to 31 dB).
                 Unit: 0.1 dB.
                "
            REFERENCE
                "ITU-T G.997.1, paragraph #7.3.1.4.4 (RA-USNRMus)"
            DEFVAL { 310 }
            ::= { hwVOPSNRMarginConfProfEntry 15 }


        hwVOPSNRMarginConfProfRaDsNrmDs OBJECT-TYPE
            SYNTAX Gauge32 (0..310)
            UNITS "0.1 dB"
            MAX-ACCESS read-create
            STATUS current
            DESCRIPTION
                "The Downstream Down-Shift Noise Margin value, to be used when hwVOPSNRMarginConfProfRaModeDs is set to dynamicRa.
                 If the downstream noise margin is below this value, and stays below it for more than the time specified by the
                 hwVOPSNRMarginConfProfDsTimeDs, the xTU-R shall attempt to increase the downstream net data rate.
                 The Downstream Down-Shift Noise Margin ranges from 0 to 310 units of 0.1 dB (Physical values are 0 to 31 dB).
                 Unit: 0.1 dB.
                "
            REFERENCE
                "ITU-T G.997.1, paragraph #7.3.1.4.7 (RA-DSNRMds)"
            DEFVAL { 10 }
            ::= { hwVOPSNRMarginConfProfEntry 16 }


        hwVOPSNRMarginConfProfRaDsNrmUs OBJECT-TYPE
            SYNTAX Gauge32 (0..310)
            UNITS "0.1 dB"
            MAX-ACCESS read-create
            STATUS current
            DESCRIPTION
                "The Upstream Down-Shift Noise Margin value, to be used when hwVOPSNRMarginConfProfRaModeUs is set to dynamicRa.
                 If the upstream noise margin is below this value, and stays below it for more than the time specified by the
                 hwVOPSNRMarginConfProfDsTimeUs, the xTU-C shall attempt to increase the upstream net data rate.
                 The Upstream Down-Shift Noise Margin ranges from 0 to 310 units of 0.1 dB (Physical values are 0 to 31 dB).
                 Unit: 0.1 dB.
                "
            REFERENCE
                "ITU-T G.997.1, paragraph #7.3.1.4.8 (RA-DSNRMus)"
            DEFVAL { 10 }
            ::= { hwVOPSNRMarginConfProfEntry 17 }


        hwVOPSNRMarginConfProfUsTimeDs OBJECT-TYPE
            SYNTAX Gauge32 (0..16383)
            UNITS "seconds"
            MAX-ACCESS read-create
            STATUS current
            DESCRIPTION
                "The Downstream Up-Shift Time Interval, to be used when hwVOPSNRMarginConfProfRaModeDs is set to dynamicRa.
                 The interval of time that the downstream noise margin should stay above the Downstream Up-Shift Noise Margin
                 before the xTU-R shall attempt to increase the downstream net data rate.
                 The time interval ranges from 0 to 16383 seconds.
                 Unit: seconds.
                "
            REFERENCE
                "ITU-T G.997.1, paragraph #7.3.1.4.5 (RA-UTIMEds)"
            DEFVAL { 3600 }
            ::= { hwVOPSNRMarginConfProfEntry 18 }


        hwVOPSNRMarginConfProfUsTimeUs OBJECT-TYPE
            SYNTAX Gauge32 (0..16383)
            UNITS "seconds"
            MAX-ACCESS read-create
            STATUS current
            DESCRIPTION
                "The Upstream Up-Shift Time Interval, to be used when hwVOPSNRMarginConfProfRaModeUs is set to dynamicRa.
                 The interval of time the upstream noise margin should stay above the Upstream Up-Shift Noise Margin
                 before the xTU-C shall attempt to increase the upstream net data rate.
                 The time interval ranges from 0 to 16383 seconds.
                 Unit: seconds.
                "
            REFERENCE
                "ITU-T G.997.1, paragraph #7.3.1.4.6 (RA-UTIMEus)"
            DEFVAL { 3600 }
            ::= { hwVOPSNRMarginConfProfEntry 19 }


        hwVOPSNRMarginConfProfDsTimeDs OBJECT-TYPE
            SYNTAX Gauge32 (0..16383)
            UNITS "seconds"
            MAX-ACCESS read-create
            STATUS current
            DESCRIPTION
                "The Downstream Downshift Time Interval, to be used when hwVOPSNRMarginConfProfRaModeDs is set to dynamicRa.
                 The interval of time the downstream noise margin should stay below the Downstream Down-Shift Noise Margin
                 before the xTU-R shall attempt to decrease the downstream net data rate.
                 The time interval ranges from 0 to 16383 seconds.
                 Unit: seconds.
                "
            REFERENCE
                "ITU-T G.997.1, paragraph #7.3.1.4.9 (RA-DTIMEds)"
            DEFVAL { 3600 }
            ::= { hwVOPSNRMarginConfProfEntry 20 }


        hwVOPSNRMarginConfProfDsTimeUs OBJECT-TYPE
            SYNTAX Gauge32 (0..16383)
            UNITS "seconds"
            MAX-ACCESS read-create
            STATUS current
            DESCRIPTION
                "The Upstream Down-Shift Time Interval, to be used when hwVOPSNRMarginConfProfUsTimeUs is set to dynamicRa.
                 The interval of time the upstream noise margin should stay below the Upstream Down-Shift Noise Margin
                 before the xTU-C shall attempt to decrease the upstream net data rate.
                 The time interval ranges from 0 to 16383 seconds.
                 Unit: seconds.
                "
            REFERENCE
                "ITU-T G.997.1, paragraph #7.3.1.4.10 (RA-DTIMEus)"
            DEFVAL { 3600 }
            ::= { hwVOPSNRMarginConfProfEntry 21 }
            
        hwVOPGfastSNRMarginConfProfMinSnrmDs OBJECT-TYPE
            SYNTAX Gauge32 (0..310)
            UNITS "0.1 dB"
            MAX-ACCESS read-create
            STATUS current
            DESCRIPTION
                "The G.fast minimum Noise Margin the xTU-R receiver shall tolerate.
                 If the noise margin falls below this level, the xTU-R shall request that the xTU-C increase
                 the xTU-C transmit power.
                 If an increase of xTU-C transmit power is not possible, a loss-of-margin (LOM) defect occurs,
                 the xTU-R shall fail and attempt to re-initialize and the NMS shall be notified.
                 The minimum noise margin ranges from 0 to 310 units of 0.1 dB (Physical values are 0 to 31 dB).
                 A value of 0 means that there is no minimum.
                 Unit: 0.1 dB.
                "
            REFERENCE
                "ITU-T G.9701, paragraph 12.3.4.2.1"
            DEFVAL { 0 }
            ::= { hwVOPSNRMarginConfProfEntry 22 }


        hwVOPGfastSNRMarginConfProfMinSnrmUs OBJECT-TYPE
            SYNTAX Gauge32 (0..310)
            UNITS "0.1 dB"
            MAX-ACCESS read-create
            STATUS current
            DESCRIPTION
                "The G.fast minimum Noise Margin the xTU-C receiver shall tolerate.
                 If the noise margin falls below this level, the xTU-C shall request that the xTU-R increase
                 the xTU-R transmit power.
                 If an increase of xTU-R transmit power is not possible, a loss-of-margin (LOM) defect occurs,
                 the xTU-C shall fail and attempt to re-initialize and the NMS shall be notified.
                 The minimum noise margin ranges from 0 to 310 units of 0.1 dB (Physical values are 0 to 31 dB).
                 A value of 0 means that there is no minimum.
                 Unit: 0.1 dB.
                "
            REFERENCE
                "ITU-T G.9701, paragraph 12.3.4.2.1"
            DEFVAL { 0 }
            ::= { hwVOPSNRMarginConfProfEntry 23 }


        hwVOPGfastSNRMarginConfProfTargetSnrmDs OBJECT-TYPE
            SYNTAX Gauge32 (0..310)
            UNITS "0.1 dB"
            MAX-ACCESS read-create
            STATUS current
            DESCRIPTION
                "The G.fast minimum Noise Margin the xTU-R receiver shall achieve, relative to the BER requirement, 
                 to successfully complete initialization.
                 The target noise margin ranges from 0 to 310 units of 0.1 dB (Physical values are 0 to 31 dB).
                 Unit: 0.1 dB.
                "
            REFERENCE
                "ITU-T G.9701, paragraph 12.3.3.2.1"
            DEFVAL { 90 }
            ::= { hwVOPSNRMarginConfProfEntry 24 }


        hwVOPGfastSNRMarginConfProfTargetSnrmUs OBJECT-TYPE
            SYNTAX Gauge32 (0..310)
            UNITS "0.1 dB"
            MAX-ACCESS read-create
            STATUS current
            DESCRIPTION
                "The G.fast minimum Noise Margin the xTU-C receiver shall achieve, relative to the BER requirement, 
                 to successfully complete initialization.
                 The target noise margin ranges from 0 to 310 units of 0.1 dB (Physical values are 0 to 31 dB).
                 Unit: 0.1 dB.
                "
            REFERENCE
                "ITU-T G.9701, paragraph 12.3.3.2.1"
            DEFVAL { 90 }
            ::= { hwVOPSNRMarginConfProfEntry 25 }


        hwVOPGfastSNRMarginConfProfMaxSnrmDs OBJECT-TYPE
            SYNTAX Gauge32 (0..310 | 2147483647)
            UNITS "0.1 dB"
            MAX-ACCESS read-create
            STATUS current
            DESCRIPTION
                "The G.fast maximum Noise Margin the xTU-R receiver shall try to sustain.
                 If the Noise Margin is above this level, the xTU-R shall request that the xTU-C reduce
                 the xTU-C transmit power to get a noise margin below this limit (if this functionality is supported).
                 The maximum noise margin ranges from 0 to 310 units of 0.1 dB (Physical values are 0 to 31 dB).
                 A value of 0x7FFFFFFF (2147483647) means that there is no maximum.
                 Unit: 0.1 dB.
                "
            REFERENCE
                "ITU-T G.9701, paragraph 12.3.7"
            DEFVAL { 310 }
            ::= { hwVOPSNRMarginConfProfEntry 26 }


        hwVOPGfastSNRMarginConfProfMaxSnrmUs OBJECT-TYPE
            SYNTAX Gauge32 (0..310 | 2147483647)
            UNITS "0.1 dB"
            MAX-ACCESS read-create
            STATUS current
            DESCRIPTION
                "The G.fast maximum Noise Margin the xTU-C receiver shall try to sustain.
                 If the Noise Margin is above this level, the xTU-C shall request that the xTU-R reduce
                 the xTU-R transmit power to get a noise margin below this limit (if this functionality is supported).
                 The maximum noise margin ranges from 0 to 310 units of 0.1 dB (Physical values are 0 to 31 dB).
                 A value of 0x7FFFFFFF (2147483647) means that there is no maximum.
                 Unit: 0.1 dB.
                "
            REFERENCE
                "ITU-T G.9701, paragraph 12.3.7"
            DEFVAL { 310 }
            ::= { hwVOPSNRMarginConfProfEntry 27 }


        hwVOPGfastSNRMarginConfProfSnrModeDs OBJECT-TYPE
            SYNTAX Xdsl2LineSnrMode
            MAX-ACCESS read-create
            STATUS obsolete
            DESCRIPTION
                "This parameter enables the G.fast transmitter referred virtual noise in the downstream direction.
                 The configuration parameters for virtual noise are in the hwVOPVirtualNoiseConfProfTable.
                "
            REFERENCE
                "ITU-T G.997.1, paragraph #7.3.1.7.1 (SNRMODEds)"
            DEFVAL { virtualNoiseDisabled }
            ::= { hwVOPSNRMarginConfProfEntry 28 }


        hwVOPGfastSNRMarginConfProfSnrModeUs OBJECT-TYPE
            SYNTAX Xdsl2LineSnrMode
            MAX-ACCESS read-create
            STATUS obsolete
            DESCRIPTION
                "This parameter enables the G.fast transmitter referred virtual noise in the upstream direction.
                 The configuration parameters for virtual noise are in the hwVOPVirtualNoiseConfProfTable.
                "
            REFERENCE
                "ITU-T G.997.1, paragraph #7.3.1.7.2 (SNRMODEus)"
            DEFVAL { virtualNoiseDisabled }
            ::= { hwVOPSNRMarginConfProfEntry 29 }


        hwVOPGfastSNRMarginConfProfRaModeDs OBJECT-TYPE
            SYNTAX HWVOPGfastRaMode
            MAX-ACCESS read-create
            STATUS obsolete
            DESCRIPTION
                "The mode of operation of a rate-adaptive xTU-C in the transmit direction.
                 Options:
                 1. manual (1)       - No Rate-Adaptation. The initialization process
                                       attempts to synchronize to a specified rate.
                 2. raInit (2)       - Rate-Adaptation during initialization process only,
                                       which attempts to synchronize to a rate between minimum
                                       and maximum specified values.
                 3. dynamicRa (3)    - Dynamic Rate-Adaptation during initialization process
                                       as well as during Showtime.
                 4. dynamicwithfra(4)- Rate-Adaptation during show time by FRA and SRA.
                                       In this mode, enabling of FRA and SRA is mandatory.
                "
            DEFVAL { dynamicwithfra }
            ::= { hwVOPSNRMarginConfProfEntry 30 }


        hwVOPGfastSNRMarginConfProfRaModeUs OBJECT-TYPE
            SYNTAX HWVOPGfastRaMode
            MAX-ACCESS read-create
            STATUS obsolete
            DESCRIPTION
                "The mode of operation of a rate-adaptive xTU-R in the transmit direction.
                 Options:
                 1. manual (1)       - No Rate-Adaptation. The initialization process
                                       attempts to synchronize to a specified rate.
                 2. raInit (2)       - Rate-Adaptation during initialization process only,
                                       which attempts to synchronize to a rate between minimum
                                       and maximum specified values.
                 3. dynamicRa (3)    - Dynamic Rate-Adaptation during initialization process
                                       as well as during Showtime.
                 4. dynamicwithfra(4)- Rate-Adaptation during show time by FRA and SRA.
                                       In this mode, enabling of FRA and SRA is mandatory.
                "
            DEFVAL { dynamicwithfra }
            ::= { hwVOPSNRMarginConfProfEntry 31 }


        hwVOPGfastSNRMarginConfProfRaUsNrmDs OBJECT-TYPE
            SYNTAX Gauge32 (0..310)
            UNITS "0.1 dB"
            MAX-ACCESS read-create
            STATUS current
            DESCRIPTION
                "The G.fast Downstream Up-Shift Noise Margin value, to be used when hwVOPGfastSNRMarginConfProfRaModeDs is set to dynamicRa.
                 If the downstream noise margin is above this value, and stays above it for more than the time specified by the
                 hwVOPGfastSNRMarginConfProfUsTimeDs, the xTU-R shall attempt to increase the Downstream net data rate.
                 The Downstream Up-Shift Noise Margin ranges from 0 to 310 units of 0.1 dB (Physical values are 0 to 31 dB).
                 Unit: 0.1 dB.
                "
            REFERENCE
                "ITU-T G.9701, paragraph 12.3.4.2.1"
            DEFVAL { 120 }
            ::= { hwVOPSNRMarginConfProfEntry 32 }


        hwVOPGfastSNRMarginConfProfRaUsNrmUs OBJECT-TYPE
            SYNTAX Gauge32 (0..310)
            UNITS "0.1 dB"
            MAX-ACCESS read-create
            STATUS current
            DESCRIPTION
                "The G.fast Upstream Up-Shift Noise Margin value, to be used when hwVOPGfastSNRMarginConfProfRaModeUs is set to dynamicRa.
                 If the upstream noise margin is above this value, and stays above it for more than the time specified by the
                 hwVOPGfastSNRMarginConfProfUsTimeUs, the xTU-C shall attempt to increase the Upstream net data rate.
                 The Upstream Up-Shift Noise Margin ranges from 0 to 310 units of 0.1 dB (Physical values are 0 to 31 dB).
                 Unit: 0.1 dB.
                "
            REFERENCE
                "ITU-T G.9701, paragraph 12.3.4.2.1"
            DEFVAL { 120 }
            ::= { hwVOPSNRMarginConfProfEntry 33 }


        hwVOPGfastSNRMarginConfProfRaDsNrmDs OBJECT-TYPE
            SYNTAX Gauge32 (0..310)
            UNITS "0.1 dB"
            MAX-ACCESS read-create
            STATUS current
            DESCRIPTION
                "The G.fast Downstream Down-Shift Noise Margin value, to be used when hwVOPGfastSNRMarginConfProfRaModeDs is set to dynamicRa.
                 If the downstream noise margin is below this value, and stays below it for more than the time specified by the
                 hwVOPGfastSNRMarginConfProfDsTimeDs, the xTU-R shall attempt to increase the Downstream net data rate.
                 The Downstream Down-Shift Noise Margin ranges from 0 to 310 units of 0.1 dB (Physical values are 0 to 31 dB).
                 Unit: 0.1 dB.
                "
            REFERENCE
                "ITU-T G.9701, paragraph 12.3.4.2.1"
            DEFVAL { 60 }
            ::= { hwVOPSNRMarginConfProfEntry 34 }


        hwVOPGfastSNRMarginConfProfRaDsNrmUs OBJECT-TYPE
            SYNTAX Gauge32 (0..310)
            UNITS "0.1 dB"
            MAX-ACCESS read-create
            STATUS current
            DESCRIPTION
                "The G.fast Upstream Down-Shift Noise Margin value, to be used when hwVOPGfastSNRMarginConfProfRaModeUs is set to dynamicRa.
                 If the upstream noise margin is below this value, and stays below it for more than the time specified by the
                 hwVOPGfastSNRMarginConfProfDsTimeUs, the xTU-C shall attempt to increase the Upstream net data rate.
                 The Upstream Down-Shift Noise Margin ranges from 0 to 310 units of 0.1 dB (Physical values are 0 to 31 dB).
                 Unit: 0.1 dB.
                "
            REFERENCE
                "ITU-T G.997.1, paragraph #7.3.1.4.8 (RA-DSNRMus)"
            DEFVAL { 60 }
            ::= { hwVOPSNRMarginConfProfEntry 35 }


        hwVOPGfastSNRMarginConfProfUsTimeDs OBJECT-TYPE
            SYNTAX Gauge32 (0..16383)
            UNITS "seconds"
            MAX-ACCESS read-create
            STATUS current
            DESCRIPTION
                "The G.fast Downstream Up-Shift Time Interval, to be used when hwVOPGfastSNRMarginConfProfRaModeDs is set to dynamicRa.
                 The interval of time that the downstream noise margin should stay above the Downstream Up-Shift Noise Margin
                 before the xTU-R shall attempt to increase the downstream net data rate.
                 The time interval ranges from 0 to 16383 seconds.
                 Unit: seconds.
                "
            REFERENCE
                "ITU-T G.9701, paragraph 12.3.4.2.1."
            DEFVAL { 8 }
            ::= { hwVOPSNRMarginConfProfEntry 36 }


        hwVOPGfastSNRMarginConfProfUsTimeUs OBJECT-TYPE
            SYNTAX Gauge32 (0..16383)
            UNITS "seconds"
            MAX-ACCESS read-create
            STATUS current
            DESCRIPTION
                "The G.fast Upstream Up-Shift Time Interval, to be used when hwVOPGfastSNRMarginConfProfRaModeUs is set to dynamicRa.
                 The interval of time the upstream noise margin should stay above the Upstream Up-Shift Noise Margin
                 before the xTU-C shall attempt to increase the upstream net data rate.
                 The time interval ranges from 0 to 16383 seconds.
                 Unit: seconds.
                "
            REFERENCE
                "ITU-T G.9701, paragraph 12.3.4.2.1."
            DEFVAL { 8 }
            ::= { hwVOPSNRMarginConfProfEntry 37 }


        hwVOPGfastSNRMarginConfProfDsTimeDs OBJECT-TYPE
            SYNTAX Gauge32 (0..16383)
            UNITS "seconds"
            MAX-ACCESS read-create
            STATUS current
            DESCRIPTION
                "The G.fast Downstream Downshift Time Interval, to be used when hwVOPGfastSNRMarginConfProfRaModeDs is set to dynamicRa.
                 The interval of time the downstream noise margin should stay below the Downstream Down-Shift Noise Margin
                 before the xTU-R shall attempt to decrease the downstream net data rate.
                 The time interval ranges from 0 to 16383 seconds.
                 Unit: seconds.
                "
            REFERENCE
                "ITU-T G.9701, paragraph 12.3.4.2.1."
            DEFVAL { 2}
            ::= { hwVOPSNRMarginConfProfEntry 38 }


        hwVOPGfastSNRMarginConfProfDsTimeUs OBJECT-TYPE
            SYNTAX Gauge32 (0..16383)
            UNITS "seconds"
            MAX-ACCESS read-create
            STATUS current
            DESCRIPTION
                "The Upstream Down-Shift Time Interval, to be used when hwVOPGfastSNRMarginConfProfRaModeUs is set to dynamicRa.
                 The interval of time the upstream noise margin should stay below the Upstream Down-Shift Noise Margin
                 before the xTU-C shall attempt to decrease the upstream net data rate.
                 The time interval ranges from 0 to 16383 seconds.
                 Unit: seconds.
                "
            REFERENCE
                "ITU-T G.9701, paragraph 12.3.4.2.1."
            DEFVAL { 2 }
            ::= { hwVOPSNRMarginConfProfEntry 39 }
            
        hwVOPGfastSNRMarginConfProfTargetSnrmRmcDs OBJECT-TYPE
            SYNTAX Gauge32 (0..310)
            UNITS "0.1 dB"
            MAX-ACCESS read-create
            STATUS current
            DESCRIPTION
                "Defines the downstream RMC noise margin that the FTU-R receiver shall achieve, 
                 relative to the BER requirement, or better, to successfully complete initialization.
                 The target noise margin ranges from 0 to 310 units of 0.1 dB (Physical values are 0 to 31 dB).
                 Unit: 0.1 dB.
                "
            REFERENCE
                "ITU-T G.997.2, paragraph 7.1.6.1"
            DEFVAL { 90 }
            ::= { hwVOPSNRMarginConfProfEntry 40 }
            
        hwVOPGfastSNRMarginConfProfTargetSnrmRmcUs OBJECT-TYPE
            SYNTAX Gauge32 (0..310)
            UNITS "0.1 dB"
            MAX-ACCESS read-create
            STATUS current
            DESCRIPTION
                "Defines the upstream RMC noise margin that the FTU-O receiver shall achieve, 
                 relative to the BER requirement, or better, to successfully complete initialization.
                 The target noise margin ranges from 0 to 310 units of 0.1 dB (Physical values are 0 to 31 dB).
                 Unit: 0.1 dB.
                "
            REFERENCE
                "ITU-T G.997.2, paragraph 7.1.6.2"
            DEFVAL { 90 }
            ::= { hwVOPSNRMarginConfProfEntry 41 }
           
        hwVOPGfastSNRMarginConfProfMinSnrmRmcDs OBJECT-TYPE
            SYNTAX Gauge32 (0..310)
            UNITS "0.1 dB"
            MAX-ACCESS read-create
            STATUS current
            DESCRIPTION
                "Defines the downstream minimum noise margin the FTU-R receiver tolerates for the RMC. 
                 If the downstream RMC noise margin falls below this level, the FTU-R initiates the RPA procedure.
                 The minimum noise margin ranges from 0 to 310 units of 0.1 dB (Physical values are 0 to 31 dB).
                 A value of 0 means that there is no minimum.
                 Unit: 0.1 dB.
                "
            REFERENCE
                "ITU-T G.997.2, paragraph 7.1.6.3"
            DEFVAL { 0 }
            ::= { hwVOPSNRMarginConfProfEntry 42 }
            
        hwVOPGfastSNRMarginConfProfMinSnrmRmcUs OBJECT-TYPE
            SYNTAX Gauge32 (0..310)
            UNITS "0.1 dB"
            MAX-ACCESS read-create
            STATUS current
            DESCRIPTION
                "Defines the upstream minimum noise margin the FTU-O receiver tolerates for the RMC. 
                 If the downstream RMC noise margin falls below this level, the FTU-O initiates the RPA procedure.
                 The minimum noise margin ranges from 0 to 310 units of 0.1 dB (Physical values are 0 to 31 dB).
                 A value of 0 means that there is no minimum.
                 Unit: 0.1 dB.
                "
            REFERENCE
                "ITU-T G.997.2, paragraph 7.1.6.4"
            DEFVAL { 0 }
            ::= { hwVOPSNRMarginConfProfEntry 43 }
            
        hwVOPGfastSNRMarginConfProfMaxBLRmcDs OBJECT-TYPE
            SYNTAX Gauge32 (2..6)
            MAX-ACCESS read-create
            STATUS current
            DESCRIPTION
                "Defines the maximum allowed bit-loading for the downstream RMC sub-carriers.
                "
            REFERENCE
                "ITU-T G.997.2, paragraph 7.1.6.5"
            DEFVAL { 6 }
            ::= { hwVOPSNRMarginConfProfEntry 44 }
            
        hwVOPGfastSNRMarginConfProfMaxBLRmcUs OBJECT-TYPE
            SYNTAX Gauge32 (2..6)
            MAX-ACCESS read-create
            STATUS current
            DESCRIPTION
                "Defines the maximum allowed bit-loading for the upstream RMC sub-carriers.
                "
            REFERENCE
                "ITU-T G.997.2, paragraph 7.1.6.6"
            DEFVAL { 6 }
            ::= { hwVOPSNRMarginConfProfEntry 45 }

        hwVOPINPDelayProfileIndexNext OBJECT-TYPE
            SYNTAX HWVOPProfileIndexOrZeroType
            MAX-ACCESS read-only
            STATUS current
            DESCRIPTION
                "This object contains an appropriate value to be used for hwVOPINPDelayConfProfIndex
                 when creating entries in the hwVOPINPDelayConfProfTableTable.
                 The value '0' indicates that no unassigned entries are available.
                 To obtain the value of hwVOPINPDelayConfProfIndex for a new entry in the table,
                 the manager issues a management protocol retrieval operation.
                 The agent will determine through its local policy when this index value will be made available for reuse.
                "
            ::= { hwVOPProfiles 15 }


        hwVOPINPDelayConfProfTable OBJECT-TYPE
            SYNTAX SEQUENCE OF HWVOPINPDelayConfProfEntry
            MAX-ACCESS not-accessible
            STATUS current
            DESCRIPTION
                "The INP-Delay parameters for each pair of upstream and downstream channels will be in
                 an INP-Delay Profile. To cover all possibilities there will be 4 indices in the vector for
                 INP-Delay Profiles. If less than the maximum number of channels is to be used then the
                 scalars corresponding to non-required channels MUST be set to a null value (0).
                 Entries in this table MUST be maintained in a persistent manner.
                 A default profile with an index of '1' will always exist and its parameters will be set to
                 vendor-specific values, unless otherwise specified in this document.
                 The index of this table is hwVOPINPDelayConfProfIndex.
                "
            REFERENCE
                "Broadband Forum TR-252, paragraph #5.7"
            ::= { hwVOPProfiles 16 }


        hwVOPINPDelayConfProfEntry OBJECT-TYPE
            SYNTAX HWVOPINPDelayConfProfEntry
            MAX-ACCESS not-accessible
            STATUS current
            DESCRIPTION
                "The INP-Delay parameters for each pair of upstream and downstream channels will be in
                 an INP-Delay Profile. To cover all possibilities there will be 4 indices in the vector for
                 INP-Delay Profiles. If less than the maximum number of channels is to be used then the
                 scalars corresponding to non-required channels MUST be set to a null value (0).
                 Entries in this table MUST be maintained in a persistent manner.
                 A default profile with an index of '1' will always exist and its parameters will be set to
                 vendor-specific values, unless otherwise specified in this document.
                 The index of this entry is hwVOPINPDelayConfProfIndex.
                "
            INDEX { hwVOPINPDelayConfProfIndex }
            ::= { hwVOPINPDelayConfProfTable 1 }


        HWVOPINPDelayConfProfEntry ::=
            SEQUENCE {
                hwVOPINPDelayConfProfIndex                    Unsigned32,
                hwVOPINPDelayConfProfRowStatus                RowStatus,
                hwVOPINPDelayConfProfDescription              OCTET STRING,
                hwVOPINPDelayConfProfMinProtectionDs          Xdsl2SymbolProtection,
                hwVOPINPDelayConfProfMinProtection8Ds         Xdsl2SymbolProtection8,
                hwVOPINPDelayConfProfMaxDelayDs               Gauge32,
                hwVOPINPDelayConfProfMinProtectionUs          Xdsl2SymbolProtection,
                hwVOPINPDelayConfProfMinProtection8Us         Xdsl2SymbolProtection8,
                hwVOPINPDelayConfProfMaxDelayUs               Gauge32,
                hwVOPINPDelayConfProfMaxDelayVar              Gauge32,
                hwVOPINPDelayConfProfInitPolicy               Xdsl2ChInitPolicy,
                hwVOPINPDelayConfProfMaxDelayRtxDs            Gauge32,
                hwVOPINPDelayConfProfMaxDelayRtxUs            Gauge32,
                hwVOPINPDelayConfProfMinDelayRtxDs            Gauge32,
                hwVOPINPDelayConfProfMinDelayRtxUs            Gauge32,
                hwVOPINPDelayConfProfMinInpShineRtxDs         Gauge32,
                hwVOPINPDelayConfProfMinInpShineRtxUs         Gauge32,
                hwVOPINPDelayConfProfMinInp8ShineRtxDs        Gauge32,
                hwVOPINPDelayConfProfMinInp8ShineRtxUs        Gauge32,
                hwVOPINPDelayConfProfShineRatioRtxDs          Gauge32,
                hwVOPINPDelayConfProfShineRatioRtxUs          Gauge32,
                hwVOPINPDelayConfProfMinInpReinRtxDs          Gauge32,
                hwVOPINPDelayConfProfMinInpReinRtxUs          Gauge32,
                hwVOPINPDelayConfProfMinInp8ReinRtxDs         Gauge32,
                hwVOPINPDelayConfProfMinInp8ReinRtxUs         Gauge32,
                hwVOPINPDelayConfProfIatReinRtxDs             INTEGER,
                hwVOPINPDelayConfProfIatReinRtxUs             INTEGER,
                hwVOPINPDelayConfProfMaxDelayOctetSplit       Gauge32,
                hwVOPGfastINPDelayConfProfMaxDelayRtxDs       Gauge32,
                hwVOPGfastINPDelayConfProfMaxDelayRtxUs       Gauge32,
                hwVOPGfastINPDelayConfProfMinInpShineRtxDs    Gauge32,
                hwVOPGfastINPDelayConfProfMinInpShineRtxUs    Gauge32,
                hwVOPGfastINPDelayConfProfShineRatioRtxDs     Gauge32,
                hwVOPGfastINPDelayConfProfShineRatioRtxUs     Gauge32,
                hwVOPGfastINPDelayConfProfMinInpReinRtxDs     Gauge32,
                hwVOPGfastINPDelayConfProfMinInpReinRtxUs     Gauge32,
                hwVOPGfastINPDelayConfProfIatReinRtxDs        INTEGER,
                hwVOPGfastINPDelayConfProfIatReinRtxUs        INTEGER,
                hwVOPGfastINPDelayConfProfMinRNRatioRtxDs     Gauge32,
                hwVOPGfastINPDelayConfProfMinRNRatioRtxUs     Gauge32
             }


        hwVOPINPDelayConfProfIndex OBJECT-TYPE
            SYNTAX Unsigned32 (1..4294967295)
            MAX-ACCESS accessible-for-notify
            STATUS current
            DESCRIPTION
                "The hwVOPINPDelayConfProfIndex identifies a row in the hwVOPINPDelayConfProfTable."
            ::= { hwVOPINPDelayConfProfEntry 1 }


        hwVOPINPDelayConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy'
                 or 'notInService'), it MUST be first unreferenced from all associated DSL lines.
                 A row in hwVOPINPDelayConfProfTable is said to be unreferenced when there is no instance of
                 hwVOPActSetupInpDelayProfId1-4 in the hwVOPActSetupTable which refers to the row.
                "
            ::= { hwVOPINPDelayConfProfEntry 2 }


        hwVOPINPDelayConfProfDescription OBJECT-TYPE
            SYNTAX OCTET STRING (SIZE (0..128))
            MAX-ACCESS read-create
            STATUS current
            DESCRIPTION
                "The hwVOPINPDelayConfProfDescription contains an optional human readable description for the profile."
            ::= { hwVOPINPDelayConfProfEntry 3 }


        hwVOPINPDelayConfProfMinProtectionDs OBJECT-TYPE
            SYNTAX Xdsl2SymbolProtection
            UNITS "symbols"
            MAX-ACCESS read-create
            STATUS current
            DESCRIPTION
                "If retransmission is not used in downstream direction, this parameter specifies the minimum impulse noise 
                 protection for the downstream bearer channel if it is transported over DMT symbols with a subcarrier spacing 
                 of 4.3125 kHz. The impulse noise protection is expressed in DMT symbols with a subcarrier spacing of 4.3125 kHz
                 and can take the values 1/2 and any integer from 0 to 16, inclusive.
                 If the xTU does not support the configured INPMIN value,it shall use the nearest supported impulse noise protection 
                 greater than INPMIN.
                 Unit: symbols.
                "
            REFERENCE
                "ITU-T G.997.1, paragraph #7.3.2.3 (INPMINds)"
            DEFVAL { noProtection }
            ::= { hwVOPINPDelayConfProfEntry 4 }


        hwVOPINPDelayConfProfMinProtection8Ds OBJECT-TYPE
            SYNTAX Xdsl2SymbolProtection8
            UNITS "symbols"
            MAX-ACCESS read-create
            STATUS current
            DESCRIPTION
                "If retransmission is not used in downstream direction, this parameter specifies the minimum impulse noise 
                 protection for the downstream bearer channel if it is transported over DMT symbols with a subcarrier spacing 
                 of 8.625 kHz. The impulse noise protection is expressed in DMT symbols with a subcarrier spacing of 8.625 kHz
                 and can take any integer value from 0 to 16, inclusive.
                 Unit: symbols.
                "
            REFERENCE
                "ITU-T G.997.1, paragraph #7.3.2.4 (INPMIN8ds)"
            ::= { hwVOPINPDelayConfProfEntry 5 }

        
        hwVOPINPDelayConfProfMaxDelayDs OBJECT-TYPE
            SYNTAX Gauge32 (0..63 | 255)
            UNITS "milliseconds"
            MAX-ACCESS read-create
            STATUS current
            DESCRIPTION
                "If retransmission is not used in downstream direction, this parameter is the maximum one-way 
                 interleaving delay introduced by the PMS-TC on downstream direction.
                 The xTUs shall choose the S (factor) and D(depth) values such that the actual one-way
                 interleaving delay (Xdsl2ChStatusActDelay - VDSL2-LINE-MIB) is as close as possible to,
                 but less than or equal to hwVOPINPDelayConfProfMaxDelayDs.
                 The delay is coded in ms, with the value 0 indicating no delay bound is being imposed.

                 The delay is coded in ms, with the special values 0, 1 and 255.
                 - The value 0 indicates no delay bound is being imposed.
                 - The value 1 indicates the Fast Latency Path shall be used in the G.992.1 operating mode
                   and S and D shall be selected such that S <= 1 and D = 1 in ITU-T Recs G.992.2, G.992.3
                   and G.992.4 operating modes (G.997.1 special value S1).
                 - The value 255 indicates a delay bound of 1 ms in ITU-T Recs G.993.2 (G.997.1 special value S2).
                 Unit: milliseconds.
                "
            REFERENCE
                "ITU-T G.997.1, paragraph #7.3.2.2 (Maximum interleaving delay)"
            ::= { hwVOPINPDelayConfProfEntry 6 }


        hwVOPINPDelayConfProfMinProtectionUs OBJECT-TYPE
            SYNTAX Xdsl2SymbolProtection
            UNITS "symbols"
            MAX-ACCESS read-create
            STATUS current
            DESCRIPTION
                "If retransmission is not used in upstream direction, this parameter specifies the minimum 
                 impulse noise protection for the upstream bearer channel if it is transported over DMT symbols 
                 with a subcarrier spacing of 4.3125 kHz. The impulse noise protection is expressed in DMT symbols 
                 with a subcarrier spacing of 4.3125 kHz and can take the values 1/2 and any integer from 0 to 16, 
                 inclusive.
                 If the xTU does not support the configured INPMIN value, it shall use the nearest supported impulse 
                 noise protection greater than INPMIN.
                 Unit: symbols.
                "
            REFERENCE
                "ITU-T G.997.1, paragraph #7.3.2.3 (INPMINds)"
            DEFVAL { noProtection }
            ::= { hwVOPINPDelayConfProfEntry 7 }


        hwVOPINPDelayConfProfMinProtection8Us OBJECT-TYPE
            SYNTAX Xdsl2SymbolProtection8
            UNITS "symbols"
            MAX-ACCESS read-create
            STATUS current
            DESCRIPTION
                "If retransmission is not used in upstream direction, this parameter specifies the minimum 
                 impulse noise protection for the upstream bearer channel if it is transported over DMT symbols 
                 with a subcarrier spacing of 8.625 kHz. The impulse noise protection is expressed in DMT symbols 
                 with a subcarrier spacing of 8.625 kHz and can take any integer value from 0 to 16, inclusive.
                 Unit: symbols.
                "
            REFERENCE
                "ITU-T G.997.1, paragraph #7.3.2.4 (INPMIN8ds)"
            ::= { hwVOPINPDelayConfProfEntry 8 }


        hwVOPINPDelayConfProfMaxDelayUs OBJECT-TYPE
            SYNTAX Gauge32 (0..63 | 255)
            UNITS "milliseconds"
            MAX-ACCESS read-create
            STATUS current
            DESCRIPTION
                "If retransmission is not used in upstream direction, this parameter is the maximum one-way 
                 interleaving delay introduced by the PMS-TC on upstream direction.
                 The xTUs shall choose the S (factor) and D(depth) values such that the actual one-way
                 interleaving delay (Xdsl2ChStatusActDelay - VDSL2-LINE-MIB) is as close as possible to,
                 but less than or equal to hwVOPINPDelayConfProfMaxDelayUs.
                 The delay is coded in ms, with the value 0 indicating no delay bound is being imposed.

                 The delay is coded in ms, with the special values 0, 1 and 255.
                 - The value 0 indicates no delay bound is being imposed.
                 - The value 1 indicates the Fast Latency Path shall be used in the G.992.1 operating mode
                   and S and D shall be selected such that S <= 1 and D = 1 in ITU-T Recs G.992.2, G.992.3
                   and G.992.4 operating modes (G.997.1 special value S1).
                 - The value 255 indicates a delay bound of 1 ms in ITU-T Recs G.993.2 (G.997.1 special value S2).
                 Unit: milliseconds.
                "
            REFERENCE
                "ITU-T G.997.1, paragraph #7.3.2.2 (Maximum interleaving delay)"
            ::= { hwVOPINPDelayConfProfEntry 9 }


        hwVOPINPDelayConfProfMaxDelayVar OBJECT-TYPE
            SYNTAX Gauge32 (1..255)
            UNITS "0.1 milliseconds"
            MAX-ACCESS read-create
            STATUS current
            DESCRIPTION
                "This optional VDSL2 specific parameter specifies the maximum value
                 for the delay variation allowed in an OLR procedure.
                 It is ranges from 1 to 254 units of 0.1 milliseconds (i.e., 0.1 to 25.4 milliseconds)
                 with the special value 255 which indicates that no delay variation bound is imposed.
                 Unit: 0.1 milliseconds.
                "
            REFERENCE
                "ITU-T G.997.1 Amendment 1, paragraph #7.3.2.9 (DVMAX)"
            DEFVAL { 255 }
            ::= { hwVOPINPDelayConfProfEntry 10 }


        hwVOPINPDelayConfProfInitPolicy OBJECT-TYPE
            SYNTAX Xdsl2ChInitPolicy
            MAX-ACCESS read-create
            STATUS current
            DESCRIPTION
                "If retransmission is not used in a given transmit direction, this parameter indicates
                 which policy shall be applied to determine the transceiver configuration parameters at 
                 initialization. The valid values for CIPOLICY are 0,1 and 2. 
                 Those policies are defined in the respective Recommendations.
                "
            REFERENCE
                "ITU-T G.997.1 Amendment 1, paragraph #7.3.2.10 (CIPOLICY)"
            DEFVAL { policy0 }
            ::= { hwVOPINPDelayConfProfEntry 11 }

        hwVOPINPDelayConfProfMaxDelayRtxDs  OBJECT-TYPE
            SYNTAX      Gauge32 (1..63)
            UNITS       "milliseconds"
            MAX-ACCESS  read-create
            STATUS      current
            DESCRIPTION
               "If retransmission is used in downstream direction, this parameter specifies 
                the maximum for the instantaneous delay due to the effect of retransmission only 
                (see G.998.4 for detailed specification). The delay ranges from 1 to 63 ms by steps of 1 ms. 
                Unit: milliseconds
               "
            REFERENCE    "ITU-T G.997.1, paragraph 7.3.2.11"
            ::= { hwVOPINPDelayConfProfEntry 12 }   

        hwVOPINPDelayConfProfMaxDelayRtxUs  OBJECT-TYPE
            SYNTAX      Gauge32 (1..63)
            UNITS       "milliseconds"
            MAX-ACCESS  read-create
            STATUS      current
            DESCRIPTION
               "If retransmission is used in upstream direction, this parameter specifies 
                the maximum for the instantaneous delay due to the effect of retransmission only 
                (see G.998.4 for detailed specification). The delay ranges from 1 to 63 ms by steps of 1 ms. 
                Unit: milliseconds
               "
            REFERENCE    "ITU-T G.997.1, paragraph 7.3.2.11"
            ::= { hwVOPINPDelayConfProfEntry 13 }   

        hwVOPINPDelayConfProfMinDelayRtxDs  OBJECT-TYPE
            SYNTAX      Gauge32 (0..63)
            UNITS       "milliseconds"
            MAX-ACCESS  read-create
            STATUS      current
            DESCRIPTION
               "If retransmission is used in downstream direction, this parameter specifies 
                the minimum for the instantaneous delay due to the effect of retransmission only 
                (see G.998.4 for detailed specification). The delay ranges from 0 to 63 ms by steps of 1 ms. 
                Unit: milliseconds
               "
            REFERENCE    "ITU-T G.997.1, paragraph 7.3.2.12"
            ::= { hwVOPINPDelayConfProfEntry 14 }   

        hwVOPINPDelayConfProfMinDelayRtxUs  OBJECT-TYPE
            SYNTAX      Gauge32 (0..63)
            UNITS       "milliseconds"
            MAX-ACCESS  read-create
            STATUS      current
            DESCRIPTION
               "If retransmission is used in upstream direction, this parameter specifies 
                the minimum for the instantaneous delay due to the effect of retransmission only 
                (see G.998.4 for detailed specification). The delay ranges from 0 to 63 ms by steps of 1 ms. 
                Unit: milliseconds
               "
            REFERENCE    "ITU-T G.997.1, paragraph 7.3.2.12"
            ::= { hwVOPINPDelayConfProfEntry 15 } 

        hwVOPINPDelayConfProfMinInpShineRtxDs  OBJECT-TYPE
            SYNTAX      Gauge32 (0..63)
            UNITS       "symbols"
            MAX-ACCESS  read-create
            STATUS      current
            DESCRIPTION
               "If retransmission is used in downstream direction, this parameter specifies 
                the minimum impulse noise protection against SHINE for the bearer channel if it is 
                transported over DMT symbols with a subcarrier spacing of 4.3125 kHz. The impulse 
                noise protection is expressed in DMT symbols with a subcarrier spacing of 4.3125 kHz 
                and can take any integer value from 0 to 63, inclusive.
                Unit: symbols
               "
            REFERENCE    "ITU-T G.997.1, paragraph 7.3.2.13"
            DEFVAL       { 0 }
            ::= { hwVOPINPDelayConfProfEntry 16 } 

        hwVOPINPDelayConfProfMinInpShineRtxUs  OBJECT-TYPE
            SYNTAX      Gauge32 (0..63)
            UNITS       "symbols"
            MAX-ACCESS  read-create
            STATUS      current
            DESCRIPTION
               "If retransmission is used in upstream direction, this parameter specifies the 
                minimum impulse noise protection against SHINE for the bearer channel if it is 
                transported over DMT symbols with a subcarrier spacing of 4.3125 kHz. The impulse 
                noise protection is expressed in DMT symbols with a subcarrier spacing of 4.3125 kHz 
                and can take any integer value from 0 to 63, inclusive.
                Unit: symbols
               "
            REFERENCE    "ITU-T G.997.1, paragraph 7.3.2.13"
            DEFVAL       { 0 }
            ::= { hwVOPINPDelayConfProfEntry 17 } 

        hwVOPINPDelayConfProfMinInp8ShineRtxDs  OBJECT-TYPE
            SYNTAX      Gauge32 (0..127)
            UNITS       "symbols"
            MAX-ACCESS  read-create
            STATUS      current
            DESCRIPTION
               "If retransmission is used in downstream direction, this parameter specifies 
                the minimum impulse noise protection against SHINE for the bearer channel if it is 
                transported over DMT symbols with a subcarrier spacing of 8.625 kHz. The impulse 
                noise protection is expressed in DMT symbols with a subcarrier spacing of 8.625 kHz 
                and can take any integer value from 0 to 127, inclusive.
                Unit: symbols
               "
            REFERENCE    "ITU-T G.997.1, paragraph 7.3.2.14"
            DEFVAL       { 0 }
            ::= { hwVOPINPDelayConfProfEntry 18 } 

        hwVOPINPDelayConfProfMinInp8ShineRtxUs  OBJECT-TYPE
            SYNTAX      Gauge32 (0..127)
            UNITS       "symbols"
            MAX-ACCESS  read-create
            STATUS      current
            DESCRIPTION
               "If retransmission is used in upstream direction, this parameter specifies the 
                minimum impulse noise protection against SHINE for the bearer channel if it is 
                transported over DMT symbols with a subcarrier spacing of 8.625 kHz. The impulse 
                noise protection is expressed in DMT symbols with a subcarrier spacing of 8.625 kHz 
                and can take any integer value from 0 to 127, inclusive.
                Unit: symbols
               "
            REFERENCE    "ITU-T G.997.1, paragraph 7.3.2.14"
            DEFVAL       { 0 }
            ::= { hwVOPINPDelayConfProfEntry 19 } 

        hwVOPINPDelayConfProfShineRatioRtxDs  OBJECT-TYPE
            SYNTAX      Gauge32 (0..100)
            MAX-ACCESS  read-create
            STATUS      current
            DESCRIPTION
               "If retransmission is used in downstream direction, this parameter specifies 
                the SHINE ratio (detailed definition see G.998.4).
                The values range from 0 to 0.100 in increments of 0.001.
               "
            REFERENCE    "ITU-T G.997.1, paragraph 7.3.2.15"
            DEFVAL       { 0 }
            ::= { hwVOPINPDelayConfProfEntry 20 } 

        hwVOPINPDelayConfProfShineRatioRtxUs  OBJECT-TYPE
            SYNTAX      Gauge32 (0..100)
            MAX-ACCESS  read-create
            STATUS      current
            DESCRIPTION
               "If retransmission is used in upstream direction, this parameter specifies 
                the SHINE ratio (detailed definition see G.998.4).
                The values range from 0 to 0.100 in increments of 0.001.
               "
            REFERENCE    "ITU-T G.997.1, paragraph 7.3.2.15"
            DEFVAL       { 0 }
            ::= { hwVOPINPDelayConfProfEntry 21 } 
            
        hwVOPINPDelayConfProfMinInpReinRtxDs  OBJECT-TYPE
            SYNTAX      Gauge32 (0..7)
            MAX-ACCESS  read-create
            STATUS      current
            DESCRIPTION
               "If retransmission is used in downstream direction, this parameter specifies 
                the minimum impulse noise protection against REIN for the bearer channel if it is 
                transported over DMT symbols with a subcarrier spacing of 4.3125 kHz. The impulse 
                noise protection is expressed in DMT symbols with a subcarrier spacing of 4.3125 kHz 
                and can take any integer value from 0 to 7, inclusive.
               "
            REFERENCE    "ITU-T G.997.1, paragraph 7.3.2.16"
            DEFVAL       { 0 }
            ::= { hwVOPINPDelayConfProfEntry 22 }             
            
        hwVOPINPDelayConfProfMinInpReinRtxUs  OBJECT-TYPE
            SYNTAX      Gauge32 (0..7)
            MAX-ACCESS  read-create
            STATUS      current
            DESCRIPTION
               "If retransmission is used in upstream direction, this parameter specifies 
                the minimum impulse noise protection against REIN for the bearer channel if it is 
                transported over DMT symbols with a subcarrier spacing of 4.3125 kHz. The impulse 
                noise protection is expressed in DMT symbols with a subcarrier spacing of 4.3125 kHz 
                and can take any integer value from 0 to 7, inclusive.
               "
            REFERENCE    "ITU-T G.997.1, paragraph 7.3.2.16"
            DEFVAL       { 0 }
            ::= { hwVOPINPDelayConfProfEntry 23 }   
            
        hwVOPINPDelayConfProfMinInp8ReinRtxDs  OBJECT-TYPE
            SYNTAX      Gauge32 (0..13)
            MAX-ACCESS  read-create
            STATUS      current
            DESCRIPTION
               "If retransmission is used in downstream direction, this parameter specifies 
                the minimum impulse noise protection against REIN for the bearer channel if it is 
                transported over DMT symbols with a subcarrier spacing of 8.625 kHz. The impulse 
                noise protection is expressed in DMT symbols with a subcarrier spacing of 8.625 kHz 
                and can take any integer value from 0 to 13, inclusive.
               "
            REFERENCE    "ITU-T G.997.1, paragraph 7.3.2.17"
            DEFVAL       { 0 }
            ::= { hwVOPINPDelayConfProfEntry 24 }             
            
        hwVOPINPDelayConfProfMinInp8ReinRtxUs  OBJECT-TYPE
            SYNTAX      Gauge32 (0..13)
            MAX-ACCESS  read-create
            STATUS      current
            DESCRIPTION
               "If retransmission is used in upstream direction, this parameter specifies 
                the minimum impulse noise protection against REIN for the bearer channel if it is 
                transported over DMT symbols with a subcarrier spacing of 8.625 kHz. The impulse 
                noise protection is expressed in DMT symbols with a subcarrier spacing of 8.625 kHz 
                and can take any integer value from 0 to 13, inclusive.
               "
            REFERENCE    "ITU-T G.997.1, paragraph 7.3.2.17"
            DEFVAL       { 0 }
            ::= { hwVOPINPDelayConfProfEntry 25 }        
            
        hwVOPINPDelayConfProfIatReinRtxDs  OBJECT-TYPE
            SYNTAX      INTEGER
                        {       
                         frequency100Hz(0),
                         frequency120Hz(1)
                        }
            MAX-ACCESS  read-create
            STATUS      current
            DESCRIPTION
               "If retransmission is used in downstream direction, this parameter specifies 
                the inter-arrival time that shall be assumed for REIN protection.
                Options:
                 1. frequency100Hz(0)  - an inter-arrival time derived from a REIN at 100 Hz
                 2. frequency120Hz(1)  - an inter-arrival time derived from a REIN at 120 Hz
               "
            REFERENCE    "ITU-T G.997.1, paragraph 7.3.2.18"
            DEFVAL       { frequency100Hz }
            ::= { hwVOPINPDelayConfProfEntry 26 }               
            
        hwVOPINPDelayConfProfIatReinRtxUs  OBJECT-TYPE
            SYNTAX      INTEGER
                        {       
                         frequency100Hz(0),
                         frequency120Hz(1)
                        }
            MAX-ACCESS  read-create
            STATUS      current
            DESCRIPTION
               "If retransmission is used in upstream direction, this parameter specifies 
                the inter-arrival time that shall be assumed for REIN protection.
                Options:
                 1. frequency100Hz(0)   - an inter-arrival time derived from a REIN at 100 Hz
                 2. frequency120Hz(1)   - an inter-arrival time derived from a REIN at 120 Hz
               "
            REFERENCE    "ITU-T G.997.1, paragraph 7.3.2.18"
            DEFVAL       { frequency100Hz }
            ::= { hwVOPINPDelayConfProfEntry 27 } 
        
	hwVOPINPDelayConfProfMaxDelayOctetSplit  OBJECT-TYPE
            SYNTAX Gauge32 (0..100 | 255)
            UNITS "percents"
            MAX-ACCESS read-create
            STATUS current
            DESCRIPTION
                "The line configuration parameter MAXDELAYOCTET-split (MDOSPLIT) defines the percentage of the MAXDELAYOCTET_ext 
                 if operating in ITU-T G.998.4 or MAXDELAYOCTET in other cases allocated to the downstream direction. All of the remaining 
                 MAXDELAYOCTET or MAXDELAYOCTET_ext shall be allocated for use in the upstream direction. 
                 The detailed specification is in ITU-T G.993.2 and ITU-T G.998.4.
                 MDOSPLIT shall be expressed as a percentage, with valid range from 5 percent to 95 percent inclusive, in steps of 1 percent. 
                 The value 0% is valid only if the maximum downstream interleaving delay is configured with the special value S1 (see clause 7.3.2.2) 
                 and retransmission is disabled in the downstream direction. The value 100% is valid only if the maximum upstream interleaving delay 
                 is configured with the special value S1 (see clause 7.3.2.2) and retransmission is disabled in the upstream direction. 
                 A special value (255) shall indicate that the VTU-O is allowed to use a vendor discretionary algorithm.
                 NOTE - The special value is introduced to ensure backwards compatibility.
                "
            REFERENCE
                "ITU-T G.997.1, paragraph #7.3.1.14"
            DEFVAL { 255 }
            ::= { hwVOPINPDelayConfProfEntry 28 }
            
        hwVOPGfastINPDelayConfProfMaxDelayRtxDs OBJECT-TYPE
            SYNTAX Gauge32 (4..252)
            UNITS "0.25 milliseconds"
            MAX-ACCESS read-create
            STATUS current
            DESCRIPTION
                "This parameter specifies the G.fast downstream maximum allowed delay for retransmission.
                 The delay values range from 1 to 63 ms in steps of 0.25 ms.
                 Unit: 0.25 milliseconds.
                "
            REFERENCE
                "ITU-T G.9701, paragraph 11.4.2.4"
            DEFVAL { 40 }    
            ::= { hwVOPINPDelayConfProfEntry 29 }
            
        hwVOPGfastINPDelayConfProfMaxDelayRtxUs OBJECT-TYPE
            SYNTAX Gauge32 (4..252)
            UNITS "0.25 milliseconds"
            MAX-ACCESS read-create
            STATUS current
            DESCRIPTION
                "This parameter specifies the G.fast upstream maximum allowed delay for retransmission.
                 The delay values range from 1 to 63 ms in steps of 0.25 ms.
                 Unit: 0.25 milliseconds.
                "
            REFERENCE
                "ITU-T G.9701, paragraph 11.4.2.4"
            DEFVAL { 40 }                    
            ::= { hwVOPINPDelayConfProfEntry 30 }
            
        hwVOPGfastINPDelayConfProfMinInpShineRtxDs  OBJECT-TYPE
            SYNTAX      Gauge32 (0..520)
            UNITS       "symbols"
            MAX-ACCESS  read-create
            STATUS      current
            DESCRIPTION
               "This parameter specifies the G.fast downstream minimum impulse noise protection against SHINE for the bearer channel 
                if it is transported over DMT symbols with a subcarrier spacing of 51.75 kHz. 
                The impulse noise protection is expressed in DMT symbols with a subcarrier spacing of 51.75 kHz 
                and can take any integer value from 0 to 520, inclusive.
                Unit: symbols
               "
            REFERENCE    "ITU-T G.9701, paragraph 11.4.2.6"
            DEFVAL       { 0 }
            ::= { hwVOPINPDelayConfProfEntry 31 } 

        hwVOPGfastINPDelayConfProfMinInpShineRtxUs  OBJECT-TYPE
            SYNTAX      Gauge32 (0..520)
            UNITS       "symbols"
            MAX-ACCESS  read-create
            STATUS      current
            DESCRIPTION
               "This parameter specifies the G.fast upstream minimum impulse noise protection against SHINE for the bearer channel 
                if it is transported over DMT symbols with a subcarrier spacing of 51.75 kHz. 
                The impulse noise protection is expressed in DMT symbols with a subcarrier spacing of 51.75 kHz 
                and can take any integer value from 0 to 520, inclusive.
                Unit: symbols
               "
            REFERENCE    "ITU-T G.9701, paragraph 11.4.2.6"
            DEFVAL       { 0 }
            ::= { hwVOPINPDelayConfProfEntry 32 }
            
        hwVOPGfastINPDelayConfProfShineRatioRtxDs  OBJECT-TYPE
            SYNTAX      Gauge32 (0..100)
            MAX-ACCESS  read-create
            STATUS      current
            DESCRIPTION
               "This parameter specifies the G.fast downstream SHINE ratio.
                The values range from 0 to 0.1 in increments of 0.001.
               "
            REFERENCE    "ITU-T G.9701, paragraph 11.4.2.7"
            DEFVAL       { 0 }
            ::= { hwVOPINPDelayConfProfEntry 33 } 

        hwVOPGfastINPDelayConfProfShineRatioRtxUs  OBJECT-TYPE
            SYNTAX      Gauge32 (0..100)
            MAX-ACCESS  read-create
            STATUS      current
            DESCRIPTION
               "This parameter specifies the G.fast upstream SHINE ratio.
                The values range from 0 to 0.1 in increments of 0.001.
               "
            REFERENCE    "ITU-T G.9701, paragraph 11.4.2.7"
            DEFVAL       { 0 }
            ::= { hwVOPINPDelayConfProfEntry 34 } 
            
        hwVOPGfastINPDelayConfProfMinInpReinRtxDs  OBJECT-TYPE
            SYNTAX      Gauge32 (0..63)
            MAX-ACCESS  read-create
            STATUS      current
            DESCRIPTION
               "This parameter specifies the G.fast downstream minimum impulse noise protection against REIN for the bearer channel 
                if it is transported over DMT symbols with a subcarrier spacing of 51.75 kHz. 
                The impulse noise protection is expressed in DMT symbols with a subcarrier spacing of 51.75 kHz 
                and can take any integer value from 0 to 63, inclusive.
               "
            REFERENCE    "ITU-T G.9701, paragraph 11.4.2.8"
            DEFVAL       { 0 }
            ::= { hwVOPINPDelayConfProfEntry 35 }             
            
        hwVOPGfastINPDelayConfProfMinInpReinRtxUs  OBJECT-TYPE
            SYNTAX      Gauge32 (0..63)
            MAX-ACCESS  read-create
            STATUS      current
            DESCRIPTION
               "This parameter specifies the G.fast upstream minimum impulse noise protection against REIN for the bearer channel 
                if it is transported over DMT symbols with a subcarrier spacing of 51.75 kHz. 
                The impulse noise protection is expressed in DMT symbols with a subcarrier spacing of 51.75 kHz 
                and can take any integer value from 0 to 63, inclusive.
               "
            REFERENCE    "ITU-T G.9701, paragraph 11.4.2.8"
            DEFVAL       { 0 }
            ::= { hwVOPINPDelayConfProfEntry 36 } 
            
        hwVOPGfastINPDelayConfProfIatReinRtxDs  OBJECT-TYPE
            SYNTAX      INTEGER
                        {       
                         frequency100Hz(0),
                         frequency120Hz(1),
                         frequency300Hz(2),
                         frequency360Hz(3)
                        }
            MAX-ACCESS  read-create
            STATUS      current
            DESCRIPTION
               "This parameter specifies the G.fast downstream inter-arrival time that shall be assumed for REIN protection.
                Options:
                 1. frequency100Hz(0)  - an inter-arrival time derived from a REIN at 100 Hz
                 2. frequency120Hz(1)  - an inter-arrival time derived from a REIN at 120 Hz
                 3. frequency300Hz(2)  - an inter-arrival time derived from a REIN at 300 Hz
                 4. frequency360Hz(3)  - an inter-arrival time derived from a REIN at 360 Hz
               "
            REFERENCE    "ITU-T G.9701, paragraph 11.4.2.9"
            DEFVAL       { frequency100Hz }
            ::= { hwVOPINPDelayConfProfEntry 37 }               
            
        hwVOPGfastINPDelayConfProfIatReinRtxUs  OBJECT-TYPE
            SYNTAX      INTEGER
                        {       
                         frequency100Hz(0),
                         frequency120Hz(1),
                         frequency300Hz(2),
                         frequency360Hz(3)
                        }
            MAX-ACCESS  read-create
            STATUS      current
            DESCRIPTION
               "This parameter specifies the G.fast upstream inter-arrival time that shall be assumed for REIN protection.
                Options:
                 1. frequency100Hz(0)  - an inter-arrival time derived from a REIN at 100 Hz
                 2. frequency120Hz(1)  - an inter-arrival time derived from a REIN at 120 Hz
                 3. frequency300Hz(2)  - an inter-arrival time derived from a REIN at 300 Hz
                 4. frequency360Hz(3)  - an inter-arrival time derived from a REIN at 360 Hz
               "
            REFERENCE    "ITU-T G.9701, paragraph 11.4.2.9"
            DEFVAL       { frequency100Hz }
            ::= { hwVOPINPDelayConfProfEntry 38 } 
            
        hwVOPGfastINPDelayConfProfMinRNRatioRtxDs  OBJECT-TYPE
            SYNTAX      Gauge32 (0..8)
            MAX-ACCESS  read-create
            STATUS      current
            DESCRIPTION
               "This parameter specifies the G.fast downstream minimum Reed-Solomon RFEC/NFEC ratio. 
                The ratio is computed as the number of redundancy bytes (RFEC) divided by the total 
                number of bytes (NFEC) in each Reed-Solomon codeword.
                The values range from 0 to 8/32 in steps of 1/32.
                Unit: 1/32
               "
            REFERENCE    "ITU-T G.9701, paragraph 11.4.2.11"
            DEFVAL       { 0 }
            ::= { hwVOPINPDelayConfProfEntry 39 }             
            
        hwVOPGfastINPDelayConfProfMinRNRatioRtxUs  OBJECT-TYPE
            SYNTAX      Gauge32 (0..8)
            MAX-ACCESS  read-create
            STATUS      current
            DESCRIPTION
               "This parameter specifies the G.fast upstream minimum Reed-Solomon RFEC/NFEC ratio.
                The ratio is computed as the number of redundancy bytes (RFEC) divided by the total 
                number of bytes (NFEC) in each Reed-Solomon codeword. 
                The values range from 0 to 8/32 in steps of 1/32.
                Unit: 1/32
               "
            REFERENCE    "ITU-T G.9701, paragraph 11.4.2.11"
            DEFVAL       { 0 }
            ::= { hwVOPINPDelayConfProfEntry 40 }                                                                                     

        hwVOPVirtualNoiseProfileIndexNext OBJECT-TYPE
            SYNTAX HWVOPProfileIndexOrZeroType
            MAX-ACCESS read-only
            STATUS current
            DESCRIPTION
                "This object contains an appropriate value to be used for hwVOPVirtualNoiseConfProfIndex
                 when creating entries in the hwVOPVirtualNoiseConfProfTable.

                 The value '0' indicates that no unassigned entries are available.
                 To obtain the value of hwVOPVirtualNoiseConfProfIndex for a new entry in the table,
                 the manager issues a management protocol retrieval operation.
                 The agent will determine through its local policy when this index value will be made available for reuse.
                "
            ::= { hwVOPProfiles 17 }


        hwVOPVirtualNoiseConfProfTable OBJECT-TYPE
            SYNTAX SEQUENCE OF HWVOPVirtualNoiseConfProfEntry
            MAX-ACCESS not-accessible
            STATUS current
            DESCRIPTION
                "The Virtual Noise Profile MUST contain the virtual noise PSDs.
                 A Virtual Noise PSD is not used if the corresponding SNRMODE parameters (hwVOPSNRMarginConfProfMaxSnrmDs,
                 hwVOPSNRMarginConfProfRaModeUs) are set to 0.
                 The SNRMODE parameters for upstream and downstream are in the hwVOPSNRMarginConfProfTable.
                 Entries in this table MUST be maintained in a persistent manner.
                 A default profile with an index of '1' will always exist and its parameters will be set to
                 vendor-specific values, unless otherwise specified in this document.
                 The index of this table is hwVOPVirtualNoiseConfProfIndex.
                "
            REFERENCE
                "Broadband Forum TR-252, paragraph #5.7"
            ::= { hwVOPProfiles 18 }


        hwVOPVirtualNoiseConfProfEntry OBJECT-TYPE
            SYNTAX HWVOPVirtualNoiseConfProfEntry
            MAX-ACCESS not-accessible
            STATUS current
            DESCRIPTION
                "The Virtual Noise Profile MUST contain the virtual noise PSDs.
                 A Virtual Noise PSD is not used if the corresponding SNRMODE parameters (hwVOPSNRMarginConfProfMaxSnrmDs,
                 hwVOPSNRMarginConfProfRaModeUs) are set to 0.
                 The SNRMODE parameters for upstream and downstream are in the hwVOPSNRMarginConfProfTable.
                 Entries in this table MUST be maintained in a persistent manner.
                 A default profile with an index of '1' will always exist and its parameters will be set to
                 vendor-specific values, unless otherwise specified in this document.
                 The index of this entry is hwVOPVirtualNoiseConfProfIndex.
                "
            INDEX { hwVOPVirtualNoiseConfProfIndex }
            ::= { hwVOPVirtualNoiseConfProfTable 1 }


        HWVOPVirtualNoiseConfProfEntry ::=
            SEQUENCE {
                hwVOPVirtualNoiseConfProfIndex                        Unsigned32,
                hwVOPVirtualNoiseConfProfRowStatus                    RowStatus,
                hwVOPVirtualNoiseConfProfDescription                  OCTET STRING,
                hwVOPVirtualNoiseConfProfTxRefVnDs                    Xdsl2LineTxRefVnDs,
                hwVOPVirtualNoiseConfProfTxRefVnUs                    Xdsl2LineTxRefVnUs
             }


        hwVOPVirtualNoiseConfProfIndex OBJECT-TYPE
            SYNTAX Unsigned32 (1..4294967295)
            MAX-ACCESS accessible-for-notify
            STATUS current
            DESCRIPTION
                "The hwVOPVirtualNoiseConfProfIndex identifies a row in the hwVOPVirtualNoiseConfProfTable."
            ::= { hwVOPVirtualNoiseConfProfEntry 1 }


        hwVOPVirtualNoiseConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy'
                 or 'notInService'), it MUST be first unreferenced from all associated DSL lines.

                 A row in hwVOPVirtualNoiseConfProfTable is said to be unreferenced when there is no instance of
                 hwVOPActSetupVNoiseProfId in the hwVOPActSetupTable which refers to the row.
                "
            ::= { hwVOPVirtualNoiseConfProfEntry 2 }


        hwVOPVirtualNoiseConfProfDescription OBJECT-TYPE
            SYNTAX OCTET STRING (SIZE (0..128))
            MAX-ACCESS read-create
            STATUS current
            DESCRIPTION
                "The hwVOPVirtualNoiseConfProfDescription contains an optional human readable description for the profile."
            ::= { hwVOPVirtualNoiseConfProfEntry 3 }


        hwVOPVirtualNoiseConfProfTxRefVnDs OBJECT-TYPE
            SYNTAX Xdsl2LineTxRefVnDs
            MAX-ACCESS read-create
            STATUS current
            DESCRIPTION
                "This configuration parameter defines the downstream transmitter referred virtual noise.
                 The TXREFVNds shall be specified through a set of breakpoints.
                 Each breakpoint shall consist of a subcarrier index t, with a subcarrier spacing of 4.3125 kHz,
                 and a noise PSD level (expressed in dBm/Hz) at that subcarrier.
                 The set of breakpoints can then be represented as: [(t1,PSD1), (t2, PSD2), ... , (tN, PSDN)].
                 32 groups can be configured at most, and 3 bytes for each group. The first two bytes represent tone index,
                 the 3th byte represents the configured PSD value. The relation between configured PSD value and real PSD 
                 value is: REAL PSD = (CONFIGURED PSD + 80) * (-0.5dBm/Hz).
                "
            REFERENCE
                "ITU-T G.997.1, paragraph #7.3.1.7.3 (TXREFVNds)"
            ::= { hwVOPVirtualNoiseConfProfEntry 4 }


        hwVOPVirtualNoiseConfProfTxRefVnUs OBJECT-TYPE
            SYNTAX Xdsl2LineTxRefVnUs
            MAX-ACCESS read-create
            STATUS current
            DESCRIPTION
                "This configuration parameter defines the upstream transmitter referred virtual noise.
                 The TXREFVNus shall be specified through a set of breakpoints.
                 Each breakpoint shall consist of a subcarrier index t, with a subcarrier spacing of 4.3125 kHz,
                 and a noise PSD level (expressed in dBm/Hz) at that subcarrier.
                 The set of breakpoints can then be represented as: [(t1, PSD1), (t2, PSD2), ... , (tN, PSDN)].
                 16 groups can be configured at most, and 3 bytes for each group. The first two bytes represent tone index,
                 the 3th byte represents the configured PSD value. The relation between configured PSD value and real PSD 
                 value is: REAL PSD = (CONFIGURED PSD + 80) * (-0.5dBm/Hz).
                "
            REFERENCE
                "ITU-T G.997.1, paragraph #7.3.1.7.4 (TXREFVNus)"
            ::= { hwVOPVirtualNoiseConfProfEntry 5 }

        hwVOPINMProfileIndexNext OBJECT-TYPE
            SYNTAX HWVOPProfileIndexOrZeroType
            MAX-ACCESS read-only
            STATUS current
            DESCRIPTION
                "This object contains an appropriate value to be used for hwVOPINMConfProfIndex
                 when creating entries in the hwVOPINMConfProfTable.

                 The value '0' indicates that no unassigned entries are available.
                 To obtain the value of hwVOPINMConfProfIndex for a new entry in the table,
                 the manager issues a management protocol retrieval operation.
                 The agent will determine through its local policy when this index value will be made available for reuse.
                "
            ::= { hwVOPProfiles 19 } 
 
        hwVOPINMConfProfTable OBJECT-TYPE
            SYNTAX SEQUENCE OF HWVOPINMConfProfEntry
            MAX-ACCESS not-accessible
            STATUS current
            DESCRIPTION
                "Impulse Noise Monitoring(INM) is not required for modem operation but is a capability for
                 the measurement of Impulse Noise. The INM Profile includes the option to control an INM
                 function on the receive direction in the xTU. A downstream Impulse Noise Monitor applies
                 to the xTU-R; an upstream Impulse Noise Monitor applies to the xTU-C.
                 If INM is not implemented, the relevant profile pointer within the xDSL Line Configuration
                 Vector instance MUST be set to a null value(0).
                 A default profile with an index of '1' will always exist and its parameters will be set to
                 vendor-specific values, unless otherwise specified in this document.
                 The index of this table is hwVOPINMConfProfIndex.
                "
            REFERENCE
                "Broadband Forum TR-252, paragraph #5.7"
            ::= { hwVOPProfiles 20 }

        hwVOPINMConfProfEntry OBJECT-TYPE
            SYNTAX HWVOPINMConfProfEntry
            MAX-ACCESS not-accessible
            STATUS current
            DESCRIPTION
                "Impulse Noise Monitoring(INM) is not required for modem operation but is a capability for
                 the measurement of Impulse Noise. The INM Profile includes the option to control an INM
                 function on the receive direction in the xTU. A downstream Impulse Noise Monitor applies
                 to the xTU-R; an upstream Impulse Noise Monitor applies to the xTU-C.
                 If INM is not implemented, the relevant profile pointer within the xDSL Line Configuration
                 Vector instance MUST be set to a null value(0).
                 A default profile with an index of '1' will always exist and its parameters will be set to
                 vendor-specific values, unless otherwise specified in this document.
                 The index of this entry is hwVOPINMConfProfIndex.
                "
            INDEX { hwVOPINMConfProfIndex }
            ::= { hwVOPINMConfProfTable 1 }

        HWVOPINMConfProfEntry ::=
            SEQUENCE {
                hwVOPINMConfProfIndex                        Unsigned32,
                hwVOPINMConfProfRowStatus                    RowStatus,
                hwVOPINMConfProfDescription                  OCTET STRING,
                hwVOPINMConfProfInmIatoDs                    Unsigned32,     
                hwVOPINMConfProfInmIatsDs                    Unsigned32,       
                hwVOPINMConfProfInmCcDs                      Unsigned32, 
                hwVOPINMConfProfInmInpeqModeDs               Unsigned32, 
                hwVOPINMConfProfInmIatoUs                    Unsigned32, 
                hwVOPINMConfProfInmIatsUs                    Unsigned32,  
                hwVOPINMConfProfInmCcUs                      Unsigned32, 
                hwVOPINMConfProfInmInpeqModeUs               Unsigned32
             }

        hwVOPINMConfProfIndex OBJECT-TYPE
            SYNTAX Unsigned32 (1..4294967295)
            MAX-ACCESS accessible-for-notify
            STATUS current
            DESCRIPTION
                "The hwVOPINMConfProfIndex identifies a row in the hwVOPINMConfProfTable."
            ::= { hwVOPINMConfProfEntry 1 }

        hwVOPINMConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy'
                 or 'notInService'), it MUST be first unreferenced from all associated DSL lines.

                 A row in hwVOPINMConfProfTable is said to be unreferenced when there is no instance of
                 hwVOPActSetupVNoiseProfId in the hwVOPActSetupTable which refers to the row.
                "
            ::= { hwVOPINMConfProfEntry 2 }

        hwVOPINMConfProfDescription OBJECT-TYPE
            SYNTAX OCTET STRING (SIZE (0..128))
            MAX-ACCESS read-create
            STATUS current
            DESCRIPTION
                "The hwVOPINMConfProfDescription contains an optional human readable description for the profile."
            ::= { hwVOPINMConfProfEntry 3 }

        hwVOPINMConfProfInmIatoDs  OBJECT-TYPE
            SYNTAX      Unsigned32(3..511)
            MAX-ACCESS  read-create
            STATUS      current
            DESCRIPTION
                "The parameter of downstream impulse noise monitoring inter arrival time offset.
                 This is the Inter Arrival Time Offset that the xTU receiver shall use to determine 
                 in which bin of the Inter Arrival Time histogram the IAT is reported. 
                 The valid values for INMIATO ranges from 3 to 511 DMT symbols in steps of 1 DMT symbol.
                "
            REFERENCE    "ITU-T G.997.1, paragraph 7.3.1.9.1"
            DEFVAL       { 3 }
            ::= { hwVOPINMConfProfEntry 4 }
            
        hwVOPINMConfProfInmIatsDs  OBJECT-TYPE
            SYNTAX      Unsigned32(0..7)
            MAX-ACCESS  read-create
            STATUS      current
            DESCRIPTION
                "The parameter of downstream impulse noise monitoring inter arrival time step.
                 This is the Inter Arrival Time Step that the xTU receiver shall use to determine 
                 in which bin of the Inter Arrival Time histogram the IAT is reported.
                 The valid values for INMIATS ranges from 0 to 7 in steps of 1.
                "
            REFERENCE    "ITU-T G.997.1, paragraph 7.3.1.9.2"
            DEFVAL       { 0 }
            ::= { hwVOPINMConfProfEntry 5 }
        
        hwVOPINMConfProfInmCcDs  OBJECT-TYPE
            SYNTAX      Unsigned32(0..64)
            MAX-ACCESS  read-create
            STATUS      current
            DESCRIPTION
                "The parameter of Downstream impulse noise monitoring cluster continuation value.
                 This is the Cluster Continuation value that the xTU receiver shall use 
                 in the cluster indication process described in the relevant ITU-T Recommendation. 
                 The valid values for INMCC range from 0 to 64 DMT symbols in steps of 1 DMT symbol.
                "
            REFERENCE    "ITU-T G.997.1, paragraph 7.3.1.9.3"
            DEFVAL       { 0 }
            ::= { hwVOPINMConfProfEntry 6 }
        
        hwVOPINMConfProfInmInpeqModeDs  OBJECT-TYPE
            SYNTAX      Unsigned32(0..4)
            MAX-ACCESS  read-create
            STATUS      current
            DESCRIPTION
                "The parameter of Downstream impulse noise monitoring equivalent impulse noise protect mode.
                 This is the INM Equivalent INP Mode that the xTU receiver shall use in the computation of the Equivalent INP, 
                 as defined in the relevant ITU-T Recommendation. The valid values for INM_INPEQ_MODE are 0, 1, 2, 3, and 4.
                "
            REFERENCE    "ITU-T G.997.1, paragraph 7.3.1.9.4"
            DEFVAL       { 0 }
            ::= { hwVOPINMConfProfEntry 7 }
            
        hwVOPINMConfProfInmIatoUs  OBJECT-TYPE
            SYNTAX      Unsigned32(3..511)
            MAX-ACCESS  read-create
            STATUS      current
            DESCRIPTION
                "The parameter of upstream impulse noise monitoring inter arrival time offset.
                 This is the Inter Arrival Time Offset that the xTU receiver shall use to determine 
                 in which bin of the Inter Arrival Time histogram the IAT is reported. 
                 The valid values for INMIATO ranges from 3 to 511 DMT symbols in steps of 1 DMT symbol.
                "
            REFERENCE    "ITU-T G.997.1, paragraph 7.3.1.9.1"
            DEFVAL       { 3 }
            ::= { hwVOPINMConfProfEntry 8 }
           
        hwVOPINMConfProfInmIatsUs  OBJECT-TYPE
            SYNTAX      Unsigned32(0..7)
            MAX-ACCESS  read-create
            STATUS      current
            DESCRIPTION
                "The parameter of upstream impulse noise monitoring inter arrival time step.
                 This is the Inter Arrival Time Step that the xTU receiver shall use to determine 
                 in which bin of the Inter Arrival Time histogram the IAT is reported.
                 The valid values for INMIATS ranges from 0 to 7 in steps of 1.
                "
            REFERENCE    "ITU-T G.997.1, paragraph 7.3.1.9.2"
            DEFVAL       { 0 }
            ::= { hwVOPINMConfProfEntry 9 }
            
        hwVOPINMConfProfInmCcUs  OBJECT-TYPE
            SYNTAX      Unsigned32(0..64)
            MAX-ACCESS  read-create
            STATUS      current
            DESCRIPTION
                "The parameter of upstream impulse noise monitoring cluster continuation value.
                 This is the Cluster Continuation value that the xTU receiver shall use 
                 in the cluster indication process described in the relevant ITU-T Recommendation. 
                 The valid values for INMCC range from 0 to 64 DMT symbols in steps of 1 DMT symbol.
                "
            REFERENCE    "ITU-T G.997.1, paragraph 7.3.1.9.3"
            DEFVAL       { 0 }
            ::= { hwVOPINMConfProfEntry 10 }
        
        hwVOPINMConfProfInmInpeqModeUs  OBJECT-TYPE
            SYNTAX      Unsigned32(0..4)
            MAX-ACCESS  read-create
            STATUS      current
            DESCRIPTION
                "The parameter of upstream impulse noise monitoring equivalent impulse noise protect mode.
                 This is the INM Equivalent INP Mode that the xTU receiver shall use in the computation of the Equivalent INP, 
                 as defined in the relevant ITU-T Recommendation. The valid values for INM_INPEQ_MODE are 0, 1, 2, 3, and 4.
                "
            REFERENCE    "ITU-T G.997.1, paragraph 7.3.1.9.4"
            DEFVAL       { 0 }
            ::= { hwVOPINMConfProfEntry 11 }
            
        hwVOPSosProfileIndexNext OBJECT-TYPE 
            SYNTAX HWVOPProfileIndexOrZeroType
            MAX-ACCESS read-only
            STATUS current
            DESCRIPTION
                "This object contains an appropriate value to be used for hwVOPSosConfProfIndex
                 when creating entries in the hwVOPSosConfProfTable.

                 The value '0' indicates that no unassigned entries are available.
                 To obtain the value of hwVOPSosConfProfIndex for a new entry in the table,
                 the manager issues a management protocol retrieval operation.
                 The agent will determine through its local policy when this index value will be made available for reuse.
                "
            ::= { hwVOPProfiles 21 } 
 
        hwVOPSosConfProfTable OBJECT-TYPE
            SYNTAX SEQUENCE OF HWVOPSosConfProfEntry
            MAX-ACCESS not-accessible
            STATUS current
            DESCRIPTION
                "Save our Showtime (SOS) provides the receiver with a means to rapidly perform a bit loading
                 reduction in a specified part of the frequency spectrum. This can be used in case of sudden 
                 noise increases. The SOS Profile provides the parameters to configure the optional procedure
                 for on-line reconfiguration of the Physical Media Dependent (PMD) sub-layer in VDSL2 operation 
                 mode. If the SOS procedure is not utilized the relevant profile pointer within the xDSL Line 
                 Configuration Vector instance MUST be set to a null value (0).
                 A default profile with an index of '1' will always exist and its parameters will be set to
                 vendor-specific values, unless otherwise specified in this document.
                 The index of this table is hwVOPSosConfProfIndex.
                "
            REFERENCE
                "Broadband Forum TR-252, paragraph #5.7"
            ::= { hwVOPProfiles 22 }

        hwVOPSosConfProfEntry OBJECT-TYPE
            SYNTAX HWVOPSosConfProfEntry
            MAX-ACCESS not-accessible
            STATUS current
            DESCRIPTION
                "Save our Showtime (SOS) provides the receiver with a means to rapidly perform a bit loading
                 reduction in a specified part of the frequency spectrum. This can be used in case of sudden 
                 noise increases. The SOS Profile provides the parameters to configure the optional procedure
                 for on-line reconfiguration of the Physical Media Dependent (PMD) sub-layer in VDSL2 operation 
                 mode. If the SOS procedure is not utilized the relevant profile pointer within the xDSL Line 
                 Configuration Vector instance MUST be set to a null value (0).
                 A default profile with an index of '1' will always exist and its parameters will be set to
                 vendor-specific values, unless otherwise specified in this document.
                 The index of this entry is hwVOPSosConfProfIndex.
                "
            INDEX { hwVOPSosConfProfIndex }
            ::= { hwVOPSosConfProfTable 1 }

        HWVOPSosConfProfEntry ::=
            SEQUENCE {
                hwVOPSosConfProfIndex               Unsigned32,
                hwVOPSosConfProfRowStatus           RowStatus,
                hwVOPSosConfProfDescription         OCTET STRING,
                hwVOPSosConfProfSosTimeDs           Unsigned32,     
                hwVOPSosConfProfSosTimeUs           Unsigned32,       
                hwVOPSosConfProfSosNtonesDs         Unsigned32, 
                hwVOPSosConfProfSosNtonesUs         Unsigned32, 
                hwVOPSosConfProfSosCrcDs            Unsigned32, 
                hwVOPSosConfProfSosCrcUs            Unsigned32,  
                hwVOPSosConfProfMaxSosDs            Unsigned32, 
                hwVOPSosConfProfMaxSosUs            Unsigned32,
                hwVOPSosConfProfSnrmoffsetRocDs     Unsigned32,
                hwVOPSosConfProfSnrmoffsetRocUs     Unsigned32,
                hwVOPSosConfProfInpminRocDs         Unsigned32,
                hwVOPSosConfProfInpminRocUs         Unsigned32,
                hwVOPGfastSosConfProfFraTimeDs      Unsigned32,
                hwVOPGfastSosConfProfFraTimeUs      Unsigned32,
                hwVOPGfastSosConfProfFraNtonesDs    Unsigned32,
                hwVOPGfastSosConfProfFraNtonesUs    Unsigned32,
                hwVOPGfastSosConfProfFraMinRtxUcDs  Unsigned32,
                hwVOPGfastSosConfProfFraMinRtxUcUs  Unsigned32,
                hwVOPGfastSosConfProfFraVenDiscDs   INTEGER,
                hwVOPGfastSosConfProfFraVenDiscUs   INTEGER
             }   
              
        hwVOPSosConfProfIndex OBJECT-TYPE
            SYNTAX Unsigned32 (1..4294967295)
            MAX-ACCESS accessible-for-notify
            STATUS current
            DESCRIPTION
                "The hwVOPSosConfProfIndex identifies a row in the hwVOPSosConfProfTable."
            ::= { hwVOPSosConfProfEntry 1 }

        hwVOPSosConfProfRowStatus OBJECT-TYPE
            SYNTAX RowStatus
            MAX-ACCESS read-create
            STATUS current
            DESCRIPTION
                "This object is used to create a new row or to modify or delete an existing row in this table.
                 A profile is activated by setting this object to 'active'.
                 Before a profile can be deleted or taken out of service (by setting this object to 'destroy'
                 or 'notInService'), it MUST be first unreferenced from all associated DSL lines.

                 A row in hwVOPSosConfProfTable is said to be unreferenced when there is no instance of
                 hwVOPActSetupSosProfId in the hwVOPActSetupTable which refers to the row.
                "
            ::= { hwVOPSosConfProfEntry 2 }

        hwVOPSosConfProfDescription OBJECT-TYPE
            SYNTAX OCTET STRING (SIZE (0..128))
            MAX-ACCESS read-create
            STATUS current
            DESCRIPTION
                "The hwVOPSosConfProfDescription contains an optional human readable description for the profile."
            ::= { hwVOPSosConfProfEntry 3 }
            
        hwVOPSosConfProfSosTimeDs  OBJECT-TYPE                                               
            SYNTAX      Unsigned32 (0..255)                                                
            UNITS       "64ms"                                                        
            MAX-ACCESS  read-create                                                         
            STATUS      current                                                             
            DESCRIPTION                                                                     
                "The parameter is used in the specification of the receiver initiated SOS. 
                 If the value of this parameter is not zero, the standard SOS triggering criteria are enabled, 
                 and the value corresponds with duration of the time window used in the standard SOS triggering 
                 criteria in the downstream direction.The special value zero, indicates that the standard SOS 
                 triggering criteria are disabled. The valid range of non-zero values is from 64 ms to (255*64) ms 
                 in steps of 64ms.
                 Unit: 64ms
                "                                               
            REFERENCE    "ITU-T G.997.1(200811), paragraph 7.3.1.10.1"                     
            ::= { hwVOPSosConfProfEntry 4 }
                        
        hwVOPSosConfProfSosTimeUs  OBJECT-TYPE                                               
            SYNTAX      Unsigned32 (0..255)                                                
            UNITS       "64ms"                                                        
            MAX-ACCESS  read-create                                                         
            STATUS      current                                                             
            DESCRIPTION                                                                     
                "The parameter is used in the specification of the receiver initiated SOS. 
                 If the value of this parameter is not zero, the standard SOS triggering criteria are enabled, 
                 and the value corresponds with duration of the time window used in the standard SOS triggering 
                 criteria in the upstream direction.The special value zero, indicates that the standard SOS 
                 triggering criteria are disabled. The valid range of non-zero values is from 64 ms to (255*64) ms 
                 in steps of 64ms.
                 Unit: 64ms
                "                                               
            REFERENCE    "ITU-T G.997.1(200811), paragraph 7.3.1.10.2"                     
            ::= { hwVOPSosConfProfEntry 5 } 
            
        hwVOPSosConfProfSosNtonesDs  OBJECT-TYPE                                               
            SYNTAX      Unsigned32 (0..100)                                                                                                        
            MAX-ACCESS  read-create                                                         
            STATUS      current                                                             
            DESCRIPTION                                                                     
                "This parameter is defined as the minimum percentage of tones in the downstream MEDLEY SET 
                 that must be degraded in order to arm the first sub-condition of the standard SOS triggering 
                 criteria in the downstream direction. The parameter SOS-NTONES-ds is defined as a percentage of tones. 
                 The valid range of values is from 1 to 100 in steps of 1. A special value of 0 indicates that this
                 parameter is not used in the decision criteria.
                "                                               
            REFERENCE    "ITU-T G.997.1(200811), paragraph 7.3.1.10.3"                     
            ::= { hwVOPSosConfProfEntry 6 } 
        
        hwVOPSosConfProfSosNtonesUs  OBJECT-TYPE                                               
            SYNTAX      Unsigned32 (0..100)                                                                                                       
            MAX-ACCESS  read-create                                                         
            STATUS      current                                                             
            DESCRIPTION                                                                     
                "This parameter is defined as the minimum percentage of tones in the upstream MEDLEY SET 
                 that must be degraded in order to arm the first sub-condition of the standard SOS triggering 
                 criteria in the downstream direction. The parameter SOS-NTONES-ds is defined as a percentage of tones. 
                 The valid range of values is from 1 to 100 in steps of 1. A special value of 0 indicates that this
                 parameter is not used in the decision criteria.
                "                                               
            REFERENCE    "ITU-T G.997.1(200811), paragraph 7.3.1.10.4"                     
            ::= { hwVOPSosConfProfEntry 7 } 
        
        hwVOPSosConfProfSosCrcDs  OBJECT-TYPE                                               
            SYNTAX      Unsigned32 (1..65535)                                                
            UNITS       "0.02"                                                        
            MAX-ACCESS  read-create                                                         
            STATUS      current                                                             
            DESCRIPTION                                                                     
                "This parameter is defined as the minimum number of normalized CRC anomalies received in SOS-TIME-ds 
                 seconds in order to arm the second sub-condition of the standard SOS triggering criteria  in the 
                 downstream direction. The valid range of SOS-CRC values is 0.02 to 65535*0.02, in steps of 0.02.
                 Unit: 0.02
                "                                               
            REFERENCE    "ITU-T G.997.1(200811), paragraph 7.3.1.10.5"                     
            ::= { hwVOPSosConfProfEntry 8 } 
            
        hwVOPSosConfProfSosCrcUs  OBJECT-TYPE                                               
            SYNTAX      Unsigned32 (1..65535)                                                
            UNITS       "0.02"                                                        
            MAX-ACCESS  read-create                                                         
            STATUS      current                                                             
            DESCRIPTION                                                                     
                "This parameter is defined as the minimum number of normalized CRC anomalies received in SOS-TIME-ds 
                 seconds in order to arm the second sub-condition of the standard SOS triggering criteria  in the 
                 upstream direction. The valid range of SOS-CRC values is 0.02 to 65535*0.02, in steps of 0.02.
                 Unit: 0.02
                "                                               
           REFERENCE    "ITU-T G.997.1(200811), paragraph 7.3.1.10.6"                     
            ::= { hwVOPSosConfProfEntry 9 } 
        
        hwVOPSosConfProfMaxSosDs  OBJECT-TYPE                                               
            SYNTAX      Unsigned32 (0..15)                                                                                                        
            MAX-ACCESS  read-create                                                         
            STATUS      current                                                             
            DESCRIPTION                                                                     
                "This parameter is used in G.993.2 de-activation. If the number of successful SOS procedures in the 
                 downstream direction performed within a 120-second interval exceeds MAX-SOS-ds, the modem shall transition 
                 to the L3 state. The valid range of values is 1 to 15. A special value of 0 indicates that there is no
                 limit on the maximum allowed number of SOS recoveries within this time interval.
                "                                               
            REFERENCE    "ITU-T G.997.1(200811), paragraph 7.3.1.10.7"                     
            ::= { hwVOPSosConfProfEntry 10 } 
        
        hwVOPSosConfProfMaxSosUs  OBJECT-TYPE                                               
            SYNTAX      Unsigned32 (0..15)                                                                                                        
            MAX-ACCESS  read-create                                                         
            STATUS      current                                                             
            DESCRIPTION                                                                     
                "This parameter is used in G.993.2 de-activation. If the number of successful SOS procedures in the 
                 upstream direction performed within a 120-second interval exceeds MAX-SOS-ds, the modem shall transition 
                 to the L3 state. The valid range of values is 1 to 15. A special value of 0 indicates that there is no
                 limit on the maximum allowed number of SOS recoveries within this time interval.
                "                                               
            REFERENCE    "ITU-T G.997.1(200811), paragraph 7.3.1.10.8"                     
            ::= { hwVOPSosConfProfEntry 11 } 
        
        hwVOPSosConfProfSnrmoffsetRocDs  OBJECT-TYPE                                               
            SYNTAX      Unsigned32 (0..310)                                                
            UNITS       "0.1dB"                                                        
            MAX-ACCESS  read-create                                                         
            STATUS      current                                                             
            DESCRIPTION                                                                     
                "The parameter is defined as the SNR Margin offset for the ROC channel in the downstream direction.
                 The parameter is used in the specification of the Channel Initialization Policy (see 12.3.7.1/G.993.2).
                 The valid range of SNR margin offset values is from 0 to (310*0.1) dB with 0.1 dB steps.
                 Unit: 0.1dB
                "                                               
            REFERENCE    "ITU-T G.997.1(200811), paragraph 7.3.1.10.9"                     
            ::= { hwVOPSosConfProfEntry 12 } 
        
        hwVOPSosConfProfSnrmoffsetRocUs  OBJECT-TYPE                                               
            SYNTAX      Unsigned32 (0..310)                                                
            UNITS       "0.1dB"                                                         
            MAX-ACCESS  read-create                                                         
            STATUS      current                                                             
            DESCRIPTION                                                                     
                "The parameter is defined as the SNR Margin offset for the ROC channel in the upstream direction.
                 The parameter is used in the specification of the Channel Initialization Policy (see 12.3.7.1/G.993.2).
                 The valid range of SNR margin offset values is from 0 to (310*0.1) dB with 0.1 dB steps.
                 Unit: 0.1dB
                "                                               
            REFERENCE    "ITU-T G.997.1(200811), paragraph 7.3.1.10.10"                     
            ::= { hwVOPSosConfProfEntry 13 } 
            
        hwVOPSosConfProfInpminRocDs  OBJECT-TYPE                                               
            SYNTAX      Unsigned32 (0..16)                                                                                                      
            MAX-ACCESS  read-create                                                         
            STATUS      current                                                             
            DESCRIPTION                                                                     
                "This parameter contains the minimum impulse noise protection to apply on the ROC in the downstream direction. 
                 The minimum impulse noise protection is an integer ranging from 0 to 16.
                "                                               
            REFERENCE    "ITU-T G.997.1(200811), paragraph 7.3.1.10.11"                     
            ::= { hwVOPSosConfProfEntry 14 } 
        
        hwVOPSosConfProfInpminRocUs  OBJECT-TYPE                                               
            SYNTAX      Unsigned32 (0..16)                                                                                                      
            MAX-ACCESS  read-create                                                         
            STATUS      current                                                             
            DESCRIPTION                                                                     
                "This parameter contains the minimum impulse noise protection to apply on the robust ROC in the upstream direction.
                 The minimum impulse noise protection is an integer ranging from 0 to 16.
                "                                               
            REFERENCE    "ITU-T G.997.1(200811), paragraph 7.3.1.10.12"                     
            ::= { hwVOPSosConfProfEntry 15 } 
            
        hwVOPGfastSosConfProfFraTimeDs  OBJECT-TYPE                                               
            SYNTAX      Unsigned32 (0..12)                                                
            UNITS       "1 logical frame length"                                                        
            MAX-ACCESS  read-create                                                         
            STATUS      current                                                             
            DESCRIPTION                                                                     
                "The parameter is used in the specification of the receiver initiated FRA. 
                 If the value of this parameter is not zero, the standard FRA triggering criteria are enabled, 
                 and the value corresponds with duration of the time window used in the standard FRA triggering 
                 criteria in the downstream direction.The special value zero, indicates that the standard FRA 
                 triggering criteria are disabled. The valid range of non-zero values is from 1 to 12 
                 in steps of 1 logical frame length.
                 Unit: 1 logical frame length
                "                                               
            REFERENCE    "ITU-T G.9701, paragraph 13.3.1.1.1.1"   
            DEFVAL { 8 }                  
            ::= { hwVOPSosConfProfEntry 16 }
                        
        hwVOPGfastSosConfProfFraTimeUs  OBJECT-TYPE                                               
            SYNTAX      Unsigned32 (0..12)                                                
            UNITS       "1 logical frame length"                                                        
            MAX-ACCESS  read-create                                                         
            STATUS      current                                                             
            DESCRIPTION                                                                     
                "The parameter is used in the specification of the receiver initiated FRA. 
                 If the value of this parameter is not zero, the standard FRA triggering criteria are enabled, 
                 and the value corresponds with duration of the time window used in the standard FRA triggering 
                 criteria in the upstream direction.The special value zero, indicates that the standard FRA 
                 triggering criteria are disabled. The valid range of non-zero values is from 1 to 12 
                 in steps of 1 logical frame length.
                 Unit: 1 logical frame length
                "                                               
            REFERENCE    "ITU-T G.9701, paragraph 13.3.1.1.1.1"
            DEFVAL { 8 }                     
            ::= { hwVOPSosConfProfEntry 17 } 
            
        hwVOPGfastSosConfProfFraNtonesDs  OBJECT-TYPE                                               
            SYNTAX      Unsigned32 (0..100)                                                                                                        
            MAX-ACCESS  read-create                                                         
            STATUS      current                                                             
            DESCRIPTION                                                                     
                "This parameter is defined as the minimum percentage of tones that must be degraded in order to arm 
                 the first sub-condition of the standard FRA triggering criteria in the downstream direction. 
                 The parameter FRA-NTONES-ds is defined as a percentage of tones. 
                 The valid range of values is from 1 to 100 in steps of 1. A special value of 0 indicates that this
                 parameter is not used in the decision criteria.
                "                                               
            REFERENCE    "ITU-T G.9701, paragraph 13.3.1.1.1.2" 
            DEFVAL { 50 }                    
            ::= { hwVOPSosConfProfEntry 18 } 
        
        hwVOPGfastSosConfProfFraNtonesUs  OBJECT-TYPE                                               
            SYNTAX      Unsigned32 (0..100)                                                                                                       
            MAX-ACCESS  read-create                                                         
            STATUS      current                                                             
            DESCRIPTION                                                                     
                "This parameter is defined as the minimum percentage of tones that must be degraded in order to arm 
                 the first sub-condition of the standard FRA triggering criteria in the downstream direction. 
                 The parameter FRA-NTONES-us is defined as a percentage of tones. 
                 The valid range of values is from 1 to 100 in steps of 1. A special value of 0 indicates that this
                 parameter is not used in the decision criteria.
                "                                               
            REFERENCE    "ITU-T G.9701, paragraph 13.3.1.1.1.2"
            DEFVAL { 50 }                     
            ::= { hwVOPSosConfProfEntry 19 } 
        
        hwVOPGfastSosConfProfFraMinRtxUcDs  OBJECT-TYPE                                               
            SYNTAX      Unsigned32 (0..1023)                                                
            MAX-ACCESS  read-create                                                         
            STATUS      current                                                             
            DESCRIPTION                                                                     
                "This parameter is defined as minimum number of rtx uc anomalies received throughout a time window 
                 equal to FRA-TIME-ds in order to arm the second FRA triggering criteria in the downstream direction. 
                 The special value 0 indicates that monitoring of the number of rtx-uc anomalies is disabled.
                "                                               
            REFERENCE    "ITU-T G.9701, paragraph 13.3.1.1.1.3" 
            DEFVAL { 150 }                    
            ::= { hwVOPSosConfProfEntry 20 } 
            
        hwVOPGfastSosConfProfFraMinRtxUcUs  OBJECT-TYPE                                               
            SYNTAX      Unsigned32 (0..1023)                                                                                                   
            MAX-ACCESS  read-create                                                         
            STATUS      current                                                             
            DESCRIPTION                                                                     
                "This parameter is defined as the minimum number of rtx uc anomalies received throughout a time window 
                 equal to FRA-TIME-us in order to arm the second FRA triggering criteria in the upstream direction. 
                 The special value 0 indicates that monitoring of the number of rtx-uc anomalies is disabled.
                "                                               
           REFERENCE    "ITU-T G.9701, paragraph 13.3.1.1.1.3"
           DEFVAL { 150 }                      
            ::= { hwVOPSosConfProfEntry 21 }
            
        hwVOPGfastSosConfProfFraVenDiscDs  OBJECT-TYPE                                               
            SYNTAX INTEGER 
	    {
                disable(1),
                enable(2)
            }                                                                                                  
            MAX-ACCESS  read-create                                                         
            STATUS      current                                                             
            DESCRIPTION                                                                     
                "Enable or disable vendor discretionary FRA triggering criteria in the downstream direction.
                 Options:
                 1. disable (1)  - Disable vendor discretionary FRA triggering criteria in the downstream direction.
                 2. enable (2)   - Enable vendor discretionary FRA triggering criteria in the downstream direction.
		"                                               
           DEFVAL { disable }                      
            ::= { hwVOPSosConfProfEntry 22 }
            
        hwVOPGfastSosConfProfFraVenDiscUs  OBJECT-TYPE                                               
            SYNTAX INTEGER 
	    {
                disable(1),
                enable(2)
            }                                                                                                    
            MAX-ACCESS  read-create                                                         
            STATUS      current                                                             
            DESCRIPTION                                                                     
                "Enable or disable vendor discretionary FRA triggering criteria in the upstream direction.
                 Options:
                 1. disable (1)  - Disable vendor discretionary FRA triggering criteria in the upstream direction.
                 2. enable (2)   - Enable vendor discretionary FRA triggering criteria in the upstream direction.
		"                                               
           DEFVAL { disable }                      
            ::= { hwVOPSosConfProfEntry 23 }                        
                      
            
        hwVOPVectors OBJECT IDENTIFIER ::= { hwVOPObjects 2 }


--
-- This group of parameters controls, on per Network Element level, the methods of attaching Vector Of Profiles (VoP) to xDSL lines
-- to be used. There are two main managed objects involved. With the first, read only, object the Network Element can indicate the
-- method(s) it supports. The second, read write, object is used by the management system in order to configure its favorite method.
--
-- Modifying the requested attachment method may implies a system reboot. Therefore, there is a third, read only, object
-- that reflects the currently used VoP attachment method.
--
--
        hwVOPGlobal OBJECT IDENTIFIER ::= { hwVOPVectors 1 }


        hwVOPGlobalAttachmentMethodCapabilties OBJECT-TYPE
            SYNTAX HWVOPAttachmentMethods
            MAX-ACCESS read-only
            STATUS current
            DESCRIPTION
                "This object reflects the VoP attachment-method(s) this Network Element supports.

                 Two attachment methods, 'direct' and 'indirect' are available and each Network
                 Element MAY be able to support both attachment-methods (but not at the same time).

                 The capability to support a specific attachment-method is indicated by the respective
                 bit-position set to '1'. Particularly, a network element that supports both methods
                 SHOULD indicate that by both bit-positions set to '1'.
                "
            ::= { hwVOPGlobal 1 }


        hwVOPGlobalAttachmentMethodConfigured OBJECT-TYPE
            SYNTAX HWVOPAttachmentMethods
            MAX-ACCESS read-write
            STATUS current
            DESCRIPTION
                "This object configures the VoP attachment-method to be used by this Network Element.
                 Two attachment methods, 'direct' and 'indirect' are available and only one method can be selected at any time.
                 To select a specific attachment-method the management system SHOULD set the respective bit-position to '1'.
                 Changing the requested attachment-method may implies a system reboot.

                 The value of this object MUST be maintained in a persistent manner.

                 In case the selected attachment-method is not supported by the network element or if the management system tries
                 to configure both methods simultaneously the SNMP SET operation SHOULD be rejected by the network element.
                 Default value is 1(direct).
                "
            ::= { hwVOPGlobal 2 }


        hwVOPGlobalAttachmentMethodCurrent OBJECT-TYPE
            SYNTAX HWVOPAttachmentMethods
            MAX-ACCESS read-only
            STATUS current
            DESCRIPTION
                "This object reflects the VoP attachment-method currently used by this Network Element.

                 Two attachment methods, 'direct' and 'indirect' are available and only one method
                 can be used at any time. The specific attachment-method used is indicated by the respective bit-position set to '1'.

                 Changing the requested attachment-method may implies a system reboot.
                "
            ::= { hwVOPGlobal 3 }


        hwVOPSetup OBJECT IDENTIFIER ::= { hwVOPVectors 2 }


        hwVOPSetupProfileIndexNext OBJECT-TYPE
            SYNTAX HWVOPSetupIndexOrZeroType
            MAX-ACCESS read-only
            STATUS current
            DESCRIPTION
                "This object is required only in case the 'indirect' attachment-method of VoP to xDSL lines is implemented,
                 in which case entries/rows in hwVOPSetupTable are dynamically created and deleted by the management system.

                 When implemented, the object reports an appropriate value to be used for hwVOPSetupIndex
                 when creating entries in the hwVOPSetupTable.

                 The value '0' indicates that no unassigned entries are available.
                 To obtain the value of hwVOPSetupIndex for a new entry in the table,
                 the manager issues a management protocol retrieval operation.
                 The agent will determine through its local policy when this index value will be made available for reuse.
                "
            ::= { hwVOPSetup 1 }


        hwVOPSetupTable OBJECT-TYPE
            SYNTAX SEQUENCE OF HWVOPSetupEntry
            MAX-ACCESS not-accessible
            STATUS current
            DESCRIPTION
                "This table contains a collection of profile indices that construct a Vector Of Profiles (VoP).

                 This table is used in both 'direct' and 'indirect' attachment-methods of VoP to xDSL lines.

                 In case the implementation uses 'direct' attachment-method of configuration VoP to xDSL lines then:
                 1) a row in this table is automatically created and deleted by the SNMP agent
                    together with creating a row in the xdsl2LineTable (VDSL2-LINE-MIB) for any xDSL line.
                 2) The row index is same as the index of the respective row in xdsl2LineTable.
                    Thus, this table can be considered as extending the xdsl2LineTable.
                 3) The row status object (hwVOPSetupRowStatus) and profile description(hwVOPSetupDescription) are unused.
                 4) The management system may modify the contents of each row in the table and, by that,
                    modify the required configuration VoP for the related xDSL line.
                 5) Note that the hwVOPActSetupTable reflects the configuration VoP currently used by each xDSL line.
                    Its importance is demonstrated during the time between modifying the configuration VoP
                    of any xDSL line and practically applying it to the xDSL line.
                 In case the implementation uses 'direct' attachment-method of VoP to xDSL lines then a row in the table
                 is automatically created by the SNMP agent when a respective row is created in the xdsl2LineTable.
                 The row objects will be set to default values.

                 In case the implementation uses 'indirect' attachment-method of VoP to xDSL lines then a default profile
                 with an index number 1 will always exist and its objects will be set to default values.
                 The index of this table is hwVOPSetupIndex.
                "
            ::= { hwVOPSetup 2 }


        hwVOPSetupEntry OBJECT-TYPE
            SYNTAX HWVOPSetupEntry
            MAX-ACCESS not-accessible
            STATUS current
            DESCRIPTION
                "This table contains a collection of profile indices that construct a Vector Of Profiles (VoP).

                 This table is used in both 'direct' and 'indirect' attachment-methods of VoP to xDSL lines.

                 In case the implementation uses 'direct' attachment-method of configuration VoP to xDSL lines then:
                 1) a row in this table is automatically created and deleted by the SNMP agent
                    together with creating a row in the xdsl2LineTable (VDSL2-LINE-MIB) for any xDSL line.
                 2) The row index is same as the index of the respective row in xdsl2LineTable.
                    Thus, this table can be considered as extending the xdsl2LineTable.
                 3) The row status object (hwVOPSetupRowStatus) and profile description(hwVOPSetupDescription) are unused.
                 4) The management system may modify the contents of each row in the table and, by that,
                    modify the required configuration VoP for the related xDSL line.
                 5) Note that the hwVOPActSetupTable reflects the configuration VoP currently used by each xDSL line.
                    Its importance is demonstrated during the time between modifying the configuration VoP
                    of any xDSL line and practically applying it to the xDSL line.
                 In case the implementation uses 'direct' attachment-method of VoP to xDSL lines then a row in the table
                 is automatically created by the SNMP agent when a respective row is created in the xdsl2LineTable.
                 The row objects will be set to default values.

                 In case the implementation uses 'indirect' attachment-method of VoP to xDSL lines then a default profile
                 with an index number 1 will always exist and its objects will be set to default values.
                 The index of this entry is hwVOPSetupIndex.
                "
            INDEX { hwVOPSetupIndex }
            ::= { hwVOPSetupTable 1 }


        HWVOPSetupEntry ::=
            SEQUENCE {
                hwVOPSetupIndex                                Unsigned32,
                hwVOPSetupRowStatus                            RowStatus,
                hwVOPSetupDescription                          OCTET STRING,
                hwVOPSetupUsDataRateProfId1                    Unsigned32,
                hwVOPSetupUsRaRatio1                           Unsigned32,
                hwVOPSetupDsDataRateProfId1                    Unsigned32,
                hwVOPSetupDsRaRatio1                           Unsigned32,
                hwVOPSetupInpDelayProfId1                      Unsigned32,
                hwVOPSetupUsDataRateProfId2                    Unsigned32,
                hwVOPSetupUsRaRatio2                           Unsigned32,
                hwVOPSetupDsDataRateProfId2                    Unsigned32,
                hwVOPSetupDsRaRatio2                           Unsigned32,
                hwVOPSetupInpDelayProfId2                      Unsigned32,
                hwVOPSetupUsDataRateProfId3                    Unsigned32,
                hwVOPSetupUsRaRatio3                           Unsigned32,
                hwVOPSetupDsDataRateProfId3                    Unsigned32,
                hwVOPSetupDsRaRatio3                           Unsigned32,
                hwVOPSetupInpDelayProfId3                      Unsigned32,
                hwVOPSetupUsDataRateProfId4                    Unsigned32,
                hwVOPSetupUsRaRatio4                           Unsigned32,
                hwVOPSetupDsDataRateProfId4                    Unsigned32,
                hwVOPSetupDsRaRatio4                           Unsigned32,
                hwVOPSetupInpDelayProfId4                      Unsigned32,
                hwVOPSetupLSpectrumProfId                      Unsigned32,
                hwVOPSetupUpboProfId                           Unsigned32,
                hwVOPSetupDpboProfId                           Unsigned32,
                hwVOPSetupRfiProfId                            Unsigned32,
                hwVOPSetupNoiseMarginProfId                    Unsigned32,
                hwVOPSetupVNoiseProfId                         Unsigned32,
                hwVOPSetupInmProfId                            Unsigned32,
                hwVOPSetupUsDataRateProf1Description           OCTET STRING,
                hwVOPSetupDsDataRateProf1Description           OCTET STRING,
                hwVOPSetupInpDelayProf1Description             OCTET STRING,
                hwVOPSetupUsDataRateProf2Description           OCTET STRING,
                hwVOPSetupDsDataRateProf2Description           OCTET STRING,
                hwVOPSetupInpDelayProf2Description             OCTET STRING,
                hwVOPSetupLSpectrumProfDescription             OCTET STRING,
                hwVOPSetupUpboProfDescription                  OCTET STRING,
                hwVOPSetupDpboProfDescription                  OCTET STRING,
                hwVOPSetupRfiProfDescription                   OCTET STRING,
                hwVOPSetupNoiseMarginProfDescription           OCTET STRING,
                hwVOPSetupVNoiseProfDescription                OCTET STRING,
                hwVOPSetupInmProfDescription                   OCTET STRING,
                hwVOPSetupSosProfId                            Unsigned32,
                hwVOPSetupSosProfDescription                   OCTET STRING
             }


        hwVOPSetupIndex OBJECT-TYPE
            SYNTAX Unsigned32 (1..4294967295)
            MAX-ACCESS not-accessible
            STATUS current
            DESCRIPTION
                "The hwVOPSetupIndex identifies a row in the hwVOPSetupTable.
                 A row in this table may be indexed either by an ifIndex pattern, in case the 'direct'
                 attachment-method of VoP to xDSL rows is implemented, or by a unique ordered number,
                 in case the 'indirect' attachment-method of VoP to xDSL rows is implemented.
                "
            ::= { hwVOPSetupEntry 1 }


        hwVOPSetupRowStatus OBJECT-TYPE
            SYNTAX RowStatus
            MAX-ACCESS read-create
            STATUS current
            DESCRIPTION
                "This object is used, in case the 'indirect' attachment-method of VoP to xDSL lines is implemented,
                 to create a new row, to modify a row, or delete an existing row in this table.

                 In case the 'direct' attachment-method of VoP to xDSL lines is implemented then rows in this table
                 are automatically created and deleted by the embedded system and this object is not implemented/used.

                 When the object is being used, as described above, rows in this table are dynamically created,
                 modified and deleted by the management system.

                 When the object is being used then before a row in this table can be deleted or
                 taken out of service (by setting this object to 'destroy' or 'notInService'), it MUST be first
                 un-referenced from all associated xDSL lines.
                 A row in voSetupTable is said to be not referenced when there is no instance
                 of xdsl2LineTable (VDSL2-LINE-MIB) which refers to the row.
                "
            ::= { hwVOPSetupEntry 2 }


        hwVOPSetupDescription OBJECT-TYPE
            SYNTAX OCTET STRING (SIZE (0..128))
            MAX-ACCESS read-create
            STATUS current
            DESCRIPTION
                "The hwVOPSetupDescription contains an optional human readable description for the profile.
                 This object is more likely to be used in case the 'indirect' attachment-method of VoP
                 to xDSL lines is implemented.

                 However, if implemented in 'direct' attachment-method of VoP to xDSL lines
                 then this object has read-write accessibility.
                "
            ::= { hwVOPSetupEntry 3 }


        hwVOPSetupUsDataRateProfId1 OBJECT-TYPE
            SYNTAX Unsigned32 (1..4294967294)
            MAX-ACCESS read-create
            STATUS current
            DESCRIPTION
                "This object identifies a row in hwVOPDataRateConfProfTable used for
                 configuring the upstream transmission direction of channel #1.

                 This object has read-write accessibility if 'direct' attachment-method of VoP to xDSL lines is implemented.
                "
            DEFVAL { 1 }
            ::= { hwVOPSetupEntry 4 }


        hwVOPSetupUsRaRatio1 OBJECT-TYPE
            SYNTAX Unsigned32 (0..100)
            MAX-ACCESS read-create
            STATUS current
            DESCRIPTION
                "Rate Adaptation Ratio.
                 The ratio (in %) that should be taken into account for the bearer channel #1
                 when performing rate adaptation on upstream.
                 The ratio refers to the available data rate in excess of the Minimum Data Rate, summed over all bearer channels.

                 Also, the 100 - hwVOPSetupUsRaRatio1 is the ratio of excess data rate to
                 be assigned to all other bearer channels on upstream direction.
                 The sum of rate adaptation ratios over all bearers on the same direction shall be equal to 100%.

                 This object has read-write accessibility if 'direct' attachment-method of VoP to xDSL lines is implemented.
                "
            DEFVAL { 100 }
            ::= { hwVOPSetupEntry 5 }


        hwVOPSetupDsDataRateProfId1 OBJECT-TYPE
            SYNTAX Unsigned32 (1..4294967294)
            MAX-ACCESS read-create
            STATUS current
            DESCRIPTION
                "This object identifies a row in hwVOPDataRateConfProfTable used for
                 configuring the downstream transmission direction of channel #1.

                 This object has read-write accessibility if 'direct' attachment-method of VoP to xDSL lines is implemented.
                "
            DEFVAL { 2 }
            ::= { hwVOPSetupEntry 6 }


        hwVOPSetupDsRaRatio1 OBJECT-TYPE
            SYNTAX Unsigned32 (0..100)
            MAX-ACCESS read-create
            STATUS current
            DESCRIPTION
                "Rate Adaptation Ratio.
                 The ratio (in %) that should be taken into account for the bearer channel #1
                 when performing rate adaptation on downstream.
                 The ratio refers to the available data rate in excess of the Minimum Data Rate, summed over all bearer channels.

                 Also, the 100 - hwVOPSetupDsRaRatio1 is the ratio of excess data rate to
                 be assigned to all other bearer channels on downstream direction.
                 The sum of rate adaptation ratios over all bearers on the same direction shall be equal to 100%.

                 This object has read-write accessibility if 'direct' attachment-method of VoP to xDSL lines is implemented.
                "
            DEFVAL { 100 }
            ::= { hwVOPSetupEntry 7 }


        hwVOPSetupInpDelayProfId1 OBJECT-TYPE
            SYNTAX Unsigned32 (1..4294967294)
            MAX-ACCESS read-create
            STATUS current
            DESCRIPTION
                "This object identifies a row in hwVOPINPDelayConfProfTable used for
                 configuring the INP-Delay parameters of channel #1.

                 This object has read-write accessibility if 'direct' attachment-method of VoP to xDSL lines is implemented.
                "
            DEFVAL { 1 }
            ::= { hwVOPSetupEntry 8 }


        hwVOPSetupUsDataRateProfId2 OBJECT-TYPE
            SYNTAX Unsigned32 (0..4294967294)
            MAX-ACCESS read-create
            STATUS current
            DESCRIPTION
                "This object identifies a row in hwVOPDataRateConfProfTable used for
                 configuring the upstream transmission direction of channel #2.
                 If channel #2 is not being used this object should be set to 0.

                 This object has read-write accessibility if 'direct' attachment-method of VoP to xDSL lines is implemented.
                "
            DEFVAL { 0 }
            ::= { hwVOPSetupEntry 9 }


        hwVOPSetupUsRaRatio2 OBJECT-TYPE
            SYNTAX Unsigned32 (0..100)
            MAX-ACCESS read-create
            STATUS current
            DESCRIPTION
                "Rate Adaptation Ratio.
                 The ratio (in %) that should be taken into account for the bearer channel #2
                 when performing rate adaptation on upstream.
                 The ratio refers to the available data rate in excess of the Minimum Data Rate, summed over all bearer channels.

                 Also, the 100 - hwVOPSetupUsRaRatio2 is the ratio of excess data rate to
                 be assigned to all other bearer channels on upstream direction.
                 The sum of rate adaptation ratios over all bearers on the same direction shall be equal to 100%.

                 This object has read-write accessibility if 'direct' attachment-method of VoP to xDSL lines is implemented.
                "
            DEFVAL { 0 }
            ::= { hwVOPSetupEntry 10 }


        hwVOPSetupDsDataRateProfId2 OBJECT-TYPE
            SYNTAX Unsigned32 (0..4294967294)
            MAX-ACCESS read-create
            STATUS current
            DESCRIPTION
                "This object identifies a row in hwVOPDataRateConfProfTable used for
                 configuring the downstream transmission direction of channel #2.
                 If channel #2 is not being used this object should be set to 0.

                 This object has read-write accessibility if 'direct' attachment-method of VoP to xDSL lines is implemented.
                "
            DEFVAL { 0 }
            ::= { hwVOPSetupEntry 11 }


        hwVOPSetupDsRaRatio2 OBJECT-TYPE
            SYNTAX Unsigned32 (0..100)
            MAX-ACCESS read-create
            STATUS current
            DESCRIPTION
                "Rate Adaptation Ratio.
                 The ratio (in %) that should be taken into account for the bearer channel #2
                 when performing rate adaptation on downstream.
                 The ratio refers to the available data rate in excess of the Minimum Data Rate, summed over all bearer channels.

                 Also, the 100 - hwVOPSetupDsRaRatio2 is the ratio of excess data rate to
                 be assigned to all other bearer channels on downstream direction.
                 The sum of rate adaptation ratios over all bearers on the same direction shall be equal to 100%.

                 This object has read-write accessibility if 'direct' attachment-method of VoP to xDSL lines is implemented.
                "
            DEFVAL { 0 }
            ::= { hwVOPSetupEntry 12 }


        hwVOPSetupInpDelayProfId2 OBJECT-TYPE
            SYNTAX Unsigned32 (0..4294967294)
            MAX-ACCESS read-create
            STATUS current
            DESCRIPTION
                "This object identifies a row in hwVOPINPDelayConfProfTable used for
                 configuring the INP-Delay parameters of channel #2.
                 If channel #2 is not being used this object should be set to 0.

                 This object has read-write accessibility if 'direct' attachment-method of VoP to xDSL lines is implemented.
                "
            DEFVAL { 0 }
            ::= { hwVOPSetupEntry 13 }


        hwVOPSetupUsDataRateProfId3 OBJECT-TYPE
            SYNTAX Unsigned32 (0..4294967294)
            MAX-ACCESS read-create
            STATUS current
            DESCRIPTION
                "This object identifies a row in hwVOPDataRateConfProfTable used for
                 configuring the upstream transmission direction of channel #3.
                 If channel #3 is not being used this object should be set to 0.

                 This object has read-write accessibility if 'direct' attachment-method of VoP to xDSL lines is implemented.
                "
            DEFVAL { 0 }
            ::= { hwVOPSetupEntry 14 }


        hwVOPSetupUsRaRatio3 OBJECT-TYPE
            SYNTAX Unsigned32 (0..100)
            MAX-ACCESS read-create
            STATUS current
            DESCRIPTION
                "Rate Adaptation Ratio.
                 The ratio (in %) that should be taken into account for the bearer channel #3
                 when performing rate adaptation on upstream.
                 The ratio refers to the available data rate in excess of the Minimum Data Rate, summed over all bearer channels.
                 Also, the 100 - hwVOPSetupUsRaRatio3 is the ratio of excess data rate to
                 be assigned to all other bearer channels on upstream direction.
                 The sum of rate adaptation ratios over all bearers on the same direction shall be equal to 100%.

                 This object has read-write accessibility if 'direct' attachment-method of VoP to xDSL lines is implemented.
                "
            DEFVAL { 0 }
            ::= { hwVOPSetupEntry 15 }


        hwVOPSetupDsDataRateProfId3 OBJECT-TYPE
            SYNTAX Unsigned32 (0..4294967294)
            MAX-ACCESS read-create
            STATUS current
            DESCRIPTION
                "This object identifies a row in hwVOPDataRateConfProfTable used for
                 configuring the downstream transmission direction of channel #3.
                 If channel #3 is not being used this object should be set to 0.

                 This object has read-write accessibility if 'direct' attachment-method of VoP to xDSL lines is implemented.
                "
            DEFVAL { 0 }
            ::= { hwVOPSetupEntry 16 }


        hwVOPSetupDsRaRatio3 OBJECT-TYPE
            SYNTAX Unsigned32 (0..100)
            MAX-ACCESS read-create
            STATUS current
            DESCRIPTION
                "Rate Adaptation Ratio.
                 The ratio (in %) that should be taken into account for the bearer channel #3
                 when performing rate adaptation on downstream.
                 The ratio refers to the available data rate in excess of the Minimum Data Rate, summed over all bearer channels.

                 Also, the 100 - hwVOPSetupDsRaRatio3 is the ratio of excess data rate to
                 be assigned to all other bearer channels on downstream direction.
                 The sum of rate adaptation ratios over all bearers on the same direction shall be equal to 100%.

                 This object has read-write accessibility if 'direct' attachment-method of VoP to xDSL lines is implemented.
                "
            DEFVAL { 0 }
            ::= { hwVOPSetupEntry 17 }


        hwVOPSetupInpDelayProfId3 OBJECT-TYPE
            SYNTAX Unsigned32 (0..4294967294)
            MAX-ACCESS read-create
            STATUS current
            DESCRIPTION
                "This object identifies a row in hwVOPINPDelayConfProfTable used for
                 configuring the INP-Delay parameters of channel #3.
                 If channel #3 is not being used this object should be set to 0.

                 This object has read-write accessibility if 'direct' attachment-method of VoP to xDSL lines is implemented.
                "
            DEFVAL { 0 }
            ::= { hwVOPSetupEntry 18 }


        hwVOPSetupUsDataRateProfId4 OBJECT-TYPE
            SYNTAX Unsigned32 (0..4294967294)
            MAX-ACCESS read-create
            STATUS current
            DESCRIPTION
                "This object identifies a row in hwVOPDataRateConfProfTable used for
                 configuring the upstream transmission direction of channel #4.
                 If channel #4 is not being used this object should be set to 0.

                 This object has read-write accessibility if 'direct' attachment-method of VoP to xDSL lines is implemented.
                "
            DEFVAL { 0 }
            ::= { hwVOPSetupEntry 19 }


        hwVOPSetupUsRaRatio4 OBJECT-TYPE
            SYNTAX Unsigned32 (0..100)
            MAX-ACCESS read-create
            STATUS current
            DESCRIPTION
                "Rate Adaptation Ratio.
                 The ratio (in %) that should be taken into account for the bearer channel #4
                 when performing rate adaptation on upstream.
                 The ratio refers to the available data rate in excess of the Minimum Data Rate, summed over all bearer channels.
                 Also, the 100 - hwVOPSetupUsRaRatio4 is the ratio of excess data rate to
                 be assigned to all other bearer channels on upstream direction.
                 The sum of rate adaptation ratios over all bearers on the same direction shall be equal to 100%.

                 This object has read-write accessibility if 'direct' attachment-method of VoP to xDSL lines is implemented.
                "
            DEFVAL { 0 }
            ::= { hwVOPSetupEntry 20 }


        hwVOPSetupDsDataRateProfId4 OBJECT-TYPE
            SYNTAX Unsigned32 (0..4294967294)
            MAX-ACCESS read-create
            STATUS current
            DESCRIPTION
                "This object identifies a row in hwVOPDataRateConfProfTable used for
                 configuring the downstream transmission direction of channel #4.
                 If channel #4 is not being used this object should be set to 0.

                 This object has read-write accessibility if 'direct' attachment-method of VoP to xDSL lines is implemented.
                "
            DEFVAL { 0 }
            ::= { hwVOPSetupEntry 21 }


        hwVOPSetupDsRaRatio4 OBJECT-TYPE
            SYNTAX Unsigned32 (0..100)
            MAX-ACCESS read-create
            STATUS current
            DESCRIPTION
                "Rate Adaptation Ratio.
                 The ratio (in %) that should be taken into account for the bearer channel #4
                 when performing rate adaptation on downstream.
                 The ratio refers to the available data rate in excess of the Minimum Data Rate, summed over all bearer channels.
                 Also, the 100 - hwVOPSetupDsRaRatio4 is the ratio of excess data rate to
                 be assigned to all other bearer channels on downstream direction.
                 The sum of rate adaptation ratios over all bearers on the same direction shall be equal to 100%.

                 This object has read-write accessibility if 'direct' attachment-method of VoP to xDSL lines is implemented.
                "
            DEFVAL { 0 }
            ::= { hwVOPSetupEntry 22 }


        hwVOPSetupInpDelayProfId4 OBJECT-TYPE
            SYNTAX Unsigned32 (0..4294967294)
            MAX-ACCESS read-create
            STATUS current
            DESCRIPTION
                "This object identifies a row in hwVOPINPDelayConfProfTable used for
                 configuring the INP-Delay parameters of channel #4.
                 If channel #4 is not being used this object should be set to 0.

                 This object has read-write accessibility if 'direct' attachment-method of VoP to xDSL lines is implemented.
                "
            DEFVAL { 0 }
            ::= { hwVOPSetupEntry 23 }


        hwVOPSetupLSpectrumProfId OBJECT-TYPE
            SYNTAX Unsigned32 (1..4294967294)
            MAX-ACCESS read-create
            STATUS current
            DESCRIPTION
                "This object identifies a row in hwVOPLineSpectrumConfProfTable used for
                 configuring the spectrum parameters of the respective xDSL line.

                 This object has read-write accessibility if 'direct' attachment-method of VoP to xDSL lines is implemented.
                "
            DEFVAL { 1 }
            ::= { hwVOPSetupEntry 24 }


        hwVOPSetupUpboProfId OBJECT-TYPE
            SYNTAX Unsigned32 (0..4294967294)
            MAX-ACCESS read-create
            STATUS current
            DESCRIPTION
                "This object identifies a row in hwVOPUPBOConfProfTable used for
                 configuring the upstream power back-off related parameters of the respective xDSL line.
                 If this leaf is not support this object should be set to 0.
                 This object has read-write accessibility if 'direct' attachment-method of VoP to xDSL lines is implemented.
                "
            DEFVAL { 1 }
            ::= { hwVOPSetupEntry 25 }


        hwVOPSetupDpboProfId OBJECT-TYPE
            SYNTAX Unsigned32 (1..4294967294)
            MAX-ACCESS read-create
            STATUS current
            DESCRIPTION
                "This object identifies a row in hwVOPDPBOConfProfTable used for
                 configuring the downstream power back-off related parameters of the respective xDSL line.

                 This object has read-write accessibility if 'direct' attachment-method of VoP to xDSL lines is implemented.
                "
            DEFVAL { 1 }
            ::= { hwVOPSetupEntry 26 }


        hwVOPSetupRfiProfId OBJECT-TYPE
            SYNTAX Unsigned32 (1..4294967294)
            MAX-ACCESS read-create
            STATUS current
            DESCRIPTION
                "This object identifies a row in hwVOPRFIConfProfTable used for
                 configuring the RFI notches related parameters of the respective xDSL line.

                 This object has read-write accessibility if 'direct' attachment-method of VoP to xDSL lines is implemented.
                "
            DEFVAL { 1 }
            ::= { hwVOPSetupEntry 27 }


        hwVOPSetupNoiseMarginProfId OBJECT-TYPE
            SYNTAX Unsigned32 (1..4294967294)
            MAX-ACCESS read-create
            STATUS current
            DESCRIPTION
                "This object identifies a row in hwVOPSNRMarginConfProfTable used for
                 configuring the noise margin related parameters of the respective xDSL line.

                 This object has read-write accessibility if 'direct' attachment-method of VoP to xDSL lines is implemented.
                "
            DEFVAL { 1 }
            ::= { hwVOPSetupEntry 28 }


        hwVOPSetupVNoiseProfId OBJECT-TYPE
            SYNTAX Unsigned32 (1..4294967294)
            MAX-ACCESS read-create
            STATUS current
            DESCRIPTION
                "This object identifies a row in hwVOPVirtualNoiseConfProfTable used for
                 configuring the virtual noise related parameters of the respective xDSL line.

                 This object has read-write accessibility if 'direct' attachment-method of VoP to xDSL lines is implemented.
                "
            DEFVAL { 1 }
            ::= { hwVOPSetupEntry 29 }
            
        hwVOPSetupInmProfId OBJECT-TYPE
            SYNTAX Unsigned32 (1..4294967294)
            MAX-ACCESS read-create
            STATUS current
            DESCRIPTION
                "This object identifies a row in hwVOPINMConfProfTable used for
                 configuring the impulse noise monitoring parameters of the respective xDSL line.

                 This object has read-write accessibility if 'direct' attachment-method of VoP to xDSL lines is implemented.
                "
            DEFVAL { 1 }
            ::= { hwVOPSetupEntry 30 }

        hwVOPSetupUsDataRateProf1Description OBJECT-TYPE
            SYNTAX OCTET STRING (SIZE (0..128))
            MAX-ACCESS read-create
            STATUS current
            DESCRIPTION
                "This object identifies a row in hwVOPDataRateConfProfTable used for
                 configuring the upstream transmission direction of channel #1.
                 	
                 This object has read-write accessibility if 'direct' attachment-method of VoP to xDSL lines is implemented.
                "
            ::= { hwVOPSetupEntry 31 }
        
        hwVOPSetupDsDataRateProf1Description OBJECT-TYPE
            SYNTAX OCTET STRING (SIZE (0..128))
            MAX-ACCESS read-create
            STATUS current
            DESCRIPTION
                "This object identifies a row in hwVOPDataRateConfProfTable used for
                 configuring the downstream transmission direction of channel #1.

                 This object has read-write accessibility if 'direct' attachment-method of VoP to xDSL lines is implemented.
                "
            ::= { hwVOPSetupEntry 32 }
        
        hwVOPSetupInpDelayProf1Description OBJECT-TYPE
            SYNTAX OCTET STRING (SIZE (0..128))
            MAX-ACCESS read-create
            STATUS current
            DESCRIPTION
                "This object identifies a row in hwVOPINPDelayConfProfTable used for
                 configuring the INP-Delay parameters of channel #1.

                 This object has read-write accessibility if 'direct' attachment-method of VoP to xDSL lines is implemented.
                "
            ::= { hwVOPSetupEntry 33 }
        
        hwVOPSetupUsDataRateProf2Description OBJECT-TYPE
            SYNTAX OCTET STRING (SIZE (0..128))
            MAX-ACCESS read-create
            STATUS current
            DESCRIPTION
                "This object identifies a row in hwVOPDataRateConfProfTable used for
                 configuring the upstream transmission direction of channel #2.
                 If channel #2 is not being used this object should be set to a zero length string.

                 This object has read-write accessibility if 'direct' attachment-method of VoP to xDSL lines is implemented.
                "
            ::= { hwVOPSetupEntry 34 }
        
        hwVOPSetupDsDataRateProf2Description OBJECT-TYPE
            SYNTAX OCTET STRING (SIZE (0..128))
            MAX-ACCESS read-create
            STATUS current
            DESCRIPTION
                "This object identifies a row in hwVOPDataRateConfProfTable used for
                 configuring the downstream transmission direction of channel #2.
                 If channel #2 is not being used this object should be set to a zero length string.

                 This object has read-write accessibility if 'direct' attachment-method of VoP to xDSL lines is implemented.
                "
            ::= { hwVOPSetupEntry 35 }
        
        hwVOPSetupInpDelayProf2Description OBJECT-TYPE
            SYNTAX OCTET STRING (SIZE (0..128))
            MAX-ACCESS read-create
            STATUS current
            DESCRIPTION
                "This object identifies a row in hwVOPINPDelayConfProfTable used for
                 configuring the INP-Delay parameters of channel #2.
                 If channel #2 is not being used this object should be set to a zero length string.

                 This object has read-write accessibility if 'direct' attachment-method of VoP to xDSL lines is implemented.
                "
            ::= { hwVOPSetupEntry 36 }
        
        hwVOPSetupLSpectrumProfDescription OBJECT-TYPE
            SYNTAX OCTET STRING (SIZE (0..128))
            MAX-ACCESS read-create
            STATUS current
            DESCRIPTION
                "This object identifies a row in hwVOPLineSpectrumConfProfTable used for
                 configuring the spectrum parameters of the respective xDSL line.

                 This object has read-write accessibility if 'direct' attachment-method of VoP to xDSL lines is implemented.
                "
            ::= { hwVOPSetupEntry 37 }
        
        hwVOPSetupUpboProfDescription OBJECT-TYPE
            SYNTAX OCTET STRING (SIZE (0..128))
            MAX-ACCESS read-create
            STATUS current
            DESCRIPTION
                "This object identifies a row in hwVOPUPBOConfProfTable used for
                 configuring the upstream power back-off related parameters of the respective xDSL line.
                 If this leaf is not support this object should be set to 0.
                 This object has read-write accessibility if 'direct' attachment-method of VoP to xDSL lines is implemented.
                "
            ::= { hwVOPSetupEntry 38 }
        
        hwVOPSetupDpboProfDescription OBJECT-TYPE
            SYNTAX OCTET STRING (SIZE (0..128))
            MAX-ACCESS read-create
            STATUS current
            DESCRIPTION
                "This object identifies a row in hwVOPDPBOConfProfTable used for
                 configuring the downstream power back-off related parameters of the respective xDSL line.

                 This object has read-write accessibility if 'direct' attachment-method of VoP to xDSL lines is implemented.
                "
            ::= { hwVOPSetupEntry 39 }
        
        hwVOPSetupRfiProfDescription OBJECT-TYPE
            SYNTAX OCTET STRING (SIZE (0..128))
            MAX-ACCESS read-create
            STATUS current
            DESCRIPTION
                "This object identifies a row in hwVOPRFIConfProfTable used for
                 configuring the RFI notches related parameters of the respective xDSL line.

                 This object has read-write accessibility if 'direct' attachment-method of VoP to xDSL lines is implemented.
                "
            ::= { hwVOPSetupEntry 40 }
        
        hwVOPSetupNoiseMarginProfDescription OBJECT-TYPE
            SYNTAX OCTET STRING (SIZE (0..128))
            MAX-ACCESS read-create
            STATUS current
            DESCRIPTION
                "This object identifies a row in hwVOPSNRMarginConfProfTable used for
                 configuring the noise margin related parameters of the respective xDSL line.

                 This object has read-write accessibility if 'direct' attachment-method of VoP to xDSL lines is implemented.
                "
            ::= { hwVOPSetupEntry 41 }
        
        hwVOPSetupVNoiseProfDescription OBJECT-TYPE
            SYNTAX OCTET STRING (SIZE (0..128))
            MAX-ACCESS read-create
            STATUS current
            DESCRIPTION
                "This object identifies a row in hwVOPVirtualNoiseConfProfTable used for
                 configuring the virtual noise related parameters of the respective xDSL line.

                 This object has read-write accessibility if 'direct' attachment-method of VoP to xDSL lines is implemented.
                "
            ::= { hwVOPSetupEntry 42 }
        
        hwVOPSetupInmProfDescription OBJECT-TYPE
            SYNTAX OCTET STRING (SIZE (0..128))
            MAX-ACCESS read-create
            STATUS current
            DESCRIPTION
                "This object identifies a row in hwVOPINMConfProfTable used for
                 configuring the impulse noise monitoring parameters of the respective xDSL line.

                 This object has read-write accessibility if 'direct' attachment-method of VoP to xDSL lines is implemented.
                "
            ::= { hwVOPSetupEntry 43 }
            
        hwVOPSetupSosProfId OBJECT-TYPE
            SYNTAX Unsigned32 (0..4294967294)
            MAX-ACCESS read-create
            STATUS current
            DESCRIPTION
                "This object identifies a row in hwVOPSosConfProfTable used for
                 configuring the save our showtime parameters of the respective xDSL line.
                 If this leaf is not support this object should be set to 0.

                 This object has read-write accessibility if 'direct' attachment-method of VoP to xDSL lines is implemented.
                "
            DEFVAL { 1 }
            ::= { hwVOPSetupEntry 44 }

        hwVOPSetupSosProfDescription OBJECT-TYPE
            SYNTAX OCTET STRING (SIZE (0..128))
            MAX-ACCESS read-create
            STATUS current
            DESCRIPTION
                "This object identifies a row in hwVOPSosConfProfTable used for
                 configuring the save our showtime parameters of the respective xDSL line.
                 If this leaf is not support this object should be set to 0.

                 This object has read-write accessibility if 'direct' attachment-method of VoP to xDSL lines is implemented.
                "
            ::= { hwVOPSetupEntry 45 }            
            
--
-- VoP Actual Setup Table
--
-- Implementing this table is mandatory, in case of 'direct' attachment-method of VoP to xDSL lines.
-- It reflects the 'actual' [VoP] configuration of the respective line.
-- The 'required' configuration for each xDSL line is provided by the row with the same index-value in the hwVOPSetupTable.
--
-- The table can optionally be implemented when the 'indirect' attachment-method of VoP to xDSL lines is
-- implemented. In such case, it is added to reflecting the actual VoP index used by the respective
-- xDSL line via the xdsl2LineStatusActTemplate object in the line table (xdsl2LineTable).
--
        hwVOPActSetupTable OBJECT-TYPE
            SYNTAX SEQUENCE OF HWVOPActSetupEntry
            MAX-ACCESS not-accessible
            STATUS current
            DESCRIPTION
                "This read-only table contains groups of profile indices actually attached to any xDSL line in the system.
                 Each group of profile indices constructs a Vector Of Profiles (VoP).

                 1) A row in this table is automatically created or deleted by the SNMP agent together
                    with creating or deleting a row in the xdsl2LineTable (VDSL2-LINE-MIB) for any xDSL line.
                 2) The row index is same as the index of the respective row in xdsl2LineTable.
                    Thus, this table can be considered as extending the xdsl2LineTable.

                 This table is mandatory in 'direct' attachment-method of VoP to xDSL lines
                 but can optionally be implemented in 'indirect' attachment-method.
                 The objects in this table reflect the actual configuration VoP of the respective xDSL line.

                 A row in the table is automatically created by the SNMP agent when a respective row is created
                 in the xdsl2LineTable. Implementing this table is mandatory in case the implementation
                 uses 'direct' attachment-method of VoP to xDSL lines.
                 Implementation is optional in case of 'indirect' attachment-method.
                 The index of this table is hwVOPActSetupIndex.
                "
            ::= { hwVOPSetup 3 }


        hwVOPActSetupEntry OBJECT-TYPE
            SYNTAX HWVOPActSetupEntry
            MAX-ACCESS not-accessible
            STATUS current
            DESCRIPTION
                "This read-only table contains groups of profile indices actually attached to any xDSL line in the system.
                 Each group of profile indices constructs a Vector Of Profiles (VoP).

                 1) A row in this table is automatically created or deleted by the SNMP agent together
                    with creating or deleting a row in the xdsl2LineTable (VDSL2-LINE-MIB) for any xDSL line.
                 2) The row index is same as the index of the respective row in xdsl2LineTable.
                    Thus, this table can be considered as extending the xdsl2LineTable.

                 This table is mandatory in 'direct' attachment-method of VoP to xDSL lines
                 but can optionally be implemented in 'indirect' attachment-method.
                 The objects in this table reflect the actual configuration VoP of the respective xDSL line.

                 A row in the table is automatically created by the SNMP agent when a respective row is created
                 in the xdsl2LineTable. Implementing this table is mandatory in case the implementation
                 uses 'direct' attachment-method of VoP to xDSL lines.
                 Implementation is optional in case of 'indirect' attachment-method.
                 The index of this entry is hwVOPActSetupIndex.
                "
            INDEX { hwVOPActSetupIndex }
            ::= { hwVOPActSetupTable 1 }


        HWVOPActSetupEntry ::=
            SEQUENCE {
                hwVOPActSetupIndex                         Unsigned32,
                hwVOPActSetupUsDataRateProfId1             Unsigned32,
                hwVOPActSetupUsRaRatio1                    Unsigned32,
                hwVOPActSetupDsDataRateProfId1             Unsigned32,
                hwVOPActSetupDsRaRatio1                    Unsigned32,
                hwVOPActSetupInpDelayProfId1               Unsigned32,
                hwVOPActSetupUsDataRateProfId2             Unsigned32,
                hwVOPActSetupUsRaRatio2                    Unsigned32,
                hwVOPActSetupDsDataRateProfId2             Unsigned32,
                hwVOPActSetupDsRaRatio2                    Unsigned32,
                hwVOPActSetupInpDelayProfId2               Unsigned32,
                hwVOPActSetupUsDataRateProfId3             Unsigned32,
                hwVOPActSetupUsRaRatio3                    Unsigned32,
                hwVOPActSetupDsDataRateProfId3             Unsigned32,
                hwVOPActSetupDsRaRatio3                    Unsigned32,
                hwVOPActSetupInpDelayProfId3               Unsigned32,
                hwVOPActSetupUsDataRateProfId4             Unsigned32,
                hwVOPActSetupUsRaRatio4                    Unsigned32,
                hwVOPActSetupDsDataRateProfId4             Unsigned32,
                hwVOPActSetupDsRaRatio4                    Unsigned32,
                hwVOPActSetupInpDelayProfId4               Unsigned32,
                hwVOPActSetupLSpectrumProfId               Unsigned32,
                hwVOPActSetupNoiseMarginProfId             Unsigned32,
                hwVOPActSetupVNoiseProfId                  Unsigned32,
                hwVOPActSetupUpboProfId                    Unsigned32,
                hwVOPActSetupDpboProfId                    Unsigned32,
                hwVOPActSetupRfiProfId                     Unsigned32,
                hwVOPActSetupInmProfId                     Unsigned32,
                hwVOPActSetupUsDataRateProf1Description    OCTET STRING,
                hwVOPActSetupDsDataRateProf1Description    OCTET STRING,
                hwVOPActSetupInpDelayProf1Description      OCTET STRING,
                hwVOPActSetupUsDataRateProf2Description    OCTET STRING,
                hwVOPActSetupDsDataRateProf2Description    OCTET STRING,
                hwVOPActSetupInpDelayProf2Description      OCTET STRING,
                hwVOPActSetupLSpectrumProfDescription      OCTET STRING,
                hwVOPActSetupUpboProfDescription           OCTET STRING,
                hwVOPActSetupDpboProfDescription           OCTET STRING,
                hwVOPActSetupRfiProfDescription            OCTET STRING,
                hwVOPActSetupNoiseMarginProfDescription    OCTET STRING,
                hwVOPActSetupVNoiseProfDescription         OCTET STRING,
                hwVOPActSetupInmProfDescription            OCTET STRING,
                hwVOPActSetupSosProfId                     Unsigned32,
                hwVOPActSetupSosProfDescription            OCTET STRING
             }


        hwVOPActSetupIndex OBJECT-TYPE
            SYNTAX Unsigned32 (1..4294967295)
            MAX-ACCESS not-accessible
            STATUS current
            DESCRIPTION
                "The hwVOPActSetupIndex identifies a row in this table. A row in this table is indexed by an ifIndex pattern."
            ::= { hwVOPActSetupEntry 1 }


        hwVOPActSetupUsDataRateProfId1 OBJECT-TYPE
            SYNTAX Unsigned32 (1..4294967294)
            MAX-ACCESS read-only
            STATUS current
            DESCRIPTION
                "This object identifies a row in hwVOPDataRateConfProfTable used for
                 configuring the upstream transmission direction of channel number #1.
                "
            ::= { hwVOPActSetupEntry 2 }


        hwVOPActSetupUsRaRatio1 OBJECT-TYPE
            SYNTAX Unsigned32 (0..100)
            MAX-ACCESS read-only
            STATUS current
            DESCRIPTION
                "Rate Adaptation Ratio.
                 The ratio (in %) that is taken into account for the bearer channel #1
                 when performing rate adaptation on upstream.
                 The ratio refers to the available data rate in excess of the Minimum Data Rate, summed over all bearer channels.
                 Also, the 100 - hwVOPActSetupUsRaRatio1 is the ratio of excess data rate assigned to
                 all other bearer channels on upstream direction.
                 The sum of rate adaptation ratios over all bearers on the same direction is equal to 100%.
                "
            ::= { hwVOPActSetupEntry 3 }


        hwVOPActSetupDsDataRateProfId1 OBJECT-TYPE
            SYNTAX Unsigned32 (1..4294967294)
            MAX-ACCESS read-only
            STATUS current
            DESCRIPTION
                "This object identifies a row in hwVOPDataRateConfProfTable used for
                 configuring the downstream transmission direction of channel #1.
                "
            ::= { hwVOPActSetupEntry 4 }


        hwVOPActSetupDsRaRatio1 OBJECT-TYPE
            SYNTAX Unsigned32 (0..100)
            MAX-ACCESS read-only
            STATUS current
            DESCRIPTION
                "Rate Adaptation Ratio.
                 The ratio (in %) that is taken into account for the bearer channel #1
                 when performing rate adaptation on downstream.
                 The ratio refers to the available data rate in excess of the Minimum Data Rate, summed over all bearer channels.
                 Also, the 100 - hwVOPActSetupDsRaRatio1 is the ratio of excess data rate assigned to
                 all other bearer channels on downstream direction.
                 The sum of rate adaptation ratios over all bearers on the same direction is equal to 100%.
                "
            ::= { hwVOPActSetupEntry 5 }


        hwVOPActSetupInpDelayProfId1 OBJECT-TYPE
            SYNTAX Unsigned32 (1..4294967294)
            MAX-ACCESS read-only
            STATUS current
            DESCRIPTION
                "This object identifies a row in hwVOPINPDelayConfProfTable used for
                 configuring the INP-Delay parameters of channel #1.
                "
            ::= { hwVOPActSetupEntry 6 }


        hwVOPActSetupUsDataRateProfId2 OBJECT-TYPE
            SYNTAX Unsigned32 (0..4294967294)
            MAX-ACCESS read-only
            STATUS current
            DESCRIPTION
                "This object identifies a row in hwVOPDataRateConfProfTable used for
                 configuring the upstream transmission direction of channel #2.
                 If channel #2 is not being used this object is set to 0.
                "
            ::= { hwVOPActSetupEntry 7 }


        hwVOPActSetupUsRaRatio2 OBJECT-TYPE
            SYNTAX Unsigned32 (0..100)
            MAX-ACCESS read-only
            STATUS current
            DESCRIPTION
                "Rate Adaptation Ratio.
                 The ratio (in %) that is taken into account for the bearer channel #2
                 when performing rate adaptation on upstream.
                 The ratio refers to the available data rate in excess of the Minimum Data Rate, summed over all bearer channels.
                 Also, the 100 - hwVOPActSetupUsRaRatio2 is the ratio of excess data rate assigned to
                 all other bearer channels on upstream direction.
                 The sum of rate adaptation ratios over all bearers on the same direction is equal to 100%.
                "
            ::= { hwVOPActSetupEntry 8 }


        hwVOPActSetupDsDataRateProfId2 OBJECT-TYPE
            SYNTAX Unsigned32 (0..4294967294)
            MAX-ACCESS read-only
            STATUS current
            DESCRIPTION
                "This object identifies a row in hwVOPDataRateConfProfTable used for
                 configuring the downstream transmission direction of channel #2.
                 If channel #2 is not being used this object is set to 0.
                "
            ::= { hwVOPActSetupEntry 9 }


        hwVOPActSetupDsRaRatio2 OBJECT-TYPE
            SYNTAX Unsigned32 (0..100)
            MAX-ACCESS read-only
            STATUS current
            DESCRIPTION
                "Rate Adaptation Ratio.
                 The ratio (in %) that is taken into account for the bearer channel #2
                 when performing rate adaptation on downstream.
                 The ratio refers to the available data rate in excess of the Minimum Data Rate, summed over all bearer channels.
                 Also, the 100 - hwVOPActSetupDsRaRatio2 is the ratio of excess data rate assigned to
                 all other bearer channels on downstream direction.
                 The sum of rate adaptation ratios over all bearers on the same direction is equal to 100%.
                "
            ::= { hwVOPActSetupEntry 10 }


        hwVOPActSetupInpDelayProfId2 OBJECT-TYPE
            SYNTAX Unsigned32 (0..4294967294)
            MAX-ACCESS read-only
            STATUS current
            DESCRIPTION
                "This object identifies a row in hwVOPINPDelayConfProfTable used for
                 configuring the INP-Delay parameters of channel #2
                 If channel #2 is not being used this object is set to 0.
                "
            ::= { hwVOPActSetupEntry 11 }


        hwVOPActSetupUsDataRateProfId3 OBJECT-TYPE
            SYNTAX Unsigned32 (0..4294967294)
            MAX-ACCESS read-only
            STATUS current
            DESCRIPTION
                "This object identifies a row in hwVOPDataRateConfProfTable used for
                 configuring the upstream transmission direction of channel #3.
                 If channel #3 is not being used this object is set to 0.
                "
            ::= { hwVOPActSetupEntry 12 }


        hwVOPActSetupUsRaRatio3 OBJECT-TYPE
            SYNTAX Unsigned32 (0..100)
            MAX-ACCESS read-only
            STATUS current
            DESCRIPTION
                "Rate Adaptation Ratio.
                 The ratio (in %) that is taken into account for the bearer channel #3
                 when performing rate adaptation on upstream.
                 The ratio refers to the available data rate in excess of the Minimum Data Rate, summed over all bearer channels.
                 Also, the 100 - hwVOPActSetupUsRaRatio3 is the ratio of excess data rate assigned to
                 all other bearer channels on upstream direction.
                 The sum of rate adaptation ratios over all bearers on the same direction is equal to 100%.
                "
            ::= { hwVOPActSetupEntry 13 }


        hwVOPActSetupDsDataRateProfId3 OBJECT-TYPE
            SYNTAX Unsigned32 (0..4294967294)
            MAX-ACCESS read-only
            STATUS current
            DESCRIPTION
                "This object identifies a row in hwVOPDataRateConfProfTable used for
                 configuring the downstream transmission direction of channel #3.
                 If channel #3 is not being used this object is set to 0.
                "
            ::= { hwVOPActSetupEntry 14 }


        hwVOPActSetupDsRaRatio3 OBJECT-TYPE
            SYNTAX Unsigned32 (0..100)
            MAX-ACCESS read-only
            STATUS current
            DESCRIPTION
                "Rate Adaptation Ratio.
                 The ratio (in %) that is taken into account for the bearer channel #3
                 when performing rate adaptation on downstream.
                 The ratio refers to the available data rate in excess of the Minimum Data Rate, summed over all bearer channels.
                 Also, the 100 - hwVOPActSetupDsRaRatio3 is the ratio of excess data rate assigned to
                 all other bearer channels on downstream direction.
                 The sum of rate adaptation ratios over all bearers on the same direction is equal to 100%.
                "
            ::= { hwVOPActSetupEntry 15 }


        hwVOPActSetupInpDelayProfId3 OBJECT-TYPE
            SYNTAX Unsigned32 (0..4294967294)
            MAX-ACCESS read-only
            STATUS current
            DESCRIPTION
                "This object identifies a row in hwVOPINPDelayConfProfTable used for
                 configuring the INP-Delay parameters of channel #3
                 If channel #3 is not being used this object is set to 0.
                "
            ::= { hwVOPActSetupEntry 16 }


        hwVOPActSetupUsDataRateProfId4 OBJECT-TYPE
            SYNTAX Unsigned32 (0..4294967294)
            MAX-ACCESS read-only
            STATUS current
            DESCRIPTION
                "This object identifies a row in hwVOPDataRateConfProfTable used for
                 configuring the upstream transmission direction of channel #4.
                 If channel #4 is not being used this object is set to 0.
                "
            ::= { hwVOPActSetupEntry 17 }


        hwVOPActSetupUsRaRatio4 OBJECT-TYPE
            SYNTAX Unsigned32 (0..100)
            MAX-ACCESS read-only
            STATUS current
            DESCRIPTION
                "Rate Adaptation Ratio.
                 The ratio (in %) that is taken into account for the bearer channel #4
                 when performing rate adaptation on upstream.
                 The ratio refers to the available data rate in excess of the Minimum Data Rate, summed over all bearer channels.
                 Also, the 100 - hwVOPActSetupUsRaRatio4 is the ratio of excess data rate assigned to
                 all other bearer channels on upstream direction.
                 The sum of rate adaptation ratios over all bearers on the same direction is equal to 100%.
                "
            ::= { hwVOPActSetupEntry 18 }


        hwVOPActSetupDsDataRateProfId4 OBJECT-TYPE
            SYNTAX Unsigned32 (0..4294967294)
            MAX-ACCESS read-only
            STATUS current
            DESCRIPTION
                "This object identifies a row in hwVOPDataRateConfProfTable used for
                 configuring the downstream transmission direction of channel #4.
                 If channel #4 is not being used this object is set to 0.
                "
            ::= { hwVOPActSetupEntry 19 }


        hwVOPActSetupDsRaRatio4 OBJECT-TYPE
            SYNTAX Unsigned32 (0..100)
            MAX-ACCESS read-only
            STATUS current
            DESCRIPTION
                "Rate Adaptation Ratio.
                 The ratio (in %) that is taken into account for the bearer channel #4
                 when performing rate adaptation on downstream.
                 The ratio refers to the available data rate in excess of the Minimum Data Rate, summed over all bearer channels.
                 Also, the 100 - hwVOPActSetupDsRaRatio4 is the ratio of excess data rate assigned to
                 all other bearer channels on downstream direction.
                 The sum of rate adaptation ratios over all bearers on the same direction is equal to 100%.
                "
            ::= { hwVOPActSetupEntry 20 }


        hwVOPActSetupInpDelayProfId4 OBJECT-TYPE
            SYNTAX Unsigned32 (0..4294967294)
            MAX-ACCESS read-only
            STATUS current
            DESCRIPTION
                "This object identifies a row in hwVOPINPDelayConfProfTable used for
                 configuring the INP-Delay parameters of channel #4
                 If channel #4 is not being used this object is set to 0.
                "
            ::= { hwVOPActSetupEntry 21 }


        hwVOPActSetupLSpectrumProfId OBJECT-TYPE
            SYNTAX Unsigned32 (1..4294967294)
            MAX-ACCESS read-only
            STATUS current
            DESCRIPTION
                "This object identifies a row in hwVOPLineSpectrumConfProfTable used for
                 configuring the spectrum parameters of the respective xDSL line.
                "
            ::= { hwVOPActSetupEntry 22 }


        hwVOPActSetupNoiseMarginProfId OBJECT-TYPE
            SYNTAX Unsigned32 (1..4294967294)
            MAX-ACCESS read-only
            STATUS current
            DESCRIPTION
                "This object identifies a row in hwVOPSNRMarginConfProfTable used for
                 configuring the noise margin related parameters of the respective xDSL line.
                "
            ::= { hwVOPActSetupEntry 23 }


        hwVOPActSetupVNoiseProfId OBJECT-TYPE
            SYNTAX Unsigned32 (1..4294967294)
            MAX-ACCESS read-only
            STATUS current
            DESCRIPTION
                "This object identifies a row in hwVOPVirtualNoiseConfProfTable used for
                 configuring the virtual noise related parameters of the respective xDSL line.
                "
            ::= { hwVOPActSetupEntry 24 }


        hwVOPActSetupUpboProfId OBJECT-TYPE
            SYNTAX Unsigned32 (0..4294967294)
            MAX-ACCESS read-only
            STATUS current
            DESCRIPTION
                "This object identifies a row in hwVOPUPBOConfProfTable used for
                 configuring the upstream power back-off related parameters of the respective xDSL line.
                 If this leaf is not support this object should be set to 0.
                "
            ::= { hwVOPActSetupEntry 25 }


        hwVOPActSetupDpboProfId OBJECT-TYPE
            SYNTAX Unsigned32 (1..4294967294)
            MAX-ACCESS read-only
            STATUS current
            DESCRIPTION
                "This object identifies a row in hwVOPDPBOConfProfTable used for
                 configuring the downstream power back-off related parameters of the respective xDSL line.
                "
            ::= { hwVOPActSetupEntry 26 }


        hwVOPActSetupRfiProfId OBJECT-TYPE
            SYNTAX Unsigned32 (1..4294967294)
            MAX-ACCESS read-only
            STATUS current
            DESCRIPTION
                "This object identifies a row in hwVOPRFIConfProfTable used for
                 configuring the RFI notches related parameters of the respective xDSL line.
                "
            ::= { hwVOPActSetupEntry 27 }

        hwVOPActSetupInmProfId OBJECT-TYPE
            SYNTAX Unsigned32 (1..4294967294)
            MAX-ACCESS read-only
            STATUS current
            DESCRIPTION
                "This object identifies a row in hwVOPINMConfProfTable used for
                 configuring the impulse noise monitoring parameters of the respective xDSL line.
                "
            ::= { hwVOPActSetupEntry 28 }            

        hwVOPActSetupUsDataRateProf1Description OBJECT-TYPE
            SYNTAX OCTET STRING (SIZE (0..128))
            MAX-ACCESS read-only
            STATUS current
            DESCRIPTION
                "This object identifies a row in hwVOPDataRateConfProfTable used for
                 configuring the upstream transmission direction of channel number #1.
                "
            ::= { hwVOPActSetupEntry 29 }
        
        hwVOPActSetupDsDataRateProf1Description OBJECT-TYPE
            SYNTAX OCTET STRING (SIZE (0..128))
            MAX-ACCESS read-only
            STATUS current
            DESCRIPTION
                "This object identifies a row in hwVOPDataRateConfProfTable used for
                 configuring the downstream transmission direction of channel #1.
                "
            ::= { hwVOPActSetupEntry 30 }
        
        hwVOPActSetupInpDelayProf1Description OBJECT-TYPE
            SYNTAX OCTET STRING (SIZE (0..128))
            MAX-ACCESS read-only
            STATUS current
            DESCRIPTION
                "This object identifies a row in hwVOPINPDelayConfProfTable used for
                 configuring the INP-Delay parameters of channel #1.
                "
            ::= { hwVOPActSetupEntry 31 }
        
        hwVOPActSetupUsDataRateProf2Description OBJECT-TYPE
            SYNTAX OCTET STRING (SIZE (0..128))
            MAX-ACCESS read-only
            STATUS current
            DESCRIPTION
                "This object identifies a row in hwVOPDataRateConfProfTable used for
                 configuring the upstream transmission direction of channel #2.
                "
            ::= { hwVOPActSetupEntry 32 }
        
        hwVOPActSetupDsDataRateProf2Description OBJECT-TYPE
            SYNTAX OCTET STRING (SIZE (0..128))
            MAX-ACCESS read-only
            STATUS current
            DESCRIPTION
                "This object identifies a row in hwVOPDataRateConfProfTable used for
                 configuring the downstream transmission direction of channel #2.
                "
            ::= { hwVOPActSetupEntry 33 }
        
        hwVOPActSetupInpDelayProf2Description OBJECT-TYPE
            SYNTAX OCTET STRING (SIZE (0..128))
            MAX-ACCESS read-only
            STATUS current
            DESCRIPTION
                "This object identifies a row in hwVOPINPDelayConfProfTable used for
                 configuring the INP-Delay parameters of channel #2
                "
            ::= { hwVOPActSetupEntry 34 }
        
        hwVOPActSetupLSpectrumProfDescription OBJECT-TYPE
            SYNTAX OCTET STRING (SIZE (0..128))
            MAX-ACCESS read-only
            STATUS current
            DESCRIPTION
                "This object identifies a row in hwVOPLineSpectrumConfProfTable used for
                 configuring the spectrum parameters of the respective xDSL line.
                "
            ::= { hwVOPActSetupEntry 35 }
        
        hwVOPActSetupUpboProfDescription OBJECT-TYPE
            SYNTAX OCTET STRING (SIZE (0..128))
            MAX-ACCESS read-only
            STATUS current
            DESCRIPTION
                "This object identifies a row in hwVOPUPBOConfProfTable used for
                 configuring the upstream power back-off related parameters of the respective xDSL line.
                 If this leaf is not support this object should be set to 0.
                "
            ::= { hwVOPActSetupEntry 36 }
        
        hwVOPActSetupDpboProfDescription OBJECT-TYPE
            SYNTAX OCTET STRING (SIZE (0..128))
            MAX-ACCESS read-only
            STATUS current
            DESCRIPTION
                "This object identifies a row in hwVOPDPBOConfProfTable used for
                 configuring the downstream power back-off related parameters of the respective xDSL line.
                "
            ::= { hwVOPActSetupEntry 37 }
        
        hwVOPActSetupRfiProfDescription OBJECT-TYPE
            SYNTAX OCTET STRING (SIZE (0..128))
            MAX-ACCESS read-only
            STATUS current
            DESCRIPTION
                "This object identifies a row in hwVOPRFIConfProfTable used for
                 configuring the RFI notches related parameters of the respective xDSL line.
                "
            ::= { hwVOPActSetupEntry 38 }
        
        hwVOPActSetupNoiseMarginProfDescription OBJECT-TYPE
            SYNTAX OCTET STRING (SIZE (0..128))
            MAX-ACCESS read-only
            STATUS current
            DESCRIPTION
                "This object identifies a row in hwVOPSNRMarginConfProfTable used for
                 configuring the noise margin related parameters of the respective xDSL line.
                "
            ::= { hwVOPActSetupEntry 39 }
        
        hwVOPActSetupVNoiseProfDescription OBJECT-TYPE
            SYNTAX OCTET STRING (SIZE (0..128))
            MAX-ACCESS read-only
            STATUS current
            DESCRIPTION
                "This object identifies a row in hwVOPVirtualNoiseConfProfTable used for
                 configuring the virtual noise related parameters of the respective xDSL line.
                "
            ::= { hwVOPActSetupEntry 40 }
        
        hwVOPActSetupInmProfDescription OBJECT-TYPE
            SYNTAX OCTET STRING (SIZE (0..128))
            MAX-ACCESS read-only
            STATUS current
            DESCRIPTION
                "This object identifies a row in hwVOPINMConfProfTable used for
                 configuring the impulse noise monitoring parameters of the respective xDSL line.
                "
            ::= { hwVOPActSetupEntry 41 }
            
        hwVOPActSetupSosProfId OBJECT-TYPE
            SYNTAX Unsigned32 (1..4294967294)
            MAX-ACCESS read-only
            STATUS current
            DESCRIPTION
                "This object identifies a row in hwVOPSosConfProfTable used for
                 configuring the save our showtime parameters of the respective xDSL line.
                 If this leaf is not support this object should be set to 0.
                "
            ::= { hwVOPActSetupEntry 42 } 
            
        hwVOPActSetupSosProfDescription OBJECT-TYPE
            SYNTAX OCTET STRING (SIZE (0..128))
            MAX-ACCESS read-only
            STATUS current
            DESCRIPTION
                "This object identifies a row in hwVOPSosConfProfTable used for
                 configuring the save our showtime parameters of the respective xDSL line.
                 If this leaf is not support this object should be set to 0.
                "
            ::= { hwVOPActSetupEntry 43 }                        
        
        --   hwOntVdsl2VOPSetupTable
        hwOntVdsl2VOPSetupTable OBJECT-TYPE
            SYNTAX SEQUENCE OF HwOntVdsl2VOPSetupEntry
            MAX-ACCESS not-accessible
            STATUS current
            DESCRIPTION
                "This table contains a collection of profile indices that construct a Vector Of Profiles (VoP).
                 This table is used in both 'direct' and 'indirect' attachment-methods of VoP to xDSL lines.
                 
                 In case the implementation uses 'indirect' attachment-method of VoP to xDSL lines then a default profile
                 with an index number 1 will always exist and its objects will be set to default values.
                 The indexes of this table are ifIndex, hwVOPOntObjectIndex and hwVOPOntVdsl2Portid.
                "
            REFERENCE
                "Broadband Forum TR-165, paragraph Appendix I"
            ::= { hwVOPSetup 4 }

        hwOntVdsl2VOPSetupEntry OBJECT-TYPE
            SYNTAX HwOntVdsl2VOPSetupEntry
            MAX-ACCESS not-accessible
            STATUS current
            DESCRIPTION
                "This table contains a collection of profile indices that construct a Vector Of Profiles (VoP).
                 This table is used in both 'direct' and 'indirect' attachment-methods of VoP to xDSL lines.
                 
                 In case the implementation uses 'indirect' attachment-method of VoP to xDSL lines then a default profile
                 with an index number 1 will always exist and its objects will be set to default values.
                 The indexes of this entry are ifIndex, hwVOPOntObjectIndex and hwVOPOntVdsl2Portid.
                "
           INDEX  { ifIndex,
                    hwVOPOntObjectIndex,
                    hwVOPOntUniPhyType,
                    hwVOPOntVdsl2Portid }
            ::= { hwOntVdsl2VOPSetupTable 1 }

        HwOntVdsl2VOPSetupEntry ::=
            SEQUENCE {
                hwVOPOntObjectIndex                                    Integer32,
                hwVOPOntUniPhyType                                     INTEGER,
                hwVOPOntVdsl2Portid                                    Integer32,
                hwOntVdsl2VOPSetupUsDataRateProfId1                    Unsigned32,
                hwOntVdsl2VOPSetupUsRaRatio1                           Unsigned32,
                hwOntVdsl2VOPSetupDsDataRateProfId1                    Unsigned32,
                hwOntVdsl2VOPSetupDsRaRatio1                           Unsigned32,
                hwOntVdsl2VOPSetupInpDelayProfId1                      Unsigned32,
                hwOntVdsl2VOPSetupUsDataRateProfId2                    Unsigned32,
                hwOntVdsl2VOPSetupUsRaRatio2                           Unsigned32,
                hwOntVdsl2VOPSetupDsDataRateProfId2                    Unsigned32,
                hwOntVdsl2VOPSetupDsRaRatio2                           Unsigned32,
                hwOntVdsl2VOPSetupInpDelayProfId2                      Unsigned32,
                hwOntVdsl2VOPSetupUsDataRateProfId3                    Unsigned32,
                hwOntVdsl2VOPSetupUsRaRatio3                           Unsigned32,
                hwOntVdsl2VOPSetupDsDataRateProfId3                    Unsigned32,
                hwOntVdsl2VOPSetupDsRaRatio3                           Unsigned32,
                hwOntVdsl2VOPSetupInpDelayProfId3                      Unsigned32,
                hwOntVdsl2VOPSetupUsDataRateProfId4                    Unsigned32,
                hwOntVdsl2VOPSetupUsRaRatio4                           Unsigned32,
                hwOntVdsl2VOPSetupDsDataRateProfId4                    Unsigned32,
                hwOntVdsl2VOPSetupDsRaRatio4                           Unsigned32,
                hwOntVdsl2VOPSetupInpDelayProfId4                      Unsigned32,
                hwOntVdsl2VOPSetupLSpectrumProfId                      Unsigned32,
                hwOntVdsl2VOPSetupUpboProfId                           Unsigned32,
                hwOntVdsl2VOPSetupDpboProfId                           Unsigned32,
                hwOntVdsl2VOPSetupRfiProfId                            Unsigned32,
                hwOntVdsl2VOPSetupNoiseMarginProfId                    Unsigned32,
                hwOntVdsl2VOPSetupVNoiseProfId                         Unsigned32,
                hwOntVdsl2VOPSetupInmProfId                            Unsigned32,
                hwOntVdsl2VOPLineAdminStatus                           INTEGER,
                hwOntVdsl2VOPSetupUsDataRateProf1Description           OCTET STRING,
		hwOntVdsl2VOPSetupDsDataRateProf1Description           OCTET STRING, 
		hwOntVdsl2VOPSetupInpDelayProf1Description             OCTET STRING, 
		hwOntVdsl2VOPSetupUsDataRateProf2Description           OCTET STRING, 
		hwOntVdsl2VOPSetupDsDataRateProf2Description           OCTET STRING, 
		hwOntVdsl2VOPSetupInpDelayProf2Description             OCTET STRING, 
		hwOntVdsl2VOPSetupUsDataRateProf3Description           OCTET STRING, 
		hwOntVdsl2VOPSetupDsDataRateProf3Description           OCTET STRING, 
		hwOntVdsl2VOPSetupInpDelayProf3Description             OCTET STRING, 
		hwOntVdsl2VOPSetupUsDataRateProf4Description           OCTET STRING, 
		hwOntVdsl2VOPSetupDsDataRateProf4Description           OCTET STRING, 
		hwOntVdsl2VOPSetupInpDelayProf4Description             OCTET STRING, 
		hwOntVdsl2VOPSetupLSpectrumProfDescription             OCTET STRING, 
		hwOntVdsl2VOPSetupUpboProfDescription                  OCTET STRING, 
		hwOntVdsl2VOPSetupDpboProfDescription                  OCTET STRING, 
		hwOntVdsl2VOPSetupRfiProfDescription                   OCTET STRING, 
		hwOntVdsl2VOPSetupNoiseMarginProfDescription           OCTET STRING, 
		hwOntVdsl2VOPSetupVNoiseProfDescription                OCTET STRING, 
		hwOntVdsl2VOPSetupInmProfDescription                   OCTET STRING
	        }

        hwVOPOntObjectIndex  OBJECT-TYPE
            SYNTAX      Integer32
            MAX-ACCESS  not-accessible
            STATUS      current
            DESCRIPTION
                "ONT ID.
                "
            ::= { hwOntVdsl2VOPSetupEntry 1 }
        
        hwVOPOntUniPhyType  OBJECT-TYPE
            SYNTAX      INTEGER{
                vdsl(37)
            }
            MAX-ACCESS  not-accessible
            STATUS      current
            DESCRIPTION
                "This object indicates the physical type of ONT UNI.
 	         Options:
 	         1. vdsl(37)           - VDSL
                "
            ::= { hwOntVdsl2VOPSetupEntry 2 }
            
        hwVOPOntVdsl2Portid  OBJECT-TYPE
            SYNTAX      Integer32
            MAX-ACCESS  not-accessible
            STATUS      current
            DESCRIPTION
                "The ONT VDSL port ID.
                "
            ::= { hwOntVdsl2VOPSetupEntry 3 }

        hwOntVdsl2VOPSetupUsDataRateProfId1 OBJECT-TYPE
            SYNTAX Unsigned32 (1..4294967294)
            MAX-ACCESS read-create
            STATUS current
            DESCRIPTION
                "This object identifies a row in hwVOPDataRateConfProfTable used for
                 configuring the upstream transmission direction of channel #1.

                 This object has read-write accessibility if 'direct' attachment-method of VoP to xDSL lines is implemented.
                "
            DEFVAL { 1 }
            ::= { hwOntVdsl2VOPSetupEntry 4 }


        hwOntVdsl2VOPSetupUsRaRatio1 OBJECT-TYPE
            SYNTAX Unsigned32 (0..100)
            MAX-ACCESS read-create
            STATUS current
            DESCRIPTION
                "Rate Adaptation Ratio.
                 The ratio (in %) that should be taken into account for the bearer channel #1
                 when performing rate adaptation on upstream.
                 The ratio refers to the available data rate in excess of the Minimum Data Rate, summed over all bearer channels.

                 Also, the 100 - hwOntVdsl2VOPSetupUsRaRatio1 is the ratio of excess data rate to
                 be assigned to all other bearer channels on upstream direction.
                 The sum of rate adaptation ratios over all bearers on the same direction shall be equal to 100%.

                 This object has read-write accessibility if 'direct' attachment-method of VoP to xDSL lines is implemented.
                "
            DEFVAL { 100 }
            ::= { hwOntVdsl2VOPSetupEntry 5 }


        hwOntVdsl2VOPSetupDsDataRateProfId1 OBJECT-TYPE
            SYNTAX Unsigned32 (1..4294967294)
            MAX-ACCESS read-create
            STATUS current
            DESCRIPTION
                "This object identifies a row in hwVOPDataRateConfProfTable used for
                 configuring the downstream transmission direction of channel #1.

                 This object has read-write accessibility if 'direct' attachment-method of VoP to xDSL lines is implemented.
                "
            DEFVAL { 2 }
            ::= { hwOntVdsl2VOPSetupEntry 6 }


        hwOntVdsl2VOPSetupDsRaRatio1 OBJECT-TYPE
            SYNTAX Unsigned32 (0..100)
            MAX-ACCESS read-create
            STATUS current
            DESCRIPTION
                "Rate Adaptation Ratio.
                 The ratio (in %) that should be taken into account for the bearer channel #1
                 when performing rate adaptation on downstream.
                 The ratio refers to the available data rate in excess of the Minimum Data Rate, summed over all bearer channels.

                 Also, the 100 - hwOntVdsl2VOPSetupDsRaRatio1 is the ratio of excess data rate to
                 be assigned to all other bearer channels on downstream direction.
                 The sum of rate adaptation ratios over all bearers on the same direction shall be equal to 100%.

                 This object has read-write accessibility if 'direct' attachment-method of VoP to xDSL lines is implemented.
                "
            DEFVAL { 100 }
            ::= { hwOntVdsl2VOPSetupEntry 7 }


        hwOntVdsl2VOPSetupInpDelayProfId1 OBJECT-TYPE
            SYNTAX Unsigned32 (1..4294967294)
            MAX-ACCESS read-create
            STATUS current
            DESCRIPTION
                "This object identifies a row in hwVOPINPDelayConfProfTable used for
                 configuring the INP-Delay parameters of channel #1.

                 This object has read-write accessibility if 'direct' attachment-method of VoP to xDSL lines is implemented.
                "
            DEFVAL { 1 }
            ::= { hwOntVdsl2VOPSetupEntry 8 }


        hwOntVdsl2VOPSetupUsDataRateProfId2 OBJECT-TYPE
            SYNTAX Unsigned32 (0..4294967294)
            MAX-ACCESS read-create
            STATUS current
            DESCRIPTION
                "This object identifies a row in hwVOPDataRateConfProfTable used for
                 configuring the upstream transmission direction of channel #2.
                 If channel #2 is not being used this object should be set to 0.

                 This object has read-write accessibility if 'direct' attachment-method of VoP to xDSL lines is implemented.
                "
            DEFVAL { 0 }
            ::= { hwOntVdsl2VOPSetupEntry 9 }


        hwOntVdsl2VOPSetupUsRaRatio2 OBJECT-TYPE
            SYNTAX Unsigned32 (0..100)
            MAX-ACCESS read-create
            STATUS current
            DESCRIPTION
                "Rate Adaptation Ratio.
                 The ratio (in %) that should be taken into account for the bearer channel #2
                 when performing rate adaptation on upstream.
                 The ratio refers to the available data rate in excess of the Minimum Data Rate, summed over all bearer channels.

                 Also, the 100 - hwOntVdsl2VOPSetupUsRaRatio2 is the ratio of excess data rate to
                 be assigned to all other bearer channels on upstream direction.
                 The sum of rate adaptation ratios over all bearers on the same direction shall be equal to 100%.

                 This object has read-write accessibility if 'direct' attachment-method of VoP to xDSL lines is implemented.
                "
            DEFVAL { 0 }
            ::= { hwOntVdsl2VOPSetupEntry 10 }


        hwOntVdsl2VOPSetupDsDataRateProfId2 OBJECT-TYPE
            SYNTAX Unsigned32 (0..4294967294)
            MAX-ACCESS read-create
            STATUS current
            DESCRIPTION
                "This object identifies a row in hwVOPDataRateConfProfTable used for
                 configuring the downstream transmission direction of channel #2.
                 If channel #2 is not being used this object should be set to 0.

                 This object has read-write accessibility if 'direct' attachment-method of VoP to xDSL lines is implemented.
                "
            DEFVAL { 0 }
            ::= { hwOntVdsl2VOPSetupEntry 11 }


        hwOntVdsl2VOPSetupDsRaRatio2 OBJECT-TYPE
            SYNTAX Unsigned32 (0..100)
            MAX-ACCESS read-create
            STATUS current
            DESCRIPTION
                "Rate Adaptation Ratio.
                 The ratio (in %) that should be taken into account for the bearer channel #2
                 when performing rate adaptation on downstream.
                 The ratio refers to the available data rate in excess of the Minimum Data Rate, summed over all bearer channels.

                 Also, the 100 - hwOntVdsl2VOPSetupDsRaRatio2 is the ratio of excess data rate to
                 be assigned to all other bearer channels on downstream direction.
                 The sum of rate adaptation ratios over all bearers on the same direction shall be equal to 100%.

                 This object has read-write accessibility if 'direct' attachment-method of VoP to xDSL lines is implemented.
                "
            DEFVAL { 0 }
            ::= { hwOntVdsl2VOPSetupEntry 12 }


        hwOntVdsl2VOPSetupInpDelayProfId2 OBJECT-TYPE
            SYNTAX Unsigned32 (0..4294967294)
            MAX-ACCESS read-create
            STATUS current
            DESCRIPTION
                "This object identifies a row in hwVOPINPDelayConfProfTable used for
                 configuring the INP-Delay parameters of channel #2.
                 If channel #2 is not being used this object should be set to 0.

                 This object has read-write accessibility if 'direct' attachment-method of VoP to xDSL lines is implemented.
                "
            DEFVAL { 0 }
            ::= { hwOntVdsl2VOPSetupEntry 13 }


        hwOntVdsl2VOPSetupUsDataRateProfId3 OBJECT-TYPE
            SYNTAX Unsigned32 (0..4294967294)
            MAX-ACCESS read-create
            STATUS current
            DESCRIPTION
                "This object identifies a row in hwVOPDataRateConfProfTable used for
                 configuring the upstream transmission direction of channel #3.
                 If channel #3 is not being used this object should be set to 0.

                 This object has read-write accessibility if 'direct' attachment-method of VoP to xDSL lines is implemented.
                 Currently, only support channel #1 and channel #2, thus this leaf is not supported.
               "
            DEFVAL { 0 }
            ::= { hwOntVdsl2VOPSetupEntry 14 }


        hwOntVdsl2VOPSetupUsRaRatio3 OBJECT-TYPE
            SYNTAX Unsigned32 (0..100)
            MAX-ACCESS read-create
            STATUS current
            DESCRIPTION
                "Rate Adaptation Ratio.
                 The ratio (in %) that should be taken into account for the bearer channel #3
                 when performing rate adaptation on upstream.
                 The ratio refers to the available data rate in excess of the Minimum Data Rate, summed over all bearer channels.
                 Also, the 100 - hwOntVdsl2VOPSetupUsRaRatio3 is the ratio of excess data rate to
                 be assigned to all other bearer channels on upstream direction.
                 The sum of rate adaptation ratios over all bearers on the same direction shall be equal to 100%.

                 This object has read-write accessibility if 'direct' attachment-method of VoP to xDSL lines is implemented.
                 Currently, only support channel #1 and channel #2, thus this leaf is not supported.
                "
            DEFVAL { 0 }
            ::= { hwOntVdsl2VOPSetupEntry 15 }


        hwOntVdsl2VOPSetupDsDataRateProfId3 OBJECT-TYPE
            SYNTAX Unsigned32 (0..4294967294)
            MAX-ACCESS read-create
            STATUS current
            DESCRIPTION
                "This object identifies a row in hwVOPDataRateConfProfTable used for
                 configuring the downstream transmission direction of channel #3.
                 If channel #3 is not being used this object should be set to 0.

                 This object has read-write accessibility if 'direct' attachment-method of VoP to xDSL lines is implemented.
                 Currently, only support channel #1 and channel #2, thus this leaf is not supported.
                "
            DEFVAL { 0 }
            ::= { hwOntVdsl2VOPSetupEntry 16 }


        hwOntVdsl2VOPSetupDsRaRatio3 OBJECT-TYPE
            SYNTAX Unsigned32 (0..100)
            MAX-ACCESS read-create
            STATUS current
            DESCRIPTION
                "Rate Adaptation Ratio.
                 The ratio (in %) that should be taken into account for the bearer channel #3
                 when performing rate adaptation on downstream.
                 The ratio refers to the available data rate in excess of the Minimum Data Rate, summed over all bearer channels.

                 Also, the 100 - hwOntVdsl2VOPSetupDsRaRatio3 is the ratio of excess data rate to
                 be assigned to all other bearer channels on downstream direction.
                 The sum of rate adaptation ratios over all bearers on the same direction shall be equal to 100%.

                 This object has read-write accessibility if 'direct' attachment-method of VoP to xDSL lines is implemented.
                 Currently, only support channel #1 and channel #2, thus this leaf is not supported.
                "
            DEFVAL { 0 }
            ::= { hwOntVdsl2VOPSetupEntry 17 }


        hwOntVdsl2VOPSetupInpDelayProfId3 OBJECT-TYPE
            SYNTAX Unsigned32 (0..4294967294)
            MAX-ACCESS read-create
            STATUS current
            DESCRIPTION
                "This object identifies a row in hwVOPINPDelayConfProfTable used for
                 configuring the INP-Delay parameters of channel #3.
                 If channel #3 is not being used this object should be set to 0.

                 This object has read-write accessibility if 'direct' attachment-method of VoP to xDSL lines is implemented.
                 Currently, only support channel #1 and channel #2, thus this leaf is not supported.
               "
            DEFVAL { 0 }
            ::= { hwOntVdsl2VOPSetupEntry 18 }


        hwOntVdsl2VOPSetupUsDataRateProfId4 OBJECT-TYPE
            SYNTAX Unsigned32 (0..4294967294)
            MAX-ACCESS read-create
            STATUS current
            DESCRIPTION
                "This object identifies a row in hwVOPDataRateConfProfTable used for
                 configuring the upstream transmission direction of channel #4.
                 If channel #4 is not being used this object should be set to 0.

                 This object has read-write accessibility if 'direct' attachment-method of VoP to xDSL lines is implemented.
                 Currently, only support channel #1 and channel #2, thus this leaf is not supported.
                "
            DEFVAL { 0 }
            ::= { hwOntVdsl2VOPSetupEntry 19 }


        hwOntVdsl2VOPSetupUsRaRatio4 OBJECT-TYPE
            SYNTAX Unsigned32 (0..100)
            MAX-ACCESS read-create
            STATUS current
            DESCRIPTION
                "Rate Adaptation Ratio.
                 The ratio (in %) that should be taken into account for the bearer channel #4
                 when performing rate adaptation on upstream.
                 The ratio refers to the available data rate in excess of the Minimum Data Rate, summed over all bearer channels.
                 Also, the 100 - hwOntVdsl2VOPSetupUsRaRatio4 is the ratio of excess data rate to
                 be assigned to all other bearer channels on upstream direction.
                 The sum of rate adaptation ratios over all bearers on the same direction shall be equal to 100%.

                 This object has read-write accessibility if 'direct' attachment-method of VoP to xDSL lines is implemented.
                  Currently, only support channel #1 and channel #2, thus this leaf is not supported.
               "
            DEFVAL { 0 }
            ::= { hwOntVdsl2VOPSetupEntry 20 }


        hwOntVdsl2VOPSetupDsDataRateProfId4 OBJECT-TYPE
            SYNTAX Unsigned32 (0..4294967294)
            MAX-ACCESS read-create
            STATUS current
            DESCRIPTION
                "This object identifies a row in hwVOPDataRateConfProfTable used for
                 configuring the downstream transmission direction of channel #4.
                 If channel #4 is not being used this object should be set to 0.

                 This object has read-write accessibility if 'direct' attachment-method of VoP to xDSL lines is implemented.
                 Currently, only support channel #1 and channel #2, thus this leaf is not supported.
                "
            DEFVAL { 0 }
            ::= { hwOntVdsl2VOPSetupEntry 21 }


        hwOntVdsl2VOPSetupDsRaRatio4 OBJECT-TYPE
            SYNTAX Unsigned32 (0..100)
            MAX-ACCESS read-create
            STATUS current
            DESCRIPTION
                "Rate Adaptation Ratio.
                 The ratio (in %) that should be taken into account for the bearer channel #4
                 when performing rate adaptation on downstream.
                 The ratio refers to the available data rate in excess of the Minimum Data Rate, summed over all bearer channels.
                 Also, the 100 - hwOntVdsl2VOPSetupDsRaRatio4 is the ratio of excess data rate to
                 be assigned to all other bearer channels on downstream direction.
                 The sum of rate adaptation ratios over all bearers on the same direction shall be equal to 100%.

                 This object has read-write accessibility if 'direct' attachment-method of VoP to xDSL lines is implemented.
                 Currently, only support channel #1 and channel #2, thus this leaf is not supported.
                "
            DEFVAL { 0 }
            ::= { hwOntVdsl2VOPSetupEntry 22 }


        hwOntVdsl2VOPSetupInpDelayProfId4 OBJECT-TYPE
            SYNTAX Unsigned32 (0..4294967294)
            MAX-ACCESS read-create
            STATUS current
            DESCRIPTION
                "This object identifies a row in hwVOPINPDelayConfProfTable used for
                 configuring the INP-Delay parameters of channel #4.
                 If channel #4 is not being used this object should be set to 0.

                 This object has read-write accessibility if 'direct' attachment-method of VoP to xDSL lines is implemented.
                 Currently, only support channel #1 and channel #2, thus this leaf is not supported.                 
                "
            DEFVAL { 0 }
            ::= { hwOntVdsl2VOPSetupEntry 23 }


        hwOntVdsl2VOPSetupLSpectrumProfId OBJECT-TYPE
            SYNTAX Unsigned32 (1..4294967294)
            MAX-ACCESS read-create
            STATUS current
            DESCRIPTION
                "This object identifies a row in hwVOPLineSpectrumConfProfTable used for
                 configuring the spectrum parameters of the respective xDSL line.

                 This object has read-write accessibility if 'direct' attachment-method of VoP to xDSL lines is implemented.
                "
            DEFVAL { 1 }
            ::= { hwOntVdsl2VOPSetupEntry 24 }


        hwOntVdsl2VOPSetupUpboProfId OBJECT-TYPE
            SYNTAX Unsigned32 (0..4294967294)
            MAX-ACCESS read-create
            STATUS current
            DESCRIPTION
                "This object identifies a row in hwVOPUPBOConfProfTable used for
                 configuring the upstream power back-off related parameters of the respective xDSL line.
                 If this leaf is not support this object should be set to 0.
                 This object has read-write accessibility if 'direct' attachment-method of VoP to xDSL lines is implemented.
                "
            DEFVAL { 1 }
            ::= { hwOntVdsl2VOPSetupEntry 25 }


        hwOntVdsl2VOPSetupDpboProfId OBJECT-TYPE
            SYNTAX Unsigned32 (1..4294967294)
            MAX-ACCESS read-create
            STATUS current
            DESCRIPTION
                "This object identifies a row in hwVOPDPBOConfProfTable used for
                 configuring the downstream power back-off related parameters of the respective xDSL line.

                 This object has read-write accessibility if 'direct' attachment-method of VoP to xDSL lines is implemented.
                "
            DEFVAL { 1 }
            ::= { hwOntVdsl2VOPSetupEntry 26 }


        hwOntVdsl2VOPSetupRfiProfId OBJECT-TYPE
            SYNTAX Unsigned32 (1..4294967294)
            MAX-ACCESS read-create
            STATUS current
            DESCRIPTION
                "This object identifies a row in hwVOPRFIConfProfTable used for
                 configuring the RFI notches related parameters of the respective xDSL line.

                 This object has read-write accessibility if 'direct' attachment-method of VoP to xDSL lines is implemented.
                "
            DEFVAL { 1 }
            ::= { hwOntVdsl2VOPSetupEntry 27 }


        hwOntVdsl2VOPSetupNoiseMarginProfId OBJECT-TYPE
            SYNTAX Unsigned32 (1..4294967294)
            MAX-ACCESS read-create
            STATUS current
            DESCRIPTION
                "This object identifies a row in hwVOPSNRMarginConfProfTable used for
                 configuring the noise margin related parameters of the respective xDSL line.

                 This object has read-write accessibility if 'direct' attachment-method of VoP to xDSL lines is implemented.
                "
            DEFVAL { 1 }
            ::= { hwOntVdsl2VOPSetupEntry 28 }


        hwOntVdsl2VOPSetupVNoiseProfId OBJECT-TYPE
            SYNTAX Unsigned32 (1..4294967294)
            MAX-ACCESS read-create
            STATUS current
            DESCRIPTION
                "This object identifies a row in hwVOPVirtualNoiseConfProfTable used for
                 configuring the virtual noise related parameters of the respective xDSL line.

                 This object has read-write accessibility if 'direct' attachment-method of VoP to xDSL lines is implemented.
                "
            DEFVAL { 1 }
            ::= { hwOntVdsl2VOPSetupEntry 29 }
            
        hwOntVdsl2VOPSetupInmProfId OBJECT-TYPE
            SYNTAX Unsigned32 (1..4294967294)
            MAX-ACCESS read-create
            STATUS current
            DESCRIPTION
                "This object identifies a row in hwVOPINMConfProfTable used for
                 configuring the impulse noise monitoring parameters of the respective xDSL line.

                 This object has read-write accessibility if 'direct' attachment-method of VoP to xDSL lines is implemented.
                "
            DEFVAL { 1 }
            ::= { hwOntVdsl2VOPSetupEntry 30 }
            
        hwOntVdsl2VOPLineAdminStatus OBJECT-TYPE
            SYNTAX INTEGER 
                {up(1),
                 down(2)
                } 
            MAX-ACCESS  read-write
            STATUS      current
             DESCRIPTION
                "The current operational state of the ONT VDSL port.
             	  Options:
             	  1. up(1)      - indicates up operation.
             	  2. down(2)    - indicates down operation.
             	 "
            DEFVAL       { up }
            ::= { hwOntVdsl2VOPSetupEntry 31 }
  
	hwOntVdsl2VOPSetupUsDataRateProf1Description OBJECT-TYPE
            SYNTAX OCTET STRING (SIZE (0..128))
            MAX-ACCESS read-create
            STATUS current
            DESCRIPTION
                "This object identifies a row in hwVOPDataRateConfProfTable used for
                 configuring the upstream transmission direction of channel #1.
                 	
                 This object has read-write accessibility if 'direct' attachment-method of VoP to xDSL lines is implemented.
                "
            ::= { hwOntVdsl2VOPSetupEntry 32 }
        
        hwOntVdsl2VOPSetupDsDataRateProf1Description OBJECT-TYPE
            SYNTAX OCTET STRING (SIZE (0..128))
            MAX-ACCESS read-create
            STATUS current
            DESCRIPTION
                "This object identifies a row in hwVOPDataRateConfProfTable used for
                 configuring the downstream transmission direction of channel #1.

                 This object has read-write accessibility if 'direct' attachment-method of VoP to xDSL lines is implemented.
                "
            ::= { hwOntVdsl2VOPSetupEntry 33 }
        
        hwOntVdsl2VOPSetupInpDelayProf1Description OBJECT-TYPE
            SYNTAX OCTET STRING (SIZE (0..128))
            MAX-ACCESS read-create
            STATUS current
            DESCRIPTION
                "This object identifies a row in hwVOPINPDelayConfProfTable used for
                 configuring the INP-Delay parameters of channel #1.

                 This object has read-write accessibility if 'direct' attachment-method of VoP to xDSL lines is implemented.
                "
            ::= { hwOntVdsl2VOPSetupEntry 34 }
        
        hwOntVdsl2VOPSetupUsDataRateProf2Description OBJECT-TYPE
            SYNTAX OCTET STRING (SIZE (0..128))
            MAX-ACCESS read-create
            STATUS current
            DESCRIPTION
                "This object identifies a row in hwVOPDataRateConfProfTable used for
                 configuring the upstream transmission direction of channel #2.
                 If channel #2 is not being used this object should be set to a zero length string.

                 This object has read-write accessibility if 'direct' attachment-method of VoP to xDSL lines is implemented.
                "
            ::= { hwOntVdsl2VOPSetupEntry 35 }
        
        hwOntVdsl2VOPSetupDsDataRateProf2Description OBJECT-TYPE
            SYNTAX OCTET STRING (SIZE (0..128))
            MAX-ACCESS read-create
            STATUS current
            DESCRIPTION
                "This object identifies a row in hwVOPDataRateConfProfTable used for
                 configuring the downstream transmission direction of channel #2.
                 If channel #2 is not being used this object should be set to a zero length string.

                 This object has read-write accessibility if 'direct' attachment-method of VoP to xDSL lines is implemented.
                "
            ::= { hwOntVdsl2VOPSetupEntry 36 }
        
        hwOntVdsl2VOPSetupInpDelayProf2Description OBJECT-TYPE
            SYNTAX OCTET STRING (SIZE (0..128))
            MAX-ACCESS read-create
            STATUS current
            DESCRIPTION
                "This object identifies a row in hwVOPINPDelayConfProfTable used for
                 configuring the INP-Delay parameters of channel #2.
                 If channel #2 is not being used this object should be set to a zero length string.

                 This object has read-write accessibility if 'direct' attachment-method of VoP to xDSL lines is implemented.
                "
            ::= { hwOntVdsl2VOPSetupEntry 37 }
        
        hwOntVdsl2VOPSetupUsDataRateProf3Description OBJECT-TYPE
            SYNTAX OCTET STRING (SIZE (0..128))
            MAX-ACCESS read-create
            STATUS current
            DESCRIPTION
                "This object identifies a row in hwVOPDataRateConfProfTable used for
                 configuring the upstream transmission direction of channel #3.        
                          	
                 This object has read-write accessibility if 'direct' attachment-method of VoP to xDSL lines is implemented.
                 Currently, only support channel #1 and channel #2, thus this leaf is not supported.
                "
            ::= { hwOntVdsl2VOPSetupEntry 38 }
        
        hwOntVdsl2VOPSetupDsDataRateProf3Description OBJECT-TYPE
            SYNTAX OCTET STRING (SIZE (0..128))
            MAX-ACCESS read-create
            STATUS current
            DESCRIPTION
                "This object identifies a row in hwVOPDataRateConfProfTable used for
                 configuring the downstream transmission direction of channel #3.
                 
                 This object has read-write accessibility if 'direct' attachment-method of VoP to xDSL lines is implemented.
                 Currently, only support channel #1 and channel #2, thus this leaf is not supported.
                "
            ::= { hwOntVdsl2VOPSetupEntry 39 }
        
        hwOntVdsl2VOPSetupInpDelayProf3Description OBJECT-TYPE
            SYNTAX OCTET STRING (SIZE (0..128))
            MAX-ACCESS read-create
            STATUS current
            DESCRIPTION
                "This object identifies a row in hwVOPINPDelayConfProfTable used for
                 configuring the INP-Delay parameters of channel #3.
                 
                 This object has read-write accessibility if 'direct' attachment-method of VoP to xDSL lines is implemented.
                 Currently, only support channel #1 and channel #2, thus this leaf is not supported.                 
                "
            ::= { hwOntVdsl2VOPSetupEntry 40 }
            
       hwOntVdsl2VOPSetupUsDataRateProf4Description OBJECT-TYPE
            SYNTAX OCTET STRING (SIZE (0..128))
            MAX-ACCESS read-create
            STATUS current
            DESCRIPTION
                "This object identifies a row in hwVOPDataRateConfProfTable used for
                 configuring the upstream transmission direction of channel #4.      
                            	
                 This object has read-write accessibility if 'direct' attachment-method of VoP to xDSL lines is implemented.
                 Currently, only support channel #1 and channel #2, thus this leaf is not supported.
                "
            ::= { hwOntVdsl2VOPSetupEntry 41 }
        
        hwOntVdsl2VOPSetupDsDataRateProf4Description OBJECT-TYPE
            SYNTAX OCTET STRING (SIZE (0..128))
            MAX-ACCESS read-create
            STATUS current
            DESCRIPTION
                "This object identifies a row in hwVOPDataRateConfProfTable used for
                 configuring the downstream transmission direction of channel #4.
                 
                 This object has read-write accessibility if 'direct' attachment-method of VoP to xDSL lines is implemented.
                 Currently, only support channel #1 and channel #2, thus this leaf is not supported.
                "
            ::= { hwOntVdsl2VOPSetupEntry 42 }
        
        hwOntVdsl2VOPSetupInpDelayProf4Description OBJECT-TYPE
            SYNTAX OCTET STRING (SIZE (0..128))
            MAX-ACCESS read-create
            STATUS current
            DESCRIPTION
                "This object identifies a row in hwVOPINPDelayConfProfTable used for
                 configuring the INP-Delay parameters of channel #4.
                 
                 This object has read-write accessibility if 'direct' attachment-method of VoP to xDSL lines is implemented.
                 Currently, only support channel #1 and channel #2, thus this leaf is not supported.
                "
            ::= { hwOntVdsl2VOPSetupEntry 43 }
        
        hwOntVdsl2VOPSetupLSpectrumProfDescription OBJECT-TYPE
            SYNTAX OCTET STRING (SIZE (0..128))
            MAX-ACCESS read-create
            STATUS current
            DESCRIPTION
                "This object identifies a row in hwVOPLineSpectrumConfProfTable used for
                 configuring the spectrum parameters of the respective xDSL line.

                 This object has read-write accessibility if 'direct' attachment-method of VoP to xDSL lines is implemented.
                "
            ::= { hwOntVdsl2VOPSetupEntry 44 }
        
        hwOntVdsl2VOPSetupUpboProfDescription OBJECT-TYPE
            SYNTAX OCTET STRING (SIZE (0..128))
            MAX-ACCESS read-create
            STATUS current
            DESCRIPTION
                "This object identifies a row in hwVOPUPBOConfProfTable used for
                 configuring the upstream power back-off related parameters of the respective xDSL line.
                 If this leaf is not support this object should be set to 0.
                 This object has read-write accessibility if 'direct' attachment-method of VoP to xDSL lines is implemented.
                "
            ::= { hwOntVdsl2VOPSetupEntry 45 }
        
        hwOntVdsl2VOPSetupDpboProfDescription OBJECT-TYPE
            SYNTAX OCTET STRING (SIZE (0..128))
            MAX-ACCESS read-create
            STATUS current
            DESCRIPTION
                "This object identifies a row in hwVOPDPBOConfProfTable used for
                 configuring the downstream power back-off related parameters of the respective xDSL line.

                 This object has read-write accessibility if 'direct' attachment-method of VoP to xDSL lines is implemented.
                "
            ::= { hwOntVdsl2VOPSetupEntry 46 }
        
        hwOntVdsl2VOPSetupRfiProfDescription OBJECT-TYPE
            SYNTAX OCTET STRING (SIZE (0..128))
            MAX-ACCESS read-create
            STATUS current
            DESCRIPTION
                "This object identifies a row in hwVOPRFIConfProfTable used for
                 configuring the RFI notches related parameters of the respective xDSL line.

                 This object has read-write accessibility if 'direct' attachment-method of VoP to xDSL lines is implemented.
                "
            ::= { hwOntVdsl2VOPSetupEntry 47 }
        
        hwOntVdsl2VOPSetupNoiseMarginProfDescription OBJECT-TYPE
            SYNTAX OCTET STRING (SIZE (0..128))
            MAX-ACCESS read-create
            STATUS current
            DESCRIPTION
                "This object identifies a row in hwVOPSNRMarginConfProfTable used for
                 configuring the noise margin related parameters of the respective xDSL line.

                 This object has read-write accessibility if 'direct' attachment-method of VoP to xDSL lines is implemented.
                "
            ::= { hwOntVdsl2VOPSetupEntry 48 }
        
        hwOntVdsl2VOPSetupVNoiseProfDescription OBJECT-TYPE
            SYNTAX OCTET STRING (SIZE (0..128))
            MAX-ACCESS read-create
            STATUS current
            DESCRIPTION
                "This object identifies a row in hwVOPVirtualNoiseConfProfTable used for
                 configuring the virtual noise related parameters of the respective xDSL line.

                 This object has read-write accessibility if 'direct' attachment-method of VoP to xDSL lines is implemented.
                "
            ::= { hwOntVdsl2VOPSetupEntry 49 }
        
        hwOntVdsl2VOPSetupInmProfDescription OBJECT-TYPE
            SYNTAX OCTET STRING (SIZE (0..128))
            MAX-ACCESS read-create
            STATUS current
            DESCRIPTION
                "This object identifies a row in hwVOPINMConfProfTable used for
                 configuring the impulse noise monitoring parameters of the respective xDSL line.

                 This object has read-write accessibility if 'direct' attachment-method of VoP to xDSL lines is implemented.
                "
            ::= { hwOntVdsl2VOPSetupEntry 50 }
            
-- VOP TRAP

        hwVOPProfileIDChangeTrap NOTIFICATION-TYPE
            OBJECTS {
                hwConfigChangeIP,
                ifIndex,
                hwVOPDataRateConfProfIndex,
                hwVOPDataRateConfProfDescription,
                hwVOPDataRateConfProfIndex,
                hwVOPDataRateConfProfDescription,
                hwVOPINPDelayConfProfIndex,
                hwVOPINPDelayConfProfDescription,
                hwVOPDataRateConfProfIndex,
                hwVOPDataRateConfProfDescription,
                hwVOPDataRateConfProfIndex,
                hwVOPDataRateConfProfDescription,
                hwVOPINPDelayConfProfIndex,
                hwVOPINPDelayConfProfDescription,
                hwVOPDPBOConfProfIndex,
                hwVOPDPBOConfProfProfDescription,
                hwVOPUPBOConfProfIndex,
                hwVOPUPBOConfProfDescription,
                hwVOPLineSpectrumConfProfIndex,
                hwVOPLineSpectrumConfProfDescription,
                hwVOPRFIConfProfIndex,
                hwVOPRFIConfProfDescription,
                hwVOPSNRMarginConfProfIndex,
                hwVOPSNRMarginConfProfDescription,
                hwVOPVirtualNoiseConfProfIndex,
                hwVOPVirtualNoiseConfProfDescription,
                hwVOPINMConfProfIndex,
                hwVOPINMConfProfDescription,
                hwVOPSosConfProfIndex,
                hwVOPSosConfProfDescription
            }
            STATUS current
            DESCRIPTION
               "The profile ID bound by the port change.

                1. hwConfigChangeIP -- The serial IP of configuration changes.
                2. ifIndex-the index of the xDSL interface.
                3. hwVOPDataRateConfProfIndex -- the data-rate profile ID used for
                   configuring the downstream transmission direction of channel #1.
                4. hwVOPDataRateConfProfDescription-the data-rate profile description used for
                   configuring the downstream transmission direction of channel #1.
                5. hwVOPDataRateConfProfIndex -- the data-rate profile ID used for
                   configuring the upstream transmission direction of channel #1.
                6. hwVOPDataRateConfProfDescription -- the data-rate profile description used for
                   configuring the upstream transmission direction of channel #1.
                7. hwVOPINPDelayConfProfIndex -- the inp-delay profile ID used for configuring the channel #1.
                8. hwVOPINPDelayConfProfDescription -- the inp-delay profile description used for configuring the channel #1.
                9. hwVOPDataRateConfProfIndex -- the data-rate profile ID used for
                   configuring the downstream transmission direction of channel #2.
                10.hwVOPDataRateConfProfDescription -- the data-rate profile description used for
                   configuring the downstream transmission direction of channel #2.
                11.hwVOPDataRateConfProfIndex -- the data-rate profile ID used for
                   configuring the upstream transmission direction of channel #2.
                12.hwVOPDataRateConfProfDescription -- the data-rate profile description used for
                   configuring the upstream transmission direction of channel #2.
                13.hwVOPINPDelayConfProfIndex -- the inp-delay profile ID used for configuring the channel #2.
                14.hwVOPINPDelayConfProfDescription -- the inp-delay profile description used for configuring the channel #2.
                15.hwVOPDPBOConfProfIndex -- the dpbo profile ID used for configuring the port.
                16.hwVOPDPBOConfProfProfDescription -- the dpbo profile description used for configuring the port.
                17.hwVOPUPBOConfProfIndex -- the upbo profile ID used for configuring the port.
                18.hwVOPUPBOConfProfDescription -- the upbo profile description used for configuring the port.
                19.hwVOPLineSpectrumConfProfIndex -- the line-spectrum profile ID used for configuring the port.
                20.hwVOPLineSpectrumConfProfDescription -- the line-spectrum profile description used for configuring the port.
                21.hwVOPRFIConfProfIndex -- the rfi profile ID used for configuring the port.
                22.hwVOPRFIConfProfDescription -- the rfi profile description used for configuring the port.
                23.hwVOPSNRMarginConfProfIndex -- the SNR-Margin profile ID used for configuring the port.
                24.hwVOPSNRMarginConfProfDescription -- the SNR-Margin profile description used for configuring the port.
                25.hwVOPVirtualNoiseConfProfIndex -- the virtual noise profile ID used for configuring the port.
                26.hwVOPVirtualNoiseConfProfDescription -- the virtual noise profile description used for configuring the port.
                27.hwVOPINMConfProfIndex -- the inm profile ID used for configuring the port.
                28.hwVOPINMConfProfDescription -- the inm profile description used for configuring the port.
                29.hwVOPSosConfProfIndex -- the sos profile ID used for configuring the port.
                30.hwVOPSosConfProfDescription -- the sos profile description used for configuring the port.
               "
            ::= { hwVOPXdslPortTraps 1 }

    END

--
-- VOP-MIB.mib
--
