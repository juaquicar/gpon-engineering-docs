-- ============================================================================
-- Copyright (C) 2015 by  HUAWEI TECHNOLOGIES. All rights reserved.
-- Description: The entity of voice port's configuration.  
-- Reference:  
-- Version: V1.39
-- ============================================================================

 HUAWEI-VOICEPORT-MIB DEFINITIONS ::= BEGIN
      IMPORTS
            MODULE-IDENTITY, OBJECT-TYPE, NOTIFICATION-TYPE, private,Integer32, Unsigned32
                FROM SNMPv2-SMI
            MODULE-COMPLIANCE, OBJECT-GROUP, NOTIFICATION-GROUP
                FROM SNMPv2-CONF
            TEXTUAL-CONVENTION
                FROM SNMPv2-TC
            IpAddress,TimeTicks,Counter32
                FROM SNMPv2-SMI
            RowStatus,DisplayString
                FROM SNMPv2-TC
            huaweiUtility
                FROM HUAWEI-MIB
            hwConfigChangeIP
                FROM HUAWEI-DEVICE-MIB;
        
      hwIASVoicePort MODULE-IDENTITY
                LAST-UPDATED "201511122130Z"
                ORGANIZATION "Huawei Technologies Co.,Ltd."
                CONTACT-INFO                                        
                             "Huawei Industrial Base                
                              Bantian, Longgang                     
                              Shenzhen 518129                       
                              People's Republic of China            
                              Website: http://www.huawei.com        
                              Email: support@huawei.com             
                             "                                      
                DESCRIPTION 
                            "
                            The entity of voice port's configuration.
                            "

                --  Revision history 
                REVISION "201511122130Z"
                DESCRIPTION "V1.39,Add one layer node to keep the OID invariableness"
							
                REVISION "201508252230Z"
                DESCRIPTION "V1.38, change in this revision:
                              1. Added a new node: hwFxoPTPPowerState.
                              2. Modified the scope and description for some nodes in hwFxoPTPConfigTable.
                              3. Added hwIASVoicePortFxoAlarmTraps.
                            "
                            
                REVISION "201501211430Z"
                DESCRIPTION "V1.37, change in this revision:
                              1. Added a new table: hwShdslPTPL1AlarmThresholdTable.
                              2. Added a new node: hwE1PTPDegradeEndService.
                            "
                            
                REVISION "201501062021Z"
                DESCRIPTION "V1.36, change in this revision:
                              1. Added hwPstnPTPPartyline.
                            "

                REVISION "201412081736Z"
                DESCRIPTION "V1.35, change in this revision:
                              1. Added hwBraPTPNlpMode.
                            "                
                 
                REVISION "201406041040Z"
                DESCRIPTION "V1.34, Modified the syntax for OMSYS" 
                
                REVISION "201404100000Z"
                DESCRIPTION "V1.33, change in this revision:
                              1. Modified the Description of hwPstnPTPCurrent.                
                            " 
                                            
                REVISION "201311110000Z"
                DESCRIPTION "V1.32, change in this revision:
                              1. Modified the value range of hwPstnPTPCurrent.
                            " 
                            
                REVISION "201305080000Z"
                DESCRIPTION "V1.31, change in this revision:
                              1. Modified the value range of hwPstnPTPPulseDurationLower.
                              2. Modified the value range of hwPstnPTPPulsePauseLower.
                            "  
                                
                REVISION "201304230000Z"
                DESCRIPTION "V1.30, change in this revision:
                              1. Added hwPstnPTPReversePolarityEnable.
                              2. Modified the name of the leaf hwPstnPTPReversePoleEnable to hwPstnPTPReversePolePulseEnable
                            "  
                                            
                REVISION "201210220000Z"
                DESCRIPTION "V1.29, change in this revision:
                              1. Added hwBraPTPActualWorkMode.
                              2. Added enum(auto) into the hwBraPTPWorkMode. 
                              3. Modified the description of the leaf hwPstnPTPImpedance.                 
                            "  
                              
                REVISION "201209050000Z"
                DESCRIPTION "V1.28, change in this revision:
                              1. Added hwPstnPTPCurrentAdjustFactor.                  
                            "  
                REVISION "201206150000Z"
                DESCRIPTION "V1.27, change in this revision:
                              1. Added hwVoicePstnPortPowerAlarmTrap for alarm.
                              2. Added hwVoicePstnPortPowerAlarmRestoreTrap for alarm.
                            "
                            
                REVISION "201205080000Z"
                DESCRIPTION "V1.26, change in this revision:
                              1. Added hwPotsBoardToneDefineTable.
                              2. Added hwVoicePstnBoardSlicLockedTrap for alarm.
                              3. Added hwVoicePstnBoardSlicUnlockedTrap for alarm.
                              4. Added hwPstnPTPIdleOffhookTime.
                              5. Added hwPstnPTPRingOffhookTime.
                              6. Added hwPstnPTPFskOffhookTime.
                            "    
                
                REVISION    "201112012105Z"                         
                DESCRIPTION "V1.25, change in this revision:        
                            --Modified the enums and description of the leaves,including:
                            hwE1PTPLoopBackState
                            hwPstnPTPNlpMode 
                            --Modified the description of the leaves,including:
                            hwPstnPTPProhibit  
                            --Added hwBraPTPActivePeriod
                            "
                            
                REVISION    "201108191005Z"                         
                DESCRIPTION "V1.24, change in this revision:        
                            --Added hwPortMask
                            --Added hwAttributeMask
                            --Added hwChangepara1
                            --Added hwChangepara2
                            --Added hwChangepara3
                            --Added hwChangepara4
                            --Added hwChangepara5
                            --Added hwChangepara6
                            --Added hwChangepara7
                            --Added hwChangepara8
                            --Added hwChangepara9
                            --Added hwChangepara10
                            --Added hwChangepara11
                            --Added hwChangepara12
                            --Added hwChangepara13
                            --Added hwChangepara14
                            --Added hwChangepara15
                            --Added hwChangepara16
                            --Added hwIASVoicePortE1AttributeCfgChgTrap
                            --Added hwIASVoicePortE1AlarmCfgChgTrap
                            --Added hwIASVoicePortShdslAttributeChgTrap"
                             
                REVISION    "201011172205Z"                         
                DESCRIPTION "V1.23, change in this revision:        
                            -Modified the description of all tables"

                REVISION    "201007260000Z"
                DESCRIPTION "V1.22, change in this revision:
                            -Modified the description of all tables"

                REVISION    "201006300000Z"
                DESCRIPTION "V1.21, change in this revision:
                            -Modified the description of the leaves,including:
                            hwPstnPTPCurrent
                            "
                            
                REVISION    "201006260000Z"
                DESCRIPTION "V1.20, change in this revision:
                            -Corrected the SYNTAX"
                                  
                REVISION    "201007090000Z"
                DESCRIPTION "V1.19, added nodes
                            -Added hwVoicePortSequence
                            -Added hwVoicePortOperateType
                            -Added hwVoicePortNum
                            -Added hwIASVoicePortPstnTrap
                            -Added hwIASVoicePortBraTrap
                            -Added hwIASVoicePortE1Trap"
                          
                REVISION    "201005050000Z"
                DESCRIPTION "V1.18, revised the errors"  
                          
                REVISION    "201001270000Z"
                DESCRIPTION "V1.17, change in this revision:
                             -Corrected the SYNTAX
                                  
                             -Added hwE1PTPLineCode into hwE1PTPConfigTable
                                
                             -Added hwShdslPTPConfigTable

                             -Added hwShdslPTPOperTable
                            "
        

                        ::= { huaweiUtility 113 }
               
 hwIASVoicePortObjects OBJECT IDENTIFIER ::= { hwIASVoicePort 1 }
 
 hwIASVoicePortTrapsVbOids OBJECT IDENTIFIER ::= { hwIASVoicePort 2 }

 hwIASVoicePortTraps OBJECT IDENTIFIER ::= { hwIASVoicePort 3 }
 
 hwIASVoicePortCommonTraps OBJECT IDENTIFIER ::= { hwIASVoicePortTraps 1 }
 
 hwIASVoicePortAlarmTraps OBJECT IDENTIFIER ::= { hwIASVoicePortTraps 2 } 
  
 hwIASVoicePortComTraps OBJECT IDENTIFIER ::= { hwIASVoicePortCommonTraps 1 }
 
 hwIASVoicePortComAlarmTraps OBJECT IDENTIFIER ::= { hwIASVoicePortAlarmTraps 1 }

 hwIASVoicePortPstnTraps OBJECT IDENTIFIER ::= { hwIASVoicePortCommonTraps 2 }
 
 hwIASVoicePortPstnAlarmTraps OBJECT IDENTIFIER ::= { hwIASVoicePortAlarmTraps 2 }
 
 hwIASVoicePortBraTraps OBJECT IDENTIFIER ::= { hwIASVoicePortCommonTraps 3 }
 
 hwIASVoicePortBraAlarmTraps OBJECT IDENTIFIER ::= { hwIASVoicePortAlarmTraps 3 }
 
 hwIASVoicePortE1Traps OBJECT IDENTIFIER ::= { hwIASVoicePortCommonTraps 4 }
 
 hwIASVoicePortE1AlarmTraps OBJECT IDENTIFIER ::= { hwIASVoicePortAlarmTraps 4 }
  
 hwIASVoicePortIsdnL2Traps OBJECT IDENTIFIER ::= { hwIASVoicePortCommonTraps 5}
 
 hwIASVoicePortIsdnL2AlarmTraps OBJECT IDENTIFIER ::= { hwIASVoicePortAlarmTraps 5 }   
 
 hwIASVoicePortFxoAlarmTraps OBJECT IDENTIFIER ::= { hwIASVoicePortAlarmTraps 6 }  
   
 
    hwPstnPTPConfigTable OBJECT-TYPE
     SYNTAX      SEQUENCE OF HwPstnPTPConfigEntry
     MAX-ACCESS  not-accessible
     STATUS      current
     DESCRIPTION
       "
       A list of hwPstnPTPConfigEntry objects.
       The index of this table is hwPstnPTPIndex. 
       "
     ::= { hwIASVoicePortObjects 1 }
 
   hwPstnPTPConfigEntry OBJECT-TYPE
     SYNTAX      HwPstnPTPConfigEntry
     MAX-ACCESS  not-accessible
     STATUS      current
     DESCRIPTION
       "
       A list of hwPstnPTPConfigEntry objects.
       The index of this entry is hwPstnPTPIndex.
       "
     INDEX    {  
               hwPstnPTPIndex
              }
     ::= { hwPstnPTPConfigTable 1 }
 
   HwPstnPTPConfigEntry ::=
     SEQUENCE
     {
       hwPstnPTPIndex                   Integer32,
       hwPstnPTPSendVoiceGain           Integer32,
       hwPstnPTPRecvVoiceGain           Integer32,
       hwPstnPTPDialMode                INTEGER,
       hwPstnPTPReversePolePulseEnable  INTEGER,
       hwPstnPTPReversePoleLevel        Integer32,
       hwPstnPTPPolarityReverseMode     INTEGER, 
       hwPstnPTPImpedance               Integer32,
       hwPstnPTPCurrent                 Integer32,
       hwPstnPTPHighLevel               Integer32,
       hwPstnPTPLowLevel                Integer32,
       hwPstnPTPKCType                  INTEGER,
       hwPstnPTPVoltage                 INTEGER,
       hwPstnPTPActualSendGain          Integer32,
       hwPstnPTPActualRecvGain          Integer32,
       hwPstnPTPConfigState             INTEGER,
       hwPstnPTPLineLock                INTEGER,
       hwPstnPTPNlpMode                 INTEGER,
       hwPstnPTPClipReversePole         INTEGER,
       hwPstnPTPPulsePeriodUpper        Integer32,
       hwPstnPTPPulsePeriodLower        Integer32,
       hwPstnPTPPulseDurationUpper      Integer32,
       hwPstnPTPPulseDurationLower      Integer32,  
       hwPstnPTPPulsePauseUpper         Integer32,
       hwPstnPTPPulsePauseLower         Integer32,        
       hwPstnPTPProhibit                INTEGER,
       hwPstnPTPIdleOffhookTime         Integer32,
       hwPstnPTPRingOffhookTime         Integer32,
       hwPstnPTPFskOffhookTime          Integer32,
       hwPstnPTPCurrentAdjustFactor     Integer32,
       hwPstnPTPReversePolarityEnable   INTEGER,
       hwPstnPTPPartyline               INTEGER
     }
 
   hwPstnPTPIndex OBJECT-TYPE
     SYNTAX      Integer32
     MAX-ACCESS  not-accessible
     STATUS      current
     DESCRIPTION
         "
         Indicates the shelf/slot/port index.
         "
     ::= { hwPstnPTPConfigEntry 1 }
 
   hwPstnPTPSendVoiceGain OBJECT-TYPE
     SYNTAX      Integer32(1..255)
     MAX-ACCESS  read-write
     STATUS      current
     DESCRIPTION
         "
         Indicates the transmit gain (dB).
            1:     5 dB
            2:   4.5 dB
            3:     4 dB
            4:   3.5 dB
            5:     3 dB
            6:   2.5 dB
            7:     2 dB
            8:   1.5 dB
            9:     1 dB
            10:  0.5 dB
            11:    0 dB
            12: -0.5 dB
            13:   -1 dB
            14: -1.5 dB
            15:   -2 dB
            16: -2.5 dB
            17:   -3 dB
            18: -3.5 dB
            19:   -4 dB
            20: -4.5 dB
            21:   -5 dB
            22: -5.5 dB
            23:   -6 dB
            255: auto gain control
         "
         DEFVAL      { 11 }
     ::= { hwPstnPTPConfigEntry 2 }
         
   hwPstnPTPRecvVoiceGain OBJECT-TYPE
     SYNTAX      Integer32(1..255)
     MAX-ACCESS  read-write
     STATUS      current
     DESCRIPTION
         "
           Indicates the receive gain (dB).
            1:     0 dB  
            2:  -0.5 dB   
            3:    -1 dB  
            4:  -1.5 dB  
            5:    -2 dB  
            6:  -2.5 dB  
            7:    -3 dB  
            8:  -3.5 dB  
            9:    -4 dB  
           10:  -4.5 dB 
           11:    -5 dB 
           12:  -5.5 dB 
           13:    -6 dB 
           14:  -6.5 dB 
           15:    -7 dB 
           16:  -7.5 dB 
           17:    -8 dB 
           18:  -8.5 dB 
           19:    -9 dB 
           20:  -9.5 dB 
           21:   -10 dB 
           22: -10.5 dB 
           23:   -11 dB 
           24: -11.5 dB 
           25:   -12 dB 
           255 :agc
         "
         DEFVAL      { 15 }
     ::= { hwPstnPTPConfigEntry 3 }
          
   hwPstnPTPDialMode OBJECT-TYPE
     SYNTAX      INTEGER{modeDtmfPulseBoth(1),modeDtmfOnly(2),modePulseOnly(3)}
     MAX-ACCESS  read-write
     STATUS      current
     DESCRIPTION
         "
         Indicates the dialing mode.
         Options:
         1.modeDtmfPulseBoth(1) -indicates the dial mode are both pulse and DTMF
         2.modeDtmfOnly(2)       -indicates the dial mode is only DTMF
         3.modePulseOnly(3)      -indicates the dial mode is only pulse
         "
         DEFVAL      { modeDtmfPulseBoth }
     ::= { hwPstnPTPConfigEntry 4 }
     
   hwPstnPTPReversePolePulseEnable OBJECT-TYPE
     SYNTAX      INTEGER{reversePolePulseDisable(1),reversePolePulseEnable(2)}
     MAX-ACCESS  read-write
     STATUS      current
     DESCRIPTION
         "
         Indicates whether to support the polarity-reversing pulse.  
         Options:
         1.reversePolePulseDisable(1)  -indicates the reverse pole pulse is disable
         2.reversePolePulseEnable(2)  -indicates the reverse pole pulse is enable
         "
         DEFVAL      { reversePolePulseEnable }
     ::= { hwPstnPTPConfigEntry 5 }
     
   hwPstnPTPReversePoleLevel OBJECT-TYPE
     SYNTAX      Integer32(20..1270)
     MAX-ACCESS  read-write
     STATUS      current
     DESCRIPTION
         "
         Indicates the level width of the polarity-reversing pulse (unit: ms). Step: 10 ms.
         "
         DEFVAL      { 100 }
     ::= { hwPstnPTPConfigEntry 6 }
     
   hwPstnPTPPolarityReverseMode OBJECT-TYPE
     SYNTAX      INTEGER{hardReversePole(1),softReversePole(2)}
     MAX-ACCESS  read-write
     STATUS      current
     DESCRIPTION
         "
         The polarity reversal mode. 
         Options:
         1.hardReversePole(1) -Indicates the polarity reversal mode is hard polarity reversal
         2.softReversePole(2) -Indicates the polarity reversal mode is soft polarity reversal
         "
         DEFVAL      { hardReversePole }
     ::= { hwPstnPTPConfigEntry 7 }     
 
   hwPstnPTPImpedance OBJECT-TYPE
     SYNTAX      Integer32(1..16)
     MAX-ACCESS  read-write
     STATUS      current
     DESCRIPTION
         "
         Port impedance of the port. The following values indicates different impedance with 
         different application circumstances.
         1  -- Bureau machine in China(200+680|| 100nf)
         2  -- User Machine in China(200+560|| 100nf)
         3  -- 600 ohm Interface
         4  -- Interface of russian(150+510|| 47nf)
         5  -- (220+820|| 115nf )
         6  -- (220+820|| 120nf )
         7  -- 900 ohm Interface
         8  -- Interface of Brazil(800|| 50nf)
         9  -- Abandoned
         10 -- HK_BT3(Zin=370+620|| 310nf,Zload=600)
         11 -- HK_BT5(Zin=270+264|| 357nf+1434|| 265nf,Zload=600)
         12 -- BT1(Zin=87+1052||228nF+229||28.4nF, Zload=93+615||471nF+179||495nF+244||32nF)
         13 -- BT2(Zin=(87 +1052 //228nF+229 //28.4nF),Zload=(270 +264 //357nF+1434 //265nF))
         14 -- BT3(Zin=(87 +1052 //228nF+229 //28.4nF),Zload=(164 +162 //363nF+1227 //350nF))
         15 -- Commonly used in Europe(Zin= 270+750|| 150nf)
         16 -- New zealand (Zin=370+620|| 310nf)         
         
         Indicates the port impedance of the board.Each value corresponds to the required impedance in a specified scenario.
         1  -- Bureau machine in China (200+680|| 100nf)
         2 -- User machine in China (200+560|| 100nf)
         3 -- 600 ohm interface
         4  -- Interface of Russia (150+510|| 47nf)
         5  -- (220+820|| 115nf )
         6  -- (220+820|| 120nf )
         7 -- 900 ohm interface
         8 - Interface of Brazil (800|| 50nf)
         9  -- Abandoned
         10 -- HK_BT3(Zin=370+620|| 310nf,Zload=600)
         11 -- HK_BT5(Zin=270+264|| 357nf+1434|| 265nf,Zload=600)
         12 -- BT1(Zin=87+1052||228nF+229||28.4nF, Zload=93+615||471nF+179||495nF+244||32nF)
         13 -- BT2(Zin=(87 +1052 //228nF+229 //28.4nF),Zload=(270 +264 //357nF+1434 //265nF))
         14 -- BT3(Zin=(87 +1052 //228nF+229 //28.4nF),Zload=(164 +162 //363nF+1227 //350nF))                          
         15 -- Commonly used in Europe (Zin= 270+750|| 150nf)
         16 -- New zealand (Zin=370+620|| 310nf)                      
         "
         DEFVAL { 3 }
         ::= { hwPstnPTPConfigEntry 8 }
 
   hwPstnPTPCurrent OBJECT-TYPE
     SYNTAX      Integer32(1..8)
     MAX-ACCESS  read-write
     STATUS      current
     DESCRIPTION
         "
         Port current supported by the board. The value ranges from 1 to 8, 
         which indicates the port current value
         (commonly the maximum number of the ports with the current exceed 35mA is 5. as for MA5600T series product, 
         the maximum number of the ports with the current exceed 40mA is 5).
         1: 16mA
         2: 20mA
         3: 25mA
         4: 30mA
         5: 35mA
         6: 40mA
         7: 45mA    
         8: 50mA
         "             
     DEFVAL { 3 }      
     ::= { hwPstnPTPConfigEntry 9 }  

   hwPstnPTPHighLevel OBJECT-TYPE
     SYNTAX      Integer32(20..500)
     MAX-ACCESS  read-write
     STATUS      current
     DESCRIPTION
         "
         Indicates the high level width of the 16KC (unit: ms).
         "
         DEFVAL { 100 }
     ::= { hwPstnPTPConfigEntry 10 }
     
   hwPstnPTPLowLevel OBJECT-TYPE
     SYNTAX      Integer32(20..500)
     MAX-ACCESS  read-write
     STATUS      current
     DESCRIPTION
         "
         Indicates the low level width of the 16KC (unit: ms).
         "
         DEFVAL { 300 }
     ::= { hwPstnPTPConfigEntry 11 }
     
   hwPstnPTPKCType OBJECT-TYPE
     SYNTAX      INTEGER{port1216kcSelector16kc(1),port1216kcSelector12kc(2)}
     MAX-ACCESS  read-write
     STATUS      current
     DESCRIPTION
         "
         Indicates the 12KC/16KC type. 
         Options:
         1.port1216kcSelector16kc(1) -indicates the 16kc
         2.port1216kcSelector12kc(2) -indicates the 12kc
         "
         DEFVAL { port1216kcselector16kc }
     ::= { hwPstnPTPConfigEntry 12 }
     
   hwPstnPTPVoltage OBJECT-TYPE
     SYNTAX      INTEGER{port1216kcValidVoltage0(1),
                         port1216kcValidVoltage1(2),
                         port1216kcValidVoltage2(3),
                         port1216kcValidVoltage3(4),
                         port1216kcValidVoltage4(5),
                         port1216kcValidVoltage5(6),
                         port1216kcValidVoltage6(7),
                         port1216kcValidVoltage7(8),
                         port1216kcValidVoltage8(9),
                         port1216kcValidVoltage9(10)}
     MAX-ACCESS  read-write
     STATUS      current
     DESCRIPTION
         "
         Indicates the valid level of the 12KC/16KC.   
         Options:
         1.port1216kcValidVoltage0(1)  -indicates 0.45 Vrms   
         2.port1216kcValidVoltage1(2)  -indicates 0.775 Vrms  
         3.port1216kcValidVoltage2(3)  -indicates 1.0 Vrms    
         4.port1216kcValidVoltage3(4)  -indicates 1.5 Vrms    
         5.port1216kcValidVoltage4(5)  -indicates 2.0 Vrms    
         6.port1216kcValidVoltage5(6)  -indicates 2.5 Vrms    
         7.port1216kcValidVoltage6(7)  -indicates 3.0 Vrms    
         8.port1216kcValidVoltage7(8)  -indicates 3.5 Vrms    
         9.port1216kcValidVoltage8(9)  -indicates 4.0 Vrms    
         10.port1216kcValidVoltage9(10) -indicates 4.5 Vrms    
         "
         DEFVAL { 6 }
     ::= { hwPstnPTPConfigEntry 13 }     
             
   hwPstnPTPActualSendGain OBJECT-TYPE
     SYNTAX      Integer32(-1|1..23)
     MAX-ACCESS  read-only
     STATUS      current
     DESCRIPTION
         "
         Indicates the actual transmit gain of the port.
           -1: invalid value
            1:     5 dB
            2:   4.5 dB
            3:     4 dB
            4:   3.5 dB
            5:     3 dB
            6:   2.5 dB
            7:     2 dB
            8:   1.5 dB
            9:     1 dB
            10:  0.5 dB
            11:    0 dB
            12: -0.5 dB
            13:   -1 dB
            14: -1.5 dB
            15:   -2 dB
            16: -2.5 dB
            17:   -3 dB
            18: -3.5 dB
            19:   -4 dB
            20: -4.5 dB
            21:   -5 dB
            22: -5.5 dB
            23:   -6 dB
         "
     ::= { hwPstnPTPConfigEntry 14 }
         
  hwPstnPTPActualRecvGain OBJECT-TYPE
     SYNTAX      Integer32(-1|1..25)
     MAX-ACCESS  read-only
     STATUS      current
     DESCRIPTION
         "
         Indicates the actual receive gain of the port.
           -1: invalid value
            1:     0 dB  
            2:  -0.5 dB   
            3:    -1 dB  
            4:  -1.5 dB  
            5:    -2 dB  
            6:  -2.5 dB  
            7:    -3 dB  
            8:  -3.5 dB  
            9:    -4 dB  
           10:  -4.5 dB 
           11:    -5 dB 
           12:  -5.5 dB 
           13:    -6 dB 
           14:  -6.5 dB 
           15:    -7 dB 
           16:  -7.5 dB 
           17:    -8 dB 
           18:  -8.5 dB 
           19:    -9 dB 
           20:  -9.5 dB 
           21:   -10 dB 
           22: -10.5 dB 
           23:   -11 dB 
           24: -11.5 dB 
           25:   -12 dB 
         "
     ::= { hwPstnPTPConfigEntry 15 }
  hwPstnPTPConfigState OBJECT-TYPE
     SYNTAX      INTEGER{notConfigUserType(1),configUserType(2)}
     MAX-ACCESS  read-only
     STATUS      current
     DESCRIPTION
         "
         Indicates the configuration status of the subscriber type. 1-Not configured; 2-Configured.   
         Options:
         1.notConfigUserType(1) -not configured
         2.configUserType(2)    -configured
         "
     ::= { hwPstnPTPConfigEntry 16 }      
 
   hwPstnPTPLineLock OBJECT-TYPE
     SYNTAX      INTEGER{enable(1),disable(2)}
     MAX-ACCESS  read-write
     STATUS      current
     DESCRIPTION
         "
         Indicates support lock port or not   
         Options:
         1.enable(1)    -support the lock of the port
         2.disable(2)   -not support the lock of the port
         "
     DEFVAL      { enable }
     ::= { hwPstnPTPConfigEntry 17 }
     
   hwPstnPTPNlpMode OBJECT-TYPE
     SYNTAX      INTEGER{normalMode(1),ecgainMode(2),increasedMode(3),reducedMode(4),close(5),dtmfEcMode(6)}
     MAX-ACCESS  read-write
     STATUS      current
     DESCRIPTION
         "
         Indicates the Nlp mode of the port.    
         Options:
         1.normalMode(1)       -indicates enable the function of non-linear process for echo control performance in default level
         2.ecgainMode(2)       -indicates enable the function to config the gain value for ec with the non-linear process
         3.increasedMode(3)    -indicates For certain 2-to-4 wire hybrid or line conditions where a larger than normal non-linear
                                    component in the echo is present,setting for an increased level of NLP engagement 
                                    in order to provide an adequate echo control performance
         4.reducedMode(4)      -indicates For applications where the default NLP level causes unpleasant voice artifacts (like choppiness
                                    at the beginning of the call in heavy double talk situations), the Host may select the NLP Tune
                                    setting to reduce the level of NLP engagement
         5.close(5)            -indicates disable the function of non-linear process for echo control performance
         6.dtmfEcMode(6)       -indicates DTMF echo elimination 
         "
     DEFVAL      { 1 }
     ::= { hwPstnPTPConfigEntry 18 }
     
    hwPstnPTPClipReversePole OBJECT-TYPE
     SYNTAX      INTEGER{enable(1),disable(2)}
     MAX-ACCESS  read-write
     STATUS      current
     DESCRIPTION
         "
         Indicates whether to support the polarity-reversing pulse when Clip.
         Options:
         1.enable(1)    -support the polarity-reversing pulse
         2.disable(2)   -not support the polarity-reversing pulse
         "
         DEFVAL      { disable }
     ::= { hwPstnPTPConfigEntry 19 }
     
   hwPstnPTPPulsePeriodUpper OBJECT-TYPE
     SYNTAX      Integer32(20..500)
     MAX-ACCESS  read-write
     STATUS      current
     DESCRIPTION
         "
         Indicates the upper limit of the pulse period (unit: ms).
         "
         DEFVAL      { 200 }
     ::= { hwPstnPTPConfigEntry 20 }
     
   hwPstnPTPPulsePeriodLower OBJECT-TYPE
     SYNTAX      Integer32(20..500)
     MAX-ACCESS  read-write
     STATUS      current
     DESCRIPTION
         "
         Indicates the lower limit of the pulse period 
         Unit: ms
         "
         DEFVAL      { 50 }
     ::= { hwPstnPTPConfigEntry 21 }     

   hwPstnPTPPulseDurationUpper OBJECT-TYPE
     SYNTAX      Integer32(20..200)
     MAX-ACCESS  read-write
     STATUS      current
     DESCRIPTION
         "
         Indicates the upper limit of the pulse duration (unit: ms).
         "
         DEFVAL      { 90 }
     ::= { hwPstnPTPConfigEntry 22 }
 
    hwPstnPTPPulseDurationLower OBJECT-TYPE
     SYNTAX      Integer32(10..200)
     MAX-ACCESS  read-write
     STATUS      current
     DESCRIPTION
         "
         Indicates the lower limit of the pulse duration (unit: ms).
         "
         DEFVAL      { 30 }
     ::= { hwPstnPTPConfigEntry 23 }

    hwPstnPTPPulsePauseUpper OBJECT-TYPE
     SYNTAX      Integer32(20..200)
     MAX-ACCESS  read-write
     STATUS      current
     DESCRIPTION
         "
         Indicates the upper limit of the pulse pause (unit: ms).
         "
         DEFVAL      { 90 }
     ::= { hwPstnPTPConfigEntry 24 }

    hwPstnPTPPulsePauseLower OBJECT-TYPE
     SYNTAX      Integer32(10..200)
     MAX-ACCESS  read-write
     STATUS      current
     DESCRIPTION
         "
         Indicates the lower limit of the pulse pause (unit: ms).
         "
         DEFVAL      { 30 }
     ::= { hwPstnPTPConfigEntry 25 }
     
     hwPstnPTPProhibit OBJECT-TYPE
     SYNTAX      INTEGER{disable(1),enable(2)}
     MAX-ACCESS  read-write
     STATUS      current
     DESCRIPTION
         "
         Indicates whether to prohibit the PSTN port.   
         Options:
         1.disable(1)   -indicates that the PSTN port is unprohibited
         2.enable(2)    -indicates that the PSTN port is prohibited
         "
         DEFVAL      { disable }
     ::= { hwPstnPTPConfigEntry 26 }
     
     hwPstnPTPIdleOffhookTime OBJECT-TYPE
     SYNTAX      Integer32(5..25)
     MAX-ACCESS  read-write
     STATUS      current
     DESCRIPTION
         "
         Indicates the caller offhook recognised time (unit: 10ms).
         If the subscriber's A/B lines were detected in short circuit longer than this time as a caller party, 
         MG will report offhook message.
         "
         DEFVAL      { 8 }
     ::= { hwPstnPTPConfigEntry 27 }
     
     hwPstnPTPRingOffhookTime OBJECT-TYPE
     SYNTAX      Integer32(5..25)
     MAX-ACCESS  read-write
     STATUS      current
     DESCRIPTION
         "
         Indicates the callee offhook recognised time during ringing (unit: 10ms).
         While the subscriber was ringing as a callee party, if the A/B lines were detected in short circuit longer
         than this time,  MG will report offhook message.
         "
         DEFVAL      { 20 }
     ::= { hwPstnPTPConfigEntry 28 }
     
     hwPstnPTPFskOffhookTime OBJECT-TYPE
     SYNTAX      Integer32(5..25)
     MAX-ACCESS  read-write
     STATUS      current
     DESCRIPTION
         "
         Indicates the callee offhook recognised time during onhook data transmission (unit: 10ms).
         While the subscriber was called but not ringing, if the A/B lines were detected in short circuit longer
         than this time,  MG will report offhook message.
         "
         DEFVAL      { 5 }
     ::= { hwPstnPTPConfigEntry 29 }

     hwPstnPTPCurrentAdjustFactor OBJECT-TYPE
     SYNTAX      Integer32(0..100)
     MAX-ACCESS  read-write
     STATUS      current
     DESCRIPTION
         "
         Indicates the adjustive speed of the DC output voltage.
         "
         DEFVAL      { 100 }
     ::= { hwPstnPTPConfigEntry 30 }
     
     hwPstnPTPReversePolarityEnable OBJECT-TYPE
     SYNTAX      INTEGER{reversePolarityDisable(1),reversePolarityEnable(2)}
     MAX-ACCESS  read-write
     STATUS      current
     DESCRIPTION
         "
         Indicates whether to support the polarity reverse.  
         Options:
         1.reversePolarityDisable(1) -indicates the reverse polarity is disable
         2.reversePolarityEnable(2)  -indicates the reverse polarity is enable
         "
         DEFVAL      { reversePolarityEnable }
     ::= { hwPstnPTPConfigEntry 31 }

    hwPstnPTPPartyline OBJECT-TYPE
     SYNTAX      INTEGER{disable(1),enable(2)}
     MAX-ACCESS  read-write
     STATUS      current
     DESCRIPTION
        "
        Enables or disables party line on ports. Only two adjacent POTS ports (port IDs 2n and 2n + 1, n = 0, 1, 2...) can be combined as a party line port. Party line takes effect only when these two ports are enabled with party line.
        Options:
         1.disable(1)   -indicates that party line disabled
         2.enable(2)    -indicates that party line enabled
        "
         DEFVAL      { disable }
     ::= { hwPstnPTPConfigEntry 32 }
       
   hwPstnPTPOperTable OBJECT-TYPE
     SYNTAX      SEQUENCE OF HwPstnPTPOperEntry
     MAX-ACCESS  not-accessible
     STATUS      current
     DESCRIPTION
       "
       Indicates the operation table (management, maintenance, and status query) of the PSTN PTP layer. 
       The index of this table is  hwPstnPTPOperIndex.
       "
     ::= { hwIASVoicePortObjects 2 }
 
   hwPstnPTPOperEntry OBJECT-TYPE
     SYNTAX      HwPstnPTPOperEntry
     MAX-ACCESS  not-accessible
     STATUS      current
     DESCRIPTION
       "
       Indicates the operation table (management, maintenance, and status query) of the PSTN PTP layer.
       The index of this entry is  hwPstnPTPOperIndex.
       "
     INDEX    {  
               hwPstnPTPOperIndex
              }
     ::= { hwPstnPTPOperTable 1 }
 
   HwPstnPTPOperEntry ::=
     SEQUENCE
     {
       hwPstnPTPOperIndex               Integer32,
       hwPstnPTPSrvState                INTEGER,
       hwPstnPTPLoopBackState           INTEGER,
       hwPstnPTPTestState               INTEGER,
       hwPstnPTPAdminOper               INTEGER,
       hwPstnPTPSrvStateChange          TimeTicks,
       hwPstnPTPLoopBackStateChange     TimeTicks,
       hwPstnPTPTestStateChange         TimeTicks,
       hwPstnPTPLicenseState            INTEGER,
       hwPstnPTPLineState               INTEGER       
     }
 
   hwPstnPTPOperIndex OBJECT-TYPE
     SYNTAX      Integer32
     MAX-ACCESS  not-accessible
     STATUS      current
     DESCRIPTION
         "
         Indicates the shelf/slot/port index.
         "
     ::= { hwPstnPTPOperEntry 1 }
 
   hwPstnPTPSrvState OBJECT-TYPE
     SYNTAX      INTEGER{normal(1),fault(2),deactive(3),powerdeny(4)}
     MAX-ACCESS  read-only
     STATUS      current
     DESCRIPTION
         "
         PSTN port physic state: 
         Options:
         1.normal(1)    -indicates the PSTN port physic state is normal 
         2.fault(2)     -indicates the PSTN port physic state is fault
         3.deactive(3)  -indicates the PSTN port physic state is deactive
         4.powerdeny(4) -indicates the PSTN port physic state is powerdeny
         "
     ::= { hwPstnPTPOperEntry 2 }
 
   hwPstnPTPLoopBackState OBJECT-TYPE
     SYNTAX      INTEGER{noLoop(1),remoteLoop(2),localLoop(3)}
     MAX-ACCESS  read-only
     STATUS      current
     DESCRIPTION
         "
         PSTN port loop state:
         Options:
         1.noLoop(1)     -indicates the PSTN port loop state is no loop
         2.remoteLoop(2) -indicates the PSTN port loop state is remote loop
         3.localLoop(3)  -indicates the PSTN port loop state is local loop
         "
     ::= { hwPstnPTPOperEntry 3 }
 
   hwPstnPTPTestState OBJECT-TYPE
     SYNTAX      INTEGER{noTest(1),test(2)}
     MAX-ACCESS  read-only
     STATUS      current
     DESCRIPTION
         "
         PSTN port test state:
         Options:
         1.noTest(1)  -indicates that there is no test on the PSTN port
         2.test(2)    -indicates that there is a test on the PSTN port
         "
     ::= { hwPstnPTPOperEntry 4 }
     
   hwPstnPTPAdminOper OBJECT-TYPE
     SYNTAX      INTEGER{reset(1),localLoop(2),remoteLoop(3),cancelLoop(4),clearLineFault(5),invalidvalue(-1)}
     MAX-ACCESS  read-write
     STATUS      current
     DESCRIPTION
         "
         Indicates the maintenance operation of the physical layer of the PSTN port. 
         Options:
         1.reset(1)          -indicates the maintenance operation is reset      
         2.localLoop(2)      -indicates the maintenance operation is local loop
         3.remoteLoop(3)     -indicates the maintenance operation is remote loop
         4.cancelLoop(4)     -indicates the maintenance operation is cancel loop
         5.clearLineFault(5) -indicates the maintenance operation is clear line fault 
         6.invalidvalue(-1)  -indicates an invalid value.
         "
     ::= { hwPstnPTPOperEntry 5 }
 
   hwPstnPTPSrvStateChange OBJECT-TYPE
     SYNTAX      TimeTicks
     MAX-ACCESS  read-only
     STATUS      current
     DESCRIPTION
         "
         Indicates the service running status changing time of the PSTN port.
         "
     ::= { hwPstnPTPOperEntry 6 }
 
   hwPstnPTPLoopBackStateChange OBJECT-TYPE
     SYNTAX      TimeTicks
     MAX-ACCESS  read-only
     STATUS      current
     DESCRIPTION
         "
         Indicates the physical loopback status changing time of the PSTN port.
         "
     ::= { hwPstnPTPOperEntry 7 }
     
    hwPstnPTPTestStateChange OBJECT-TYPE
     SYNTAX      TimeTicks
     MAX-ACCESS  read-only
     STATUS      current
     DESCRIPTION
         "
         Indicates the physical test status changing time of the PSTN port.
         "
     ::= { hwPstnPTPOperEntry 8 }       
  
    hwPstnPTPLicenseState OBJECT-TYPE
     SYNTAX      INTEGER{noConfigure(1),noLicense(2),licensed(3)}
     MAX-ACCESS  read-only
     STATUS      current
     DESCRIPTION
         "
         Indicates the service license status of the PSTN port.
         Options:
         1.noConfigure(1) -indicates the service license status of the PSTN port is no configuration       
         2.noLicense(2)   -indicates the service license status of the PSTN port is no license
         3.licensed(3)    -indicates the service license status of the PSTN port is licensed
         "
     ::= { hwPstnPTPOperEntry 9 }   
     
     hwPstnPTPLineState OBJECT-TYPE
     SYNTAX      INTEGER{normal(1),onEarth(2),unknown(3)}
     MAX-ACCESS  read-only
     STATUS      current
     DESCRIPTION
         "
         PSTN port line state: 
         Options:
         1.normal(1)  -indicates that the state of PSTN port line is normal 
         2.onEarth(2) -indicates that the state of PSTN port line on earth
         3.unknown(3) -indicates that the state of PSTN port line is unknown
         "
     ::= { hwPstnPTPOperEntry 10 }    

   hwBraPTPConfigTable OBJECT-TYPE
     SYNTAX      SEQUENCE OF HwBraPTPConfigEntry
     MAX-ACCESS  not-accessible
     STATUS      current
     DESCRIPTION
       "
       Indicates the physical attribute configuration table of the BRA port.
       The index of this table is hwBraPTPIndex. 
       "
     ::= { hwIASVoicePortObjects 3 }
 
   hwBraPTPConfigEntry OBJECT-TYPE
     SYNTAX      HwBraPTPConfigEntry
     MAX-ACCESS  not-accessible
     STATUS      current
     DESCRIPTION
       "
       Indicates the physical attribute configuration table of the BRA port.
       The index of this entry is hwBraPTPIndex.
       "
     INDEX    {  
               hwBraPTPIndex
              }
     ::= { hwBraPTPConfigTable 1 }
 
   HwBraPTPConfigEntry ::=
     SEQUENCE
     {
       hwBraPTPIndex                    Integer32,
       hwBraPTPRPower                   INTEGER,
       hwBraPTPAutoDeactive             INTEGER,
       hwBraPTPAutoDeactiveDelay        Integer32,
       hwBraPTPWorkMode                 INTEGER,
       hwBraPTPPowerState               INTEGER,
       hwBraPTPConfigState              INTEGER,
       hwBraPTPL1ActiveMode             INTEGER,
       hwBraPTPUniAlarmReport           INTEGER,
       hwBraPTPL2Monitor                INTEGER,
       hwBraPTPActivePeriod             Integer32,
       hwBraPTPActualWorkMode           INTEGER,
       hwBraPTPNlpMode                  INTEGER
     }
 
   hwBraPTPIndex OBJECT-TYPE
     SYNTAX      Integer32
     MAX-ACCESS  not-accessible
     STATUS      current
     DESCRIPTION
         "
         Indicates the shelf/slot/port index.
         "
     ::= { hwBraPTPConfigEntry 1 }
 
   hwBraPTPRPower OBJECT-TYPE
     SYNTAX      INTEGER{disable(1), enable(2)}
     MAX-ACCESS  read-write
     STATUS      current
     DESCRIPTION
         "
         Indicates whether remote power supply is supported. 1-Not supported; 2-Supported.
         Options:
         1.disable(1) -not support remote power supply
         2.enable(2)  -support remote power supply
         "
         DEFVAL      { disable }
     ::= { hwBraPTPConfigEntry 2 }
 
   hwBraPTPAutoDeactive OBJECT-TYPE
     SYNTAX      INTEGER{disable(1), enable(2)}
     MAX-ACCESS  read-write
     STATUS      current
     DESCRIPTION
         "
         Indicates whether automatic deactivation is supported. 1-Not supported; 2-Supported.
         Options:
         1.disable(1) -not support automatic deactivation
         2.enable(2)  -support automatic deactivation
         "
         DEFVAL      { disable }
     ::= { hwBraPTPConfigEntry 3 }
 
   hwBraPTPAutoDeactiveDelay OBJECT-TYPE
     SYNTAX      Integer32(10..360) 
     MAX-ACCESS  read-write
     STATUS      current
     DESCRIPTION
         "
         Indicates the automatic deactivation delay of the BRA (unit: second).
         "
         DEFVAL      { 30 }
     ::= { hwBraPTPConfigEntry 4 }
     
  hwBraPTPWorkMode OBJECT-TYPE
     SYNTAX      INTEGER{p2mp(1), p2p(2), auto(3)}
     MAX-ACCESS  read-write
     STATUS      current
     DESCRIPTION
         "
         Indicates the BRA port working mode.             
         Options:
         1.p2mp(1) -indicates Point to multi-point
         2.p2p(2)  -indicates Point to point  
         3.auto(3) -indicates the adaptive manner, the result of consultation may be p2mp or p2p
         "
         DEFVAL      { p2mp }
     ::= { hwBraPTPConfigEntry 5 }
 
   hwBraPTPPowerState OBJECT-TYPE
     SYNTAX      INTEGER{state1(1),state2(2),state3(3),state4(4),invalidvalue(-1)}
     MAX-ACCESS  read-only
     STATUS      current
     DESCRIPTION
         " 
         Indicates the power status of the NT1. 1-Active power supply (PS1); 2-Standby power supply (PS2).
         Options:
         1.state1(1) -indicates PS1 is normal; PS2 is normal
         2.state2(2) -indicates PS1 is normal; PS2 is abnormal
         3.state3(3) -indicates PS1 is abnormal; PS2 is normal
         4.state4(4) -indicates PS1 is abnormal; PS2 is abnormal
         5.invalidvalue(-1) -indicates an invalid value.
         "
     ::= { hwBraPTPConfigEntry 6 }
     
  hwBraPTPConfigState OBJECT-TYPE
     SYNTAX      INTEGER{notConfigUserType(1),configUserType(2)}
     MAX-ACCESS  read-only
     STATUS      current
     DESCRIPTION
         "
         Indicates the configuration status of the subscriber type. 
         Options:
         1.notConfigUserType(1) -not configured
         2.configUserType(2)    -configured
         "
     ::= { hwBraPTPConfigEntry 7}

  hwBraPTPL1ActiveMode OBJECT-TYPE
     SYNTAX      INTEGER{stableActive(1),unstableActive(2)}
     MAX-ACCESS  read-write
     STATUS      current
     DESCRIPTION
         "
         Indicates layer 1 active mode of bra port.
         Options:
         1.stableActive(1)      -indicates the layer 1 active mode of bra port is stable active
         2.unstableActive(2)    -indicates the layer 1 active mode of bra port is unstable active
         "
     ::= { hwBraPTPConfigEntry 8}
     
  hwBraPTPUniAlarmReport OBJECT-TYPE
     SYNTAX      INTEGER{enable(1),disable(2)}
     MAX-ACCESS  read-write
     STATUS      current
     DESCRIPTION
         "
         Indicates enable user network interface fault alarm or not.
         Options:
         1.enable(1)    -indicates enable the user network interface fault alarm
         2.disable(2)   -indicates disable the user network interface fault alarm
         Default: disable(2)
         "
     ::= { hwBraPTPConfigEntry 9}
  
  hwBraPTPL2Monitor OBJECT-TYPE
     SYNTAX      INTEGER{disable(1),enable(2)}
     MAX-ACCESS  read-write
     STATUS      current
     DESCRIPTION
         "
         Indicates enable layer 2 error statistic of bra port or not.
         Options:
         1.disable(1) -indicates disable the layer 2 error statistic of bra port
         2.enable(2)  -indicates enable the layer 2 error statistic of bra port
         Default:disable(2)
         "
     ::= { hwBraPTPConfigEntry 10}

   hwBraPTPActivePeriod OBJECT-TYPE
     SYNTAX      Integer32(0..60) 
     MAX-ACCESS  read-write
     STATUS      current
     DESCRIPTION
         "
         Indicates the interval of the periodical automatic activation. 0 means that periodical automatic activation is disabled (unit: minutes).
         "
         DEFVAL      { 0 }
     ::= { hwBraPTPConfigEntry 11 }     

   hwBraPTPActualWorkMode OBJECT-TYPE
     SYNTAX      INTEGER{p2mp(1),p2p(2)}
     MAX-ACCESS  read-only
     STATUS      current
     DESCRIPTION
         "
         Indicates the BRA port actual working mode.
         Options:
         1.p2mp(1) -indicates Point to multi-point
         2.p2p(2)  -indicates Point to point
         "
     ::= { hwBraPTPConfigEntry 12}
     
   hwBraPTPNlpMode OBJECT-TYPE
     SYNTAX      INTEGER{normalMode(1),ecgainMode(2),increasedMode(3),reducedMode(4),close(5),dtmfEcMode(6)}
     MAX-ACCESS  read-write
     STATUS      current
     DESCRIPTION
         "
         Indicates the Nlp mode of the port.    
 	 Options:
 	 1.normalMode(1)      -indicates enable the function of non-linear process for echo control performance in default level
 	 2.ecgainMode(2)      -indicates enable the function to config the gain value for ec with the non-linear process
 	 3.increasedMode(3)   -indicates For certain 2-to-4 wire hybrid or line conditions where a larger than normal non-linear 
 	                        	  component in the echo is present,setting for an increased level of NLP engagement in order to 
 	                        	  provide an adequate echo control performance
 	 4.reducedMode(4)     -indicates For applications where the default NLP level causes unpleasant voice artifacts (like choppiness
 	                        	  at the beginning of the call in heavy double talk situations), the Host may select the NLP Tune
 	                        	  setting to reduce the level of NLP engagement
 	 5.close(5)           -indicates disable the function of non-linear process for echo control performance
 	 6.dtmfEcMode(6)      -indicates DTMF echo elimination
         "
         DEFVAL      { normalMode }
     ::= { hwBraPTPConfigEntry 13}

   hwBraPTPOperTable OBJECT-TYPE
     SYNTAX      SEQUENCE OF HwBraPTPOperEntry
     MAX-ACCESS  not-accessible
     STATUS      current
     DESCRIPTION
       "
       Indicates the operation table (management, maintenance, and status query) of the BRA PTP layer.
       The index of this table is hwBraPTPOperIndex.
       "
     ::= { hwIASVoicePortObjects 4 }
     
   hwBraPTPOperEntry OBJECT-TYPE
     SYNTAX      HwBraPTPOperEntry
     MAX-ACCESS  not-accessible
     STATUS      current
     DESCRIPTION
       "
       Indicates the operation table (management, maintenance, and status query) of the BRA PTP layer.
       The index of this entry is hwBraPTPOperIndex.
       "
     INDEX    {  
              hwBraPTPOperIndex
              }
     ::= { hwBraPTPOperTable 1 }
 
   HwBraPTPOperEntry ::=
     SEQUENCE
     {
       hwBraPTPOperIndex              Integer32,
       hwBraPTPSrvState               INTEGER,
       hwBraPTPLoopBackState          INTEGER,
       hwBraPTPTestState              INTEGER,
       hwBraPTPAdminOper              INTEGER,
       hwBraPTPSrvStateChange         TimeTicks,
       hwBraPTPLoopBackStateChange    TimeTicks,
       hwBraPTPTestStateChange        TimeTicks,
       hwBraPTPLicenseState           INTEGER,
       hwBraPTPAlarmState             BITS         
     }
 
   hwBraPTPOperIndex OBJECT-TYPE
     SYNTAX      Integer32
     MAX-ACCESS  not-accessible
     STATUS      current
     DESCRIPTION
         "
         Indicates the shelf/slot/port index.
         "
     ::= { hwBraPTPOperEntry 1 }
 
   hwBraPTPSrvState OBJECT-TYPE
     SYNTAX      INTEGER{normal(1),fault(2),deactive(3)}
     MAX-ACCESS  read-only
     STATUS      current
     DESCRIPTION
         "
         Indicates the service running status of the BRA port.
         Options:
         1.normal(1)    -indicates the service running status of the BRA port is normal
         2.fault(2)     -indicates the service running status of the BRA port is fault
         3.deactive(3)  -indicates the service running status of the BRA port is deactive
         "
     ::= { hwBraPTPOperEntry 2 }
 
   hwBraPTPLoopBackState OBJECT-TYPE
     SYNTAX      INTEGER{noLoop(1),remoteLoop(2),localLoop(3)}
     MAX-ACCESS  read-only
     STATUS      current
     DESCRIPTION
         "  
         Indicates the physical loopback status of the BRA port.
         Options: 
         1.noLoop(1)     -indicates the loopback status is no loop
         2.remoteLoop(2) -indicates the loopback status is remote loop
         3.localLoop(3)  -indicates the loopback status is local loop
         "
     ::= { hwBraPTPOperEntry 3 }
     
   hwBraPTPTestState OBJECT-TYPE
     SYNTAX      INTEGER{noTest(1),test(2)}
     MAX-ACCESS  read-only
     STATUS      current
     DESCRIPTION
         "
         Indicates the test status of the BRA port.
         Options:
         1.noTest(1) -indicates there is no test
         2.test(2)   -indicates there is a test   
         "
     ::= { hwBraPTPOperEntry 4 }
 
   hwBraPTPAdminOper OBJECT-TYPE
     SYNTAX      INTEGER{reset(1),localLoop(2),remoteLoop(3),cancelLoop(4),active(5),deactive(6),invalidvalue(-1)}
     MAX-ACCESS  read-write
     STATUS      current
     DESCRIPTION
         "
         Indicates the maintenance operation of the physical layer of the BRA port.         
         Options:
         1.reset(1)      -indicates the maintenance operation is reset
         2.localLoop(2)  -indicates the maintenance operation is local loop
         3.remoteLoop(3) -indicates the maintenance operation is remote loop
         4.cancelLoop(4) -indicates the maintenance operation is no loop
         5.active(5)     -indicates the maintenance operation is active
         6.deactive(6)   -indicates the maintenance operation is deactive
         7.invalidvalue(-1) -indicates an invalid value.         
         "
     ::= { hwBraPTPOperEntry 5 }
 
   hwBraPTPSrvStateChange OBJECT-TYPE
     SYNTAX      TimeTicks
     MAX-ACCESS  read-only
     STATUS      current
     DESCRIPTION
         "
         Indicates the service running status changing time of the BRA port.
         "
     ::= { hwBraPTPOperEntry 6 }
 
   hwBraPTPLoopBackStateChange OBJECT-TYPE
     SYNTAX      TimeTicks
     MAX-ACCESS  read-only
     STATUS      current
     DESCRIPTION
         "
         Indicates the loopback status changing time of the BRA port.
         "
     ::= { hwBraPTPOperEntry 7 }
     
   hwBraPTPTestStateChange OBJECT-TYPE
     SYNTAX      TimeTicks
     MAX-ACCESS  read-only
     STATUS      current
     DESCRIPTION
         "
         Indicates the test status changing time of the BRA port.
         "
     ::= { hwBraPTPOperEntry 8 }
 
    hwBraPTPLicenseState OBJECT-TYPE
     SYNTAX      INTEGER{noConfigure(1),noLicense(2),licensed(3)}
     MAX-ACCESS  read-only
     STATUS      current
     DESCRIPTION
         "
         Indicates the service license status of the BRA port. 
         Options:
         1.noConfigure(1) -indicates the service license status is no configuration
         2.noLicense(2)   -indicates the service license status is no license
         3.licensed(3)    -indicates the service license status is licensed
         "
     ::= { hwBraPTPOperEntry 9 }   
     
    hwBraPTPAlarmState OBJECT-TYPE
     SYNTAX      BITS{bit0(0),bit1(1),bit2(2),bit3(3),bit4(4)}
     MAX-ACCESS  read-only
     STATUS      current
     DESCRIPTION
         "
         Indicates the alarm state of bra port,from left to right,each bit represents one alarm state.
         Options:
         1.bit0(0)  -indicates LT overload
         2.bit1(1)  -indicates S port fault(EI2)
         3.bit2(2)  -indicates U port fault(LOS/RSY)
         4.bit3(3)  -indicates S port deactive(SAI)
         5.bit4(4)  -indicates U port deactive(ACT) 
         0 means no alarm present
         1 means the alarm present
         "
     ::= { hwBraPTPOperEntry 10}

    
 
   hwBRAPTPPerformanceStatTable OBJECT-TYPE
     SYNTAX      SEQUENCE OF HwBRAPTPPerformanceStatEntry
     MAX-ACCESS  not-accessible
     STATUS      current
     DESCRIPTION
       "
       Indicates the performance statistics table of the BRA PTP layer.
       The index of this table is hwBraPTPPerforIndex.
       "
     ::= { hwIASVoicePortObjects 5 }
 
   hwBRAPTPPerformanceStatEntry OBJECT-TYPE
     SYNTAX      HwBRAPTPPerformanceStatEntry
     MAX-ACCESS  not-accessible
     STATUS      current
     DESCRIPTION
       "
       Indicates the performance statistics table of the BRA PTP layer.
       The index of this entry is hwBraPTPPerforIndex.
       "
     INDEX    {  
               hwBraPTPPerforIndex
              }
     ::= { hwBRAPTPPerformanceStatTable 1 }
 
   HwBRAPTPPerformanceStatEntry ::=
     SEQUENCE
     {
       hwBraPTPPerforIndex              Integer32,
       hwBraPTPPerformanceStatOprType   INTEGER,
       hwBraPTPPerformanceStatPeri      Integer32,
       hwBraPTPErrorcode                Integer32,
       hwBraPTPNebeUas                  Integer32,
       hwBraPTPFebeUas                  Integer32,
       hwBraPTPNebeEs                   Integer32,
       hwBraPTPFebeEs                   Integer32,
       hwBraPTPNebeSes                  Integer32,
       hwBraPTPFebeSes                  Integer32
     }
 
   hwBraPTPPerforIndex OBJECT-TYPE
    SYNTAX      Integer32
    MAX-ACCESS  not-accessible
    STATUS      current
    DESCRIPTION
        " 
        Indicates the shelf/slot/port index. 
        "
    ::= { hwBRAPTPPerformanceStatEntry 1 }    
    
    hwBraPTPPerformanceStatOprType OBJECT-TYPE
    SYNTAX      INTEGER{stop(1), start(2)}
    MAX-ACCESS  read-write
    STATUS      current
    DESCRIPTION
        " 
        Indicates the status of the performance statistics operation. 
        Options:
        1.stop(1)   -indicates the status of the performance statistics operation is stop
        2.start(2)  -indicates the status of the performance statistics operation is start
        "
    ::= { hwBRAPTPPerformanceStatEntry 2 }   
    
    hwBraPTPPerformanceStatPeri OBJECT-TYPE
    SYNTAX      Integer32(1..5)
    MAX-ACCESS  read-write
    STATUS      current
    DESCRIPTION
        " 
        Indicates the performance statistics period (minute).
        "
    ::= { hwBRAPTPPerformanceStatEntry 3 }   
    
    hwBraPTPErrorcode OBJECT-TYPE
    SYNTAX      Integer32(50..84)
    MAX-ACCESS  read-write
    STATUS      current
    DESCRIPTION
        " 
        Indicates the threshold of error code (count of error code).
        "
    ::= { hwBRAPTPPerformanceStatEntry 4 }
    
    hwBraPTPNebeUas OBJECT-TYPE
    SYNTAX      Integer32
    MAX-ACCESS  read-only
    STATUS      current
    DESCRIPTION
        "
        Indicates the Near End Block Error (NEBE) unavailable seconds (second). 
        "
    ::= { hwBRAPTPPerformanceStatEntry 5 }   
    
    hwBraPTPFebeUas OBJECT-TYPE
    SYNTAX      Integer32
    MAX-ACCESS  read-only
    STATUS      current
    DESCRIPTION
        "
        Indicates the Far End Block Error (FEBE) unavailable seconds (second). 
        "
    ::= { hwBRAPTPPerformanceStatEntry 6 }
    
    hwBraPTPNebeEs OBJECT-TYPE
    SYNTAX      Integer32
    MAX-ACCESS  read-only
    STATUS      current
    DESCRIPTION
        "
        Indicates the NEBE errored seconds (second). 
        "
    ::= { hwBRAPTPPerformanceStatEntry 7 }
    
    hwBraPTPFebeEs OBJECT-TYPE
    SYNTAX      Integer32
    MAX-ACCESS  read-only
    STATUS      current
    DESCRIPTION
        "
        Indicates the FEBE errored seconds (second). 
        "
    ::= { hwBRAPTPPerformanceStatEntry 8 }
    
    hwBraPTPNebeSes OBJECT-TYPE
    SYNTAX      Integer32
    MAX-ACCESS  read-only
    STATUS      current
    DESCRIPTION
        "
        Indicates the NEBE severely errored seconds (second). 
        "
    ::= { hwBRAPTPPerformanceStatEntry 9 }
    
    hwBraPTPFebeSes OBJECT-TYPE
    SYNTAX      Integer32
    MAX-ACCESS  read-only
    STATUS      current
    DESCRIPTION
        "
        Indicates the FEBE severely errored seconds (second). 
        "
    ::= { hwBRAPTPPerformanceStatEntry 10 } 
     
   hwE1PTPConfigTable OBJECT-TYPE
     SYNTAX      SEQUENCE OF HwE1PTPConfigEntry
     MAX-ACCESS  not-accessible
     STATUS      current
     DESCRIPTION
       "
       Indicates the configuration table (attribute configuration and query) of the E1 PTP layer.
       The index of this table is hwE1PTPIndex.
       "
     ::= { hwIASVoicePortObjects 6 }
   
   hwE1PTPConfigEntry OBJECT-TYPE
     SYNTAX      HwE1PTPConfigEntry
     MAX-ACCESS  not-accessible
     STATUS      current
     DESCRIPTION
       "
       Indicates the configuration table (attribute configuration and query) of the E1 PTP layer.
       The index of this entry is hwE1PTPIndex.
       "
     INDEX    {  
               hwE1PTPIndex
              }
     ::= { hwE1PTPConfigTable 1 }
 
   HwE1PTPConfigEntry ::=
     SEQUENCE
     {
       hwE1PTPIndex             Integer32,
       hwE1PTPFrameVerifyMode   INTEGER,
       hwE1PTPImpedance         INTEGER,
       hwE1PTPSignalType        INTEGER,
       hwE1PTPConfigState       INTEGER,
       hwE1PTPAccessDSMode      INTEGER,
       hwE1PTPErrAlarmSet       BITS,
       hwE1PTPL2Monitor         INTEGER,
       hwE1PTPLineCode          INTEGER
     }
 
   hwE1PTPIndex OBJECT-TYPE
     SYNTAX      Integer32
     MAX-ACCESS  not-accessible
     STATUS      current
     DESCRIPTION
         "
         Indicates the shelf/slot/port index.
         "
     ::= { hwE1PTPConfigEntry 1 }
 
   hwE1PTPFrameVerifyMode OBJECT-TYPE
     SYNTAX      INTEGER{enable(1),disable(2)}
     MAX-ACCESS  read-write
     STATUS      current
     DESCRIPTION
         "
         Indicates the CRC4 frame check.
         Options:
         1.enable(1)  -indicates the CRC4 frame check is enable
         2.disable(2) -indicates the CRC4 frame check is disable
         "
         DEFVAL      { disable }
     ::= { hwE1PTPConfigEntry 2 }
 
   hwE1PTPImpedance OBJECT-TYPE
     SYNTAX      INTEGER{ohm75(1),ohm120(2)}
     MAX-ACCESS  read-write
     STATUS      current
     DESCRIPTION
         "
         Indicates the port impedance.
         Options:
         1.ohm75(1)  -indicates the port impedance is 75 ohm
         2.ohm120(2) -indicates the port impedance is 120 ohm
         "
         DEFVAL      { ohm75 }
     ::= { hwE1PTPConfigEntry 3 }
 
   hwE1PTPSignalType OBJECT-TYPE
     SYNTAX      INTEGER{ccs(1),cas(2),unframe(3)}
     MAX-ACCESS  read-write
     STATUS      current
     DESCRIPTION
         "
         Indicates the signaling type.   
         Options:
         1.ccs(1)     -indicates the signaling type is ccs
         2.cas(2)     -indicates the signaling type is cas
         3.unframe(3) -indicates the signaling type is unframe
         "
         DEFVAL      { ccs }
     ::= { hwE1PTPConfigEntry 4 }
     
   hwE1PTPConfigState OBJECT-TYPE
     SYNTAX      INTEGER{notConfigUserType(1),configVoiceUserType(2),configPWUserType(3),configNativeTDM(4)}
     MAX-ACCESS  read-only
     STATUS      current
     DESCRIPTION
         "
         Indicates the configuration status of the subscriber type.
         Options:
         1.notConfigUserType(1)     -not configured
         2.configVoiceUserType(2)   -configured MG PRA subscriber
         3.configPWUserType(3)      -configured PW user 
         4.configNativeTDM(4)       -configured Native TDM
         "
     ::= { hwE1PTPConfigEntry 5}
     
  hwE1PTPAccessDSMode OBJECT-TYPE
     SYNTAX      INTEGER{digitalAccess(1),directAccess(2)}
     MAX-ACCESS  read-write
     STATUS      current
     DESCRIPTION
         "
         Indicates physical layer digital section access mode of e1 port,default:digitalAccess(1).
         Options:
         1.digitalAccess(1) -digital access
         2.directAccess(2)  -direct access
         "
     ::= { hwE1PTPConfigEntry 6}
  
  hwE1PTPErrAlarmSet OBJECT-TYPE
     SYNTAX      BITS{bit0(0),bit1(1),bit2(2),bit3(3),bit4(4),bit5(5)}
     MAX-ACCESS  read-write
     STATUS      current
     DESCRIPTION
         "
         Indicates set e1 error alarm switch,from left to right,each bit respresent a switch,default:111000
         Options:
         1.bit0(0)  -indicates report pcm line fault alarm        
         2.bit1(1)  -indicates when error rate reached ULF(Unconditional Line Fai2008-5-30 14:24lure)threshold,report pcm line fault alarm            
         3.bit2(2)  -indicates when error rate reached OLF(Optional Line Failure) threshold,report pcm line fault alarm
         4.bit3(3)  -indicates when error rate reached LDT(Line Disturbance Transient Event) threshold,report E1 digital line transient event alarm
         5.bit4(4)  -indicates when E1 frame slip frequency exceeded in observation interval reached degraded threshold,report event alarm
         6.bit5(5)  -indicates when any line temporary event occurs,report event alarm
         "
     ::= { hwE1PTPConfigEntry 7}
  
  hwE1PTPL2Monitor OBJECT-TYPE
     SYNTAX      INTEGER{disable(1),enable(2)}
     MAX-ACCESS  read-write
     STATUS      current
     DESCRIPTION
         "
         enable layer 2 error statistic of e1 port or not,default:enable(2).
         Options:
         1.disable(1) -indicates the layer 2 error statistic of e1 port is disable
         2.enable(2)  -indicates the layer 2 error statistic of e1 port is enable
         "
     ::= { hwE1PTPConfigEntry 8}

  hwE1PTPLineCode OBJECT-TYPE
     SYNTAX      INTEGER{hdb3(1),ami(2)}
     MAX-ACCESS  read-write
     STATUS      current
     DESCRIPTION
         "
         line code of e1 port,default:hdb3(1).
         Options:
         1.hdb3(1) -indicates the line code of e1 port is hdb3
         2.ami(2)  -indicates the line code of e1 port is ami
         "
     ::= { hwE1PTPConfigEntry 9}
     
   hwE1PTPOperTable OBJECT-TYPE
     SYNTAX      SEQUENCE OF HwE1PTPOperEntry
     MAX-ACCESS  not-accessible
     STATUS      current
     DESCRIPTION
       "
       Indicates the operation table (management, maintenance, and status query) of the E1 PTP layer.
       The index of this table is hwE1PTPOperIndex.
       "
     ::= { hwIASVoicePortObjects 7 }
 
   hwE1PTPOperEntry OBJECT-TYPE
     SYNTAX      HwE1PTPOperEntry
     MAX-ACCESS  not-accessible
     STATUS      current
     DESCRIPTION
       "
       Indicates the operation table (management, maintenance, and status query) of the E1 PTP layer.
       The index of this entry is hwE1PTPOperIndex.
       "
     INDEX    {  
               hwE1PTPOperIndex
              }
     ::= { hwE1PTPOperTable 1 }
 
   HwE1PTPOperEntry ::=
     SEQUENCE
     {
       hwE1PTPOperIndex           Integer32,
       hwE1PTPSrvState            INTEGER,
       hwE1PTPLoopBackState       INTEGER,
       hwE1PTPAdminOper           INTEGER,
       hwE1PTPWarningState        Integer32,
       hwE1PTPLicenseState        INTEGER
     }
 
   hwE1PTPOperIndex OBJECT-TYPE
     SYNTAX      Integer32
     MAX-ACCESS  not-accessible
     STATUS      current
     DESCRIPTION
         "
         Indicates the shelf/slot/port index.
         "
     ::= { hwE1PTPOperEntry 1 }
 
   hwE1PTPSrvState OBJECT-TYPE
     SYNTAX      INTEGER{normal(1),fault(2),lineAbnormal(3)}
     MAX-ACCESS  read-only
     STATUS      current
     DESCRIPTION
         "
         Indicates the service running status of the E1 port.
         Options:
         1.normal(1)        -indicates the service running status of e1 port is normal
         2.fault(2)         -indicates the service running status of e1 port is fault         
         3.lineAbnormal(3)  -indicates the service running status of e1 port is line abnormal
         "
     ::= { hwE1PTPOperEntry 2 }
 
   hwE1PTPLoopBackState OBJECT-TYPE
     SYNTAX      INTEGER{noLoop(1),remoteLoop(2),localLoop(3),eocLoop(4)}
     MAX-ACCESS  read-only
     STATUS      current
     DESCRIPTION
         "
         Indicates the physical loopback status of the E1 port.         
         Options:
         1.noLoop(1)        -indicates the loopback status of e1 port is no loop
         2.remoteLoop(2)    -indicates the loopback status of e1 port is remote loop
         3.localLoop(3)     -indicates the loopback status of e1 port is local loop
         4.eocLoop(4)       -indicates the loopback status of e1 port is EOC loop
         "
     ::= { hwE1PTPOperEntry 3 }
 
   hwE1PTPAdminOper OBJECT-TYPE
     SYNTAX      INTEGER{reset(1),localLoop(2),remoteLoop(3),cancelLoop(4),invalidvalue(-1)}
     MAX-ACCESS  read-write
     STATUS      current
     DESCRIPTION
         "
         Indicates the maintenance operation of the physical layer of the E1 port.
         Options:
         1.reset(1)         -indicates the maintenance operation of e1 port is no reset
         2.localLoop(2)     -indicates the maintenance operation of e1 port is local loop
         3.remoteLoop(3)    -indicates the maintenance operation of e1 port is remote loop 
         4.cancelLoop(4)    -indicates the maintenance operation of e1 port is no loop
         5.invalidvalue(-1) -indicates an invalid value
         "
     ::= { hwE1PTPOperEntry 4 }
 
   hwE1PTPWarningState OBJECT-TYPE
     SYNTAX      Integer32(-1|0..4294967295)
     MAX-ACCESS  read-only
     STATUS      current
     DESCRIPTION
         "
         Indicates the alarm status of the E1 line.
         Bit0: LOS (0: no LOS alarm; 1: LOS alarm occurs)
         Bit1: AIS (0: no AIS alarm; 1: AIS alarm occurs)
         Bit2: LFA (0: no LFA alarm; 1: LFA alarm occurs)
         it3: LMFA (0: no LMFA alarm; 1: LMFA alarm occurs)
         it4: RRA (0: no RRA alarm; 1: RRA alarm occurs)
         it5: CRCER (0: no CRCER alarm; 1: CRCER alarm occurs)
         it6:SCOL alarm
         it7:ULF alarm
         it8:OLF alarm
         it9:LDT alarm
         it10:error second alarm,in direction ET/LT to NT1
         it11:error second alarm,in direction NT1 to ET/LT 
         it12:sequential severe error second alarm,in direction ET/LT to NT1
         it13:sequential severe error second alarm,in direction NT1 to ET/LT
         it14:degrade minute alarm,in direction ET/LT to NT1
         it15:degrade minute alarm,in direction NT1 to ET/LT
        
         1: Invalid value
         "   
     ::= { hwE1PTPOperEntry 5 }
    
   hwE1PTPLicenseState OBJECT-TYPE
     SYNTAX      INTEGER{noConfigure(1),noLicense(2),licensed(3)}
     MAX-ACCESS  read-only
     STATUS      current
     DESCRIPTION
         "
         Indicates the service license status of the E1 port.
         Options:
         1.noConfigure(1) -indicates the service license status of the E1 port is no configuration       
         2.noLicense(2)   -indicates the service license status of the E1 port is no license
         3.licensed(3)    -indicates the service license status of the E1 port is licensed
         "
     ::= { hwE1PTPOperEntry 9 }   
    
   hwGTCOperateTable OBJECT-TYPE
     SYNTAX      SEQUENCE OF HwGTCOperateEntry
     MAX-ACCESS  not-accessible
     STATUS      current
     DESCRIPTION
       "
       Indicates the GTC operation table (test control).
       The index of this table is hwGTCIndex.
       "
     ::= { hwIASVoicePortObjects 8 }
 
   hwGTCOperateEntry OBJECT-TYPE
     SYNTAX      HwGTCOperateEntry
     MAX-ACCESS  not-accessible
     STATUS      current
     DESCRIPTION
       "
       Indicates the GTC operation table (test control).
       The index of this entry is hwGTCIndex.
       "
     INDEX    {  
               hwGTCIndex
              }
     ::= { hwGTCOperateTable 1 }
 
   HwGTCOperateEntry ::=
     SEQUENCE
     {
       hwGTCIndex                     Integer32,
       hwGTCTimer                     Integer32,
       hwGTCOperate                   INTEGER
     }
 
   hwGTCIndex OBJECT-TYPE
     SYNTAX      Integer32
     MAX-ACCESS  not-accessible
     STATUS      current
     DESCRIPTION
         "
         Indicates the GTC test index.
         "
     ::= { hwGTCOperateEntry 1 }
 
   hwGTCTimer OBJECT-TYPE
     SYNTAX      Integer32(1..600)
     MAX-ACCESS  read-write
     STATUS      current
     DESCRIPTION
         "
         Indicates the value of the GTC test timer.
         The system automatically stops the GTC test when the timer times out (unit: second).When the command for starting a test is delivered, the command must be bound to the test timer with a specified value.
         "
     ::= { hwGTCOperateEntry 2 }
 
   hwGTCOperate OBJECT-TYPE
     SYNTAX      INTEGER{undertest(1),finishtest(2),invalidvalue(-1)}
     MAX-ACCESS  read-write
     STATUS      current
     DESCRIPTION
         "
         Options:
         1.undertest(1) -indicates Start the GTC test
         2.finishtest(2) -indicates Stop the GTC test
         3.invalidvalue(-1) -indicates an invalid value
         "
     ::= { hwGTCOperateEntry 3 } 

     hwUserDefineRingTypeTable     OBJECT-TYPE
        SYNTAX         SEQUENCE OF HwUserDefineRingTypeEntry
        MAX-ACCESS     not-accessible
        STATUS         current
        DESCRIPTION
           "
           Indicates the user-defined ring type table.
           The index of this table is hwUserDefineRingType.
           "
    ::= { hwIASVoicePortObjects 9 }

    hwUserDefineRingTypeEntry         OBJECT-TYPE
       SYNTAX         HwUserDefineRingTypeEntry
       MAX-ACCESS     not-accessible
       STATUS         current
       DESCRIPTION    
          " 
          Indicates the user-defined ring type table.
          The index of this entry is hwUserDefineRingType.
          "
          INDEX    { 
                     hwUserDefineRingType
                   }
    ::= { hwUserDefineRingTypeTable  1 }

     HwUserDefineRingTypeEntry ::= SEQUENCE 
     {
        hwUserDefineRingType           Integer32,
        hwUserDefineRingPara1          Integer32,
        hwUserDefineRingPara2          Integer32,
        hwUserDefineRingPara3          Integer32,
        hwUserDefineRingPara4          Integer32,
        hwUserDefineRingPara5          Integer32,
        hwUserDefineRingPara6          Integer32     
           
     }

    hwUserDefineRingType         OBJECT-TYPE
        SYNTAX      Integer32(1..16) 
        MAX-ACCESS  not-accessible
        STATUS      current
        DESCRIPTION
         " Index of ring type "
    ::= { hwUserDefineRingTypeEntry 1 }

    hwUserDefineRingPara1         OBJECT-TYPE
        SYNTAX      Integer32(0..12750) 
        MAX-ACCESS  read-write
        STATUS      current
        DESCRIPTION
         "
         The first ring time length(>=100 and <= 12750, 0 means to cancel parameter value)(millisecond)
         "
    ::= { hwUserDefineRingTypeEntry 2 }


    hwUserDefineRingPara2         OBJECT-TYPE
        SYNTAX      Integer32(0..12750) 
        MAX-ACCESS  read-write
        STATUS      current
        DESCRIPTION
         "
         The first silent time length(>=100 and <= 12750, 0 means to cancel parameter value)(millisecond)
         "
    ::= { hwUserDefineRingTypeEntry 3 }

    hwUserDefineRingPara3         OBJECT-TYPE
        SYNTAX      Integer32(0..12750) 
        MAX-ACCESS  read-write
        STATUS      current
        DESCRIPTION
         "
         The second ring time length(>=100 and <= 12750, 0 means to cancel parameter value)(millisecond)
         "
    ::= { hwUserDefineRingTypeEntry 4 }

    hwUserDefineRingPara4         OBJECT-TYPE
        SYNTAX      Integer32(0..12750) 
        MAX-ACCESS  read-write
        STATUS      current
        DESCRIPTION
         "
         The second silent time length(>=100 and <= 12750,0 means to cancel parameter value)(millisecond)
         "
    ::= { hwUserDefineRingTypeEntry 5 }

    hwUserDefineRingPara5         OBJECT-TYPE
        SYNTAX      Integer32(0..12750) 
        MAX-ACCESS  read-write
        STATUS      current
        DESCRIPTION
         "
         The third ring time length(>=100 and <= 12750,0 means to cancel parameter value)(millisecond)
         "
    ::= { hwUserDefineRingTypeEntry 6 }

    hwUserDefineRingPara6         OBJECT-TYPE
        SYNTAX      Integer32(0..12750) 
        MAX-ACCESS  read-write
        STATUS      current
        DESCRIPTION
         "
         The third silent time length(>=100 and <= 12750,0 means to cancel parameter value)(millisecond)
         "
    ::= { hwUserDefineRingTypeEntry 7 } 

    hwPortDataTrapSequence OBJECT IDENTIFIER ::= { hwIASVoicePortObjects 10 }
        
        hwPstnPortDataTrapSequence OBJECT-TYPE
            SYNTAX Integer32
            MAX-ACCESS read-only
            STATUS current
            DESCRIPTION
                "
                  Indicates that the Trap sequence is reported after the PSTN port data changes.
                                "
            ::= { hwPortDataTrapSequence 1 }
        
        hwBraPortDataChangeSequence OBJECT-TYPE
            SYNTAX Integer32
            MAX-ACCESS read-only
            STATUS current
            DESCRIPTION
                "
                  Indicates that the Trap sequence is reported after the BRA port data changes.
                                "
            ::= { hwPortDataTrapSequence 2 }
        
        hwE1PortDataChangeSequence OBJECT-TYPE
            SYNTAX Integer32
            MAX-ACCESS read-only
            STATUS current
            DESCRIPTION
                "
                  Indicates that the Trap sequence is reported after the E1 port data changes.
                                "
            ::= { hwPortDataTrapSequence 3 }

   hwPstnPortStateStatisticTable OBJECT-TYPE
     SYNTAX      SEQUENCE OF HwPstnPortStateStatisticEntry
     MAX-ACCESS  not-accessible
     STATUS      current
     DESCRIPTION
       "
       Indicates the PSTN port status mapping table.
       The indexes of this table are hwPstnPTPFrameIndex and hwPstnPTPSlotIndex.
       "
     ::= { hwIASVoicePortObjects 11 }
 
   hwPstnPortStateStatisticEntry OBJECT-TYPE
     SYNTAX      HwPstnPortStateStatisticEntry
     MAX-ACCESS  not-accessible
     STATUS      current
     DESCRIPTION
       "
       Indicates the PSTN port status mapping table.
       The indexes of this entry are hwPstnPTPFrameIndex and hwPstnPTPSlotIndex.
       "
     INDEX    {  
           hwPstnPTPFrameIndex,
           hwPstnPTPSlotIndex 
              }
     ::= { hwPstnPortStateStatisticTable 1 }
 
   HwPstnPortStateStatisticEntry ::=
     SEQUENCE
     {       
       hwPstnPTPFrameIndex                      Integer32,
       hwPstnPTPSlotIndex                       Integer32,
       hwPstnBoardPortNumber                    Integer32,
       hwPstnPTPSrvStateBitmapList              OCTET STRING,
       hwPstnPTPLoopBackStateBitmapList         OCTET STRING,
       hwPstnPTPTestStateBitmapList             OCTET STRING
     }
 
   hwPstnPTPFrameIndex OBJECT-TYPE
     SYNTAX      Integer32
     MAX-ACCESS  not-accessible
     STATUS      current
     DESCRIPTION
         "
         Indicates the shelf index.
         "
     ::= { hwPstnPortStateStatisticEntry 1 }
     
   hwPstnPTPSlotIndex OBJECT-TYPE
     SYNTAX      Integer32
     MAX-ACCESS  not-accessible
     STATUS      current
     DESCRIPTION
         "
         Indicates the slot index.
         "
     ::= { hwPstnPortStateStatisticEntry 2 } 
    
   hwPstnBoardPortNumber OBJECT-TYPE
     SYNTAX      Integer32
     MAX-ACCESS  read-only
     STATUS      current
     DESCRIPTION
         "
         Indicates the total number of ports on the specified PSTN service board.
         "
     ::= { hwPstnPortStateStatisticEntry 3 } 

   hwPstnPTPSrvStateBitmapList OBJECT-TYPE
     SYNTAX      OCTET STRING
     MAX-ACCESS  read-only
     STATUS      current
     DESCRIPTION
         "
         Indicates the bit mapping table of the service running status of all the PSTN ports of the specified board (the status table consists of variable-length character strings, and each UCHAR corresponds to a port status). 1-Normal; 2-Faulty; 3-Deactivated; 4-Low power consumption.
         "
     ::= { hwPstnPortStateStatisticEntry 4 } 

   hwPstnPTPLoopBackStateBitmapList OBJECT-TYPE
     SYNTAX      OCTET STRING
     MAX-ACCESS  read-only
     STATUS      current
     DESCRIPTION
         "
         Indicates the bit mapping table of the physical loopback status of all the PSTN ports of the specified board (the status table consists of variable-length character strings, and each UCHAR corresponds to a port status). 1-No loopback; 2-Remote loopback; 3-Local loopback.
         "
     ::= { hwPstnPortStateStatisticEntry 5 } 
     
   hwPstnPTPTestStateBitmapList OBJECT-TYPE
     SYNTAX      OCTET STRING
     MAX-ACCESS  read-only
     STATUS      current
     DESCRIPTION
         "
         Indicates the bit mapping table of the physical test status of all the PSTN ports of the specified board (the status table consists of variable-length character strings, and each UCHAR corresponds to a port status). 1-Not tested; 2-Tested.
         "
     ::= { hwPstnPortStateStatisticEntry 6 } 
     

   hwBraPortStateStatisticTable OBJECT-TYPE
     SYNTAX      SEQUENCE OF HwBraPortStateStatisticEntry
     MAX-ACCESS  not-accessible
     STATUS      current
     DESCRIPTION
       "
       Indicates the BRA port status mapping table.
       The indexes of this table are hwBraPTPFrameIndex and hwBraPTPSlotIndex.
       "
     ::= { hwIASVoicePortObjects 12 }
 
   hwBraPortStateStatisticEntry OBJECT-TYPE
     SYNTAX      HwBraPortStateStatisticEntry
     MAX-ACCESS  not-accessible
     STATUS      current
     DESCRIPTION
       "
       Indicates the BRA port status mapping table.
       The indexes of this entry are hwBraPTPFrameIndex and hwBraPTPSlotIndex.
       "
     INDEX    {  
           hwBraPTPFrameIndex,
           hwBraPTPSlotIndex 
              }
     ::= { hwBraPortStateStatisticTable 1 }
 
   HwBraPortStateStatisticEntry ::=
     SEQUENCE
     {
       hwBraPTPFrameIndex                       Integer32,
       hwBraPTPSlotIndex                        Integer32,
       hwBraBoardPortNumber                     Integer32,
       hwBraPTPSrvStateBitmapLists              OCTET STRING,
       hwBraPTPLoopBackStateBitmapLists         OCTET STRING,
       hwBraPTPTestStateBitmapList              OCTET STRING
     }
 
   hwBraPTPFrameIndex OBJECT-TYPE
     SYNTAX      Integer32
     MAX-ACCESS  not-accessible
     STATUS      current
     DESCRIPTION
         "
         Indicates the shelf index.
         "
     ::= { hwBraPortStateStatisticEntry 1 }
     
   hwBraPTPSlotIndex OBJECT-TYPE
     SYNTAX      Integer32
     MAX-ACCESS  not-accessible
     STATUS      current
     DESCRIPTION
         "
         Indicates the slot index.
         "
     ::= { hwBraPortStateStatisticEntry 2 }
  
   hwBraBoardPortNumber OBJECT-TYPE
     SYNTAX      Integer32
     MAX-ACCESS  read-only
     STATUS      current
     DESCRIPTION
         "
         Indicates the total number of ports on the specified BRA service board.
         "
     ::= { hwBraPortStateStatisticEntry 3 } 

   hwBraPTPSrvStateBitmapLists OBJECT-TYPE
     SYNTAX      OCTET STRING
     MAX-ACCESS  read-only
     STATUS      current
     DESCRIPTION
         "
         Indicates the bit mapping table of the service running status of all the BRA ports of the specified board (the status table consists of variable-length character strings, and each UCHAR corresponds to a port status). 1-Normal; 2-Faulty; 3-Deactivated.
         "
     ::= { hwBraPortStateStatisticEntry 4 } 

   hwBraPTPLoopBackStateBitmapLists OBJECT-TYPE
     SYNTAX      OCTET STRING
     MAX-ACCESS  read-only
     STATUS      current
     DESCRIPTION
         "
         Indicates the bit mapping table of the physical loopback status of all the BRA ports of the specified board (the status table consists of variable-length character strings, and each UCHAR corresponds to a port status). 1-No loopback; 2-Remote loopback; 3-Local loopback.
         "
     ::= { hwBraPortStateStatisticEntry 5 } 
     
   hwBraPTPTestStateBitmapList OBJECT-TYPE
     SYNTAX      OCTET STRING
     MAX-ACCESS  read-only
     STATUS      current
     DESCRIPTION
         "
         Indicates the bit mapping table of the physical test status of all the BRA ports of the specified board (the status table consists of variable-length character strings, and each UCHAR corresponds to a port status). 1-Not tested; 2-Tested.
         "
     ::= { hwBraPortStateStatisticEntry 6 }      



   hwE1PTPL1AlarmThresholdTable OBJECT-TYPE
     SYNTAX      SEQUENCE OF HwE1PTPL1AlarmThresholdEntry
     MAX-ACCESS  not-accessible
     STATUS      current
     DESCRIPTION
       "
       degrade alarm threshold config table of e1 port layer 1 
       The index of this table is hwE1PTPAlarmIndex.
       "
     ::= { hwIASVoicePortObjects 13 }
 
   hwE1PTPL1AlarmThresholdEntry OBJECT-TYPE
     SYNTAX      HwE1PTPL1AlarmThresholdEntry
     MAX-ACCESS  not-accessible
     STATUS      current
     DESCRIPTION
       "
       degrade alarm threshold config table of e1 port layer 1 
       The index of this entry is hwE1PTPAlarmIndex.
       "
     INDEX    {  
           hwE1PTPAlarmIndex 
              }
     ::= { hwE1PTPL1AlarmThresholdTable 1 }
 
   HwE1PTPL1AlarmThresholdEntry ::=
     SEQUENCE
     {
       hwE1PTPAlarmIndex                  Integer32,
       hwE1PTPDMAlarmThreshold            Integer32,
       hwE1PTPESAlarmThreshold            Integer32,
       hwE1PTPSESAlarmThreshold           Integer32,
       hwE1PTPDegradeEndService           INTEGER       
     }
 
   hwE1PTPAlarmIndex OBJECT-TYPE
     SYNTAX      Integer32
     MAX-ACCESS  not-accessible
     STATUS      current
     DESCRIPTION
         "
         Indicates the shelf/slot/port index.
         "
     ::= { hwE1PTPL1AlarmThresholdEntry 1 }
     
   hwE1PTPDMAlarmThreshold OBJECT-TYPE
     SYNTAX      Integer32(0..60)
     MAX-ACCESS  read-write
     STATUS      current
     DESCRIPTION
         "
         Indicates degrade minute alarm threshold, default:8.
         "
     ::= { hwE1PTPL1AlarmThresholdEntry 2 }
  
   hwE1PTPESAlarmThreshold OBJECT-TYPE
     SYNTAX      Integer32(0..3600)
     MAX-ACCESS  read-write
     STATUS      current
     DESCRIPTION
         "
         Indicates error second alarm threshold, default:432.
         "
     ::= { hwE1PTPL1AlarmThresholdEntry 3 } 

   hwE1PTPSESAlarmThreshold OBJECT-TYPE
     SYNTAX      Integer32(0..60)
     MAX-ACCESS  read-write
     STATUS      current
     DESCRIPTION
         "
         Indicates sequential severe error second alarm threshold, default:4.
         "
     ::= { hwE1PTPL1AlarmThresholdEntry 4 } 
     
   hwE1PTPDegradeEndService OBJECT-TYPE
     SYNTAX      INTEGER{enable(1),disable(2)}
     MAX-ACCESS  read-write
     STATUS      current
     DESCRIPTION
         "
         Whether port goes out of service when line quality gets worse. 
         Options:
         1.enable(1)  -indicates port goes out of service
         2.disable(2) -indicates port does not go out of service
         "
         DEFVAL      { enable }
     ::= { hwE1PTPL1AlarmThresholdEntry 5 }
     
   hwISDNPTPL2AlarmThresholdTable OBJECT-TYPE
     SYNTAX      SEQUENCE OF HwISDNPTPL2AlarmThresholdEntry
     MAX-ACCESS  not-accessible
     STATUS      current
     DESCRIPTION
       "
       Indicates layer 2 signal error alarm threshold config table of ISDN(BRA/PRA) port.
       The index of this table is hwIsdnPTPIndex.
       "
     ::= { hwIASVoicePortObjects 14 }
 
   hwISDNPTPL2AlarmThresholdEntry OBJECT-TYPE
     SYNTAX      HwISDNPTPL2AlarmThresholdEntry
     MAX-ACCESS  not-accessible
     STATUS      current
     DESCRIPTION
       "
       Indicates layer 2 signal error alarm threshold config table of ISDN(BRA/PRA) port.
       The index of this entry is hwIsdnPTPIndex.
       "
     INDEX    {  
           hwIsdnPTPIndex 
              }
     ::= { hwISDNPTPL2AlarmThresholdTable 1 }

   HwISDNPTPL2AlarmThresholdEntry ::=
     SEQUENCE
     {
       hwIsdnPTPIndex                          Integer32,
       hwIsdnL2DAUnexpectRespondThreshold      Integer32,
       hwIsdnL2DARebuiltLinkRequestThreshold   Integer32,
       hwIsdnL2DAN200OutTimeThreshold          Integer32,
       hwIsdnL2DAQ921AddrDomainErrThreshold    Integer32,
       hwIsdnL2DAMDLERRJToOThreshold           Integer32,
       hwIsdnL2DAFrameSNErrThreshold           Integer32,
       hwIsdnL2DABufferOverFlowThreshold       Integer32
     }
 
   hwIsdnPTPIndex OBJECT-TYPE
     SYNTAX      Integer32
     MAX-ACCESS  not-accessible
     STATUS      current
     DESCRIPTION
         "
         Indicates the shelf/slot/port index.
         "
     ::= { hwISDNPTPL2AlarmThresholdEntry 1 }
     
   hwIsdnL2DAUnexpectRespondThreshold OBJECT-TYPE
     SYNTAX      Integer32(0..20)
     MAX-ACCESS  read-write
     STATUS      current
     DESCRIPTION
         "
         Indicates threshold of unexpected response alarm threshold,default :0, 0 means does not report alarm.
         "
     ::= { hwISDNPTPL2AlarmThresholdEntry 2 }
  
   hwIsdnL2DARebuiltLinkRequestThreshold OBJECT-TYPE
     SYNTAX      Integer32(0..20)
     MAX-ACCESS  read-write
     STATUS      current
     DESCRIPTION
         "
         Indicates threshold of peer initiated re-establishments when in multiple frame established state, default:0, 0 means does not report alarm.
         "
     ::= { hwISDNPTPL2AlarmThresholdEntry 3 } 

   hwIsdnL2DAN200OutTimeThreshold OBJECT-TYPE
     SYNTAX      Integer32(0..20)
     MAX-ACCESS  read-write
     STATUS      current
     DESCRIPTION
         "
         Indicates threshold of unsuccessful re-transmissions n200 times, default:0, 0 means does not report alarm.
         "
     ::= { hwISDNPTPL2AlarmThresholdEntry 4 } 

   hwIsdnL2DAQ921AddrDomainErrThreshold OBJECT-TYPE
     SYNTAX      Integer32(0..20)
     MAX-ACCESS  read-write
     STATUS      current
     DESCRIPTION
         "
         Indicates threshold of Q.921 address field errors, default:0, 0 means does not report alarm.
         "
     ::= { hwISDNPTPL2AlarmThresholdEntry 5 } 
     
   hwIsdnL2DAMDLERRJToOThreshold OBJECT-TYPE
     SYNTAX      Integer32(0..20)
     MAX-ACCESS  read-write
     STATUS      current
     DESCRIPTION
         "
         Indicates threshold of Q.921 general protocol errors: MDL errors J to O : ETS.300.125, default:0, 0 means does not report alarm.
         "
     ::= { hwISDNPTPL2AlarmThresholdEntry 6 } 
     
   hwIsdnL2DAFrameSNErrThreshold OBJECT-TYPE
     SYNTAX      Integer32(0..20)
     MAX-ACCESS  read-write
     STATUS      current
     DESCRIPTION
         "
         Indicates threshold of frame check sequence errors : for Q.921, default:0, 0 means does not report alarm.
         "
     ::= { hwISDNPTPL2AlarmThresholdEntry 7 } 
     
   hwIsdnL2DABufferOverFlowThreshold OBJECT-TYPE
     SYNTAX      Integer32(0..20)
     MAX-ACCESS  read-write
     STATUS      current
     DESCRIPTION
         "
         Indicates threshold of buffer overflows, applies to Q.921, default:0, 0 means does not report alarm.
         "
     ::= { hwISDNPTPL2AlarmThresholdEntry 8 } 
     
    hwFxoPTPConfigTable OBJECT-TYPE
     SYNTAX      SEQUENCE OF HwFxoPTPConfigEntry
     MAX-ACCESS  not-accessible
     STATUS      current
     DESCRIPTION
       "
       Indicates A list of hwFxoPTPConfigTable objects.
       The index of this table is hwFxoPTPIndex"
     ::= { hwIASVoicePortObjects 15 }
 
   hwFxoPTPConfigEntry OBJECT-TYPE
     SYNTAX      HwFxoPTPConfigEntry
     MAX-ACCESS  not-accessible
     STATUS      current
     DESCRIPTION
       "       
       Indicates A list of hwFxoPTPConfigTable objects.
       The index of this entry is hwFxoPTPIndex"
     INDEX    {  
               hwFxoPTPIndex
              }
     ::= { hwFxoPTPConfigTable 1 }
 
   HwFxoPTPConfigEntry ::=
     SEQUENCE
     {
       hwFxoPTPIndex            Unsigned32,
       hwFxoPTPSendVoiceGain    Unsigned32,
       hwFxoPTPRecvVoiceGain    Unsigned32,
       hwFxoPTPDCImpedance      Unsigned32,
       hwFxoPTPACImpedance      Unsigned32,       
       hwFxoPTPRingMinOntime    Unsigned32,
       hwFxoPTPRingMaxOfftime   Unsigned32,       
       hwFxoPTPRingFrequence    Unsigned32,
       hwFxoPTPRingACAmplitude  Unsigned32,
       hwFxoPTPRingOffset       Unsigned32,
       hwFxoPTPFeedMaxVol       Unsigned32,
       hwFxoPTPFeedMinVol       Unsigned32,
       hwFxoPTPFeedMaxCurrent   Unsigned32,
       hwFxoPTPFeedMinCurrent   Unsigned32
    }
 
   hwFxoPTPIndex OBJECT-TYPE
        SYNTAX      Unsigned32
        MAX-ACCESS  not-accessible
        STATUS      current
        DESCRIPTION
        "
        Indicates the frame/slot/port index.
        "
        ::= { hwFxoPTPConfigEntry 1 }

   hwFxoPTPSendVoiceGain OBJECT-TYPE
        SYNTAX      Unsigned32(0..39)
        MAX-ACCESS  read-write
        STATUS      current
        DESCRIPTION
        "
        Indicates the Fxo board send voice gain.
        0: -7.5dB,     
        1: -7.0dB,      
        2: -6.5dB,       
        3: -6.0dB,     
        4: -5.5dB,       
        5: -5.0dB,      
        6: -4.5dB,       
        7: -4.0dB,     
        8: -3.5dB,      
        9: -3.0dB,       
        10: -2.5dB,         
        11: -2.0dB,     
        12: -1.5dB,     
        13: -1.0dB,     
        14: -0.5dB,    
        15:    0dB,     
        16: +0.5dB,     
        17: +1.0dB,     
        18: +1.5dB,      
        19: +2.0dB     
        20: +2.5dB,     
        21: +3.0dB,     
        22: +3.5dB,        
        23: +4.0dB,    
        24: +4.5dB,    
        25: +5.0dB,     
        26: +5.5dB,    
        27: +6.0dB,    
        28: +6.5dB,    
        29: +7.0dB,    
        30: +7.5dB,    
        31: +8.0dB,    
        32: +8.5dB     
        33: +9.0dB,    
        34: +9.5dB,    
        35: +10.0dB,   
        36: +10.5dB,   
        37: +11.0dB,   
        38: +11.5dB    
        39: +12.0dB
        "
        ::= { hwFxoPTPConfigEntry 2 }
    
   hwFxoPTPRecvVoiceGain OBJECT-TYPE
        SYNTAX      Unsigned32(0..26)
        MAX-ACCESS  read-write
        STATUS      current
        DESCRIPTION
        "
        Indicates the Fxo board receive voice gain.
        0: -16.0dB,         
        1: -15.5dB,         
        2: -15.0dB,          
        3: -14.5dB,         
        4: -14.0dB,        
        5: -13.5dB,         
        6: -13.0dB,          
        7: -12.5dB,         
        8: -12.0dB,         
        9: -11.5dB,          
        10: -11.0dB,            
        11: -10.5dB,
        12: -10.0dB,        
        13: -9.5dB,        
        14: -9.0dB,       
        15: -8.5dB        
        16: -8.0dB,        
        17: -7.5dB,        
        18: -7.0dB,        
        19: -6.5dB        
        20: -6.0dB,        
        21: -5.5dB,        
        22: -5.0dB,            
        23: -4.5dB,       
        24: -4.0dB,       
        25: -3.5dB,        
        26: -3.0dB       
        "
        ::= { hwFxoPTPConfigEntry 3 }
        
   hwFxoPTPDCImpedance OBJECT-TYPE
     SYNTAX      Unsigned32(0..1)
     MAX-ACCESS  read-write
     STATUS      current
     DESCRIPTION
         "
         Indicates the DC Impedance.
         0: 50
         1: 800
         (unit: ohm)
         "
     ::= { hwFxoPTPConfigEntry 4 }
     
   hwFxoPTPACImpedance OBJECT-TYPE
     SYNTAX      Unsigned32(0..15)
     MAX-ACCESS  read-write
     STATUS      current
     DESCRIPTION
         "
         Indicates the AC Impedance.
         0: 600
         1: 900 
         2: 270 + (750 || 150 nF) and 275 + (780 || 150 nF)
         3: 220 + (820 || 120 nF) and 220 + (820 || 115 nF)
         4: 370 + (620 || 310 nF)
         5: 320 + (1050 || 230 nF)
         6: 370 + (820 || 110 nF)
         7: 275 + (780 || 115 nF)
         8: 20 + (820 || 110 nF)
         9: 350 + (1000 || 210 nF)
         10: 200 + (680 || 100 nF)
         11: 600 + 2.16 uF
         12: 900 + 1 uF
         13: 900 + 2.16 uF
         14: 600 + 1 uF
         15: Global impedance
         (unit: ohm)
         "
     ::= { hwFxoPTPConfigEntry 5 }        
       
   hwFxoPTPRingMinOntime OBJECT-TYPE
     SYNTAX      Unsigned32(0..7)
     MAX-ACCESS  read-write
     STATUS      current
     DESCRIPTION
         "
         Indicates the min ontime for ringing detect.
         0: 100 ms  
         1: 150 ms  
         2: 200 ms
         3: 256 ms  
         4: 384 ms  
         5: 512 ms
         6: 640 ms  
         7: 1024 ms
         "
     ::= { hwFxoPTPConfigEntry 6 }
     
   hwFxoPTPRingMaxOfftime OBJECT-TYPE
     SYNTAX      Unsigned32(2..20)
     MAX-ACCESS  read-write
     STATUS      current
     DESCRIPTION
         "Indicates the threshold for ringing disappear.(unit: s)"
     ::= { hwFxoPTPConfigEntry 7 }
     
   hwFxoPTPRingFrequence OBJECT-TYPE
     SYNTAX      Unsigned32(0..3)
     MAX-ACCESS  read-write
     STATUS      current
     DESCRIPTION
         "
         Indicates the ring frequence.
         0: 16Hz,  
         1: 25Hz,  
         2: 50Hz,
         3: 20Hz         
         "
     ::= { hwFxoPTPConfigEntry 8 }
     
   hwFxoPTPRingACAmplitude OBJECT-TYPE
     SYNTAX      Unsigned32(0..2)
     MAX-ACCESS  read-write
     STATUS      current
     DESCRIPTION
         "
         Indicates the ring of the AC amplitude.
         0: 20Vrms, 
         1: 30Vrms,  
         2: 50Vrms         
         "
     ::= { hwFxoPTPConfigEntry 9 } 
     
     
   hwFxoPTPRingOffset OBJECT-TYPE
     SYNTAX      Unsigned32(0..100)
     MAX-ACCESS  read-write
     STATUS      current
     DESCRIPTION
         "
         Indicates the ring offset.
         "
     ::= { hwFxoPTPConfigEntry 10 }     
     
   hwFxoPTPFeedMaxVol OBJECT-TYPE
     SYNTAX      Unsigned32(0..5)
     MAX-ACCESS  read-write
     STATUS      current
     DESCRIPTION
         "
         Indicates the max of the PTP feed voltage.
         0: -30V,  
         1: -35V, 
         2: -40V
         3: -45V,  
         4: -50V  
         5: -55V 
         "
     ::= { hwFxoPTPConfigEntry 11 }
     
     
   hwFxoPTPFeedMinVol OBJECT-TYPE
     SYNTAX      Unsigned32(0..6)
     MAX-ACCESS  read-write
     STATUS      current
     DESCRIPTION
         "
         Indicates the min of the PTP feed voltage.
         0: -50V,  
         1: -55V, 
         2: -60V
         3: -65V,  
         4: -70V  
         5: -75V 
         6: -80V
         "
     ::= { hwFxoPTPConfigEntry 12 }
     
     
   hwFxoPTPFeedMaxCurrent OBJECT-TYPE
     SYNTAX      Unsigned32(0..9)
     MAX-ACCESS  read-write
     STATUS      current
     DESCRIPTION
         "
         Indicates the max of the PTP feed current.
         0: 25mA  
         1: 30mA  
         2: 35mA  
         3: 40mA
         4: 45mA  
         5: 50mA  
         6: 55mA  
         7: 60mA
         8: 65mA  
         9: 70mA                  
         "
     ::= { hwFxoPTPConfigEntry 13 }
     
     
   hwFxoPTPFeedMinCurrent OBJECT-TYPE
     SYNTAX      Unsigned32(0..4)
     MAX-ACCESS  read-write
     STATUS      current
     DESCRIPTION
         "
         Indicates the min of the PTP feed current.
         0: 16mA  
         1: 17mA  
         2: 18mA  
         3: 19mA  
         4: 20mA         
         "
     ::= { hwFxoPTPConfigEntry 14 }       
        
   hwFxoPTPOperateTable OBJECT-TYPE
     SYNTAX      SEQUENCE OF HwFxoPTPOperateEntry
     MAX-ACCESS  not-accessible
     STATUS      current
     DESCRIPTION
       "
       A list of HwFxoPTPOperateEntry objects.
       The index of this table is hwFxoPTPOperIndex.
       "
     ::= { hwIASVoicePortObjects 16 }
 
   hwFxoPTPOperateEntry OBJECT-TYPE
     SYNTAX      HwFxoPTPOperateEntry
     MAX-ACCESS  not-accessible
     STATUS      current
     DESCRIPTION
       "
       A list of HwFxoPTPOperateEntry objects.
       The index of this entry is hwFxoPTPOperIndex.
       "
     INDEX    {  
               hwFxoPTPOperIndex
              }
     ::= { hwFxoPTPOperateTable 1 }
 
   HwFxoPTPOperateEntry ::=
     SEQUENCE
     {
       hwFxoPTPOperIndex      Unsigned32,
       hwFxoPTPSrvState       INTEGER,
       hwFxoPTPLoopBackState  INTEGER,
       hwFxoPTPAdminOper      INTEGER,
       hwFxoPTPPowerState     INTEGER 
    }
 
   hwFxoPTPOperIndex OBJECT-TYPE
        SYNTAX      Unsigned32
        MAX-ACCESS  not-accessible
        STATUS      current
        DESCRIPTION
        "
        Indicates the frame/slot/port index.
        "
        ::= { hwFxoPTPOperateEntry 1 }

   hwFxoPTPSrvState OBJECT-TYPE
        SYNTAX      INTEGER{normal(1),fault(2)}
        MAX-ACCESS  read-only
        STATUS      current
        DESCRIPTION
        "
        Indicates the state of port.  
        Options:
        1.normal(1) -indicates the state of port is normal
        2.fault(2)  -indicates the state of port is fault
        "
        ::= { hwFxoPTPOperateEntry 2 }
        
   hwFxoPTPLoopBackState OBJECT-TYPE
         SYNTAX      INTEGER{noLoop(1),remoteLoop(2),localLoop(3)}
         MAX-ACCESS  read-only
         STATUS      current
         DESCRIPTION
         "
         FXO port loop state: 
         Options:
         1.noLoop(1)        -indicates the FXO port loop state is no loop
         2.remoteLoop(2)    -indicates the FXO port loop state is remote loop
         3.localLoop(3)     -indicates the FXO port loop state is local loop
         "
     ::= { hwFxoPTPOperateEntry 3 }    
     
   hwFxoPTPAdminOper OBJECT-TYPE
        SYNTAX      INTEGER{reset(1),localLoop(2),remoteLoop(3),cancelLoop(4),invalidvalue(-1)}
        MAX-ACCESS  read-write
        STATUS      current
        DESCRIPTION
        "
        Indicates the operate type.
        Options:
        1.reset(1)         -indicates the operate type is no reset
        2.localLoop(2)     -indicates the operate type is local loop
        3.remoteLoop(3)    -indicates the operate type is remote loop 
        4.cancelLoop(4)    -indicates the operate type is no loop
        5.invalidvalue(-1) -indicates an invalid value
        "
        ::= { hwFxoPTPOperateEntry 4 }

   hwFxoPTPPowerState OBJECT-TYPE
        SYNTAX      INTEGER{normal(1),abnormal(2)}
        MAX-ACCESS  read-only
        STATUS      current
        DESCRIPTION
        "
        Indicates the power state.
        Options:
        1.normal(1)       -indicates normal power feed
        2.abnormal(2)     -indicates no power feed
        "
        ::= { hwFxoPTPOperateEntry 5 }
        
   hwShdslPTPConfigTable OBJECT-TYPE
     SYNTAX      SEQUENCE OF HwShdslPTPConfigEntry
     MAX-ACCESS  not-accessible
     STATUS      current
     DESCRIPTION
       "
       Indicates the configuration table (attribute configuration and query) of the Shdsl PTP layer.
       The index of this table is hwShdslPTPIndex.
       "
     ::= { hwIASVoicePortObjects 17 }
   
   hwShdslPTPConfigEntry OBJECT-TYPE
     SYNTAX      HwShdslPTPConfigEntry
     MAX-ACCESS  not-accessible
     STATUS      current
     DESCRIPTION
       "
       Indicates the configuration table (attribute configuration and query) of the Shdsl PTP layer. 
       The index of this entry is hwShdslPTPIndex.
       "
     INDEX    {  
               hwShdslPTPIndex
              }
     ::= { hwShdslPTPConfigTable 1 }
 
   HwShdslPTPConfigEntry ::=
     SEQUENCE
     {
       hwShdslPTPIndex                  Integer32,
       hwShdslPTPFrameVerifyMode        INTEGER,
       hwShdslPTPSignalType             INTEGER,
       hwShdslPTPConfigState            INTEGER,
       hwShdslPTPErrAlarmSet            BITS,
       hwShdslPTPL2Monitor              INTEGER
     }
 
   hwShdslPTPIndex OBJECT-TYPE
     SYNTAX      Integer32
     MAX-ACCESS  not-accessible
     STATUS      current
     DESCRIPTION
         "
         Indicates the shelf/slot/port index.
         "
     ::= { hwShdslPTPConfigEntry 1 }
 
   hwShdslPTPFrameVerifyMode OBJECT-TYPE
     SYNTAX      INTEGER{enable(1),disable(2)}
     MAX-ACCESS  read-write
     STATUS      current
     DESCRIPTION
         "
         Indicates the CRC4 frame check. 
         Options:
         1.enable(1)    -indicates the CRC4 frame check is enable
         2.disable(2)   -indicates the CRC4 frame check is disable
         "
         DEFVAL      { disable }
     ::= { hwShdslPTPConfigEntry 2 }
 
   hwShdslPTPSignalType OBJECT-TYPE
     SYNTAX      INTEGER{ccs(1),cas(2),unframe(3)}
     MAX-ACCESS  read-write
     STATUS      current
     DESCRIPTION
         "
         Indicates the signaling type.
         Options:
         1.ccs(1)     -indicates the signaling type is ccs
         2.cas(2)     -indicates the signaling type is cas
         3.unframe(3) -indicates the signaling type is unframe
         "
         DEFVAL      { ccs }
     ::= { hwShdslPTPConfigEntry 3 }
     
   hwShdslPTPConfigState OBJECT-TYPE
     SYNTAX      INTEGER{notconfigUserType(1),configUserType(2)}
     MAX-ACCESS  read-only
     STATUS      current
     DESCRIPTION
         "
         Indicates the configuration status of the subscriber type.
         Options:
         1.notconfigUserType(1) -not configured
         2.configUserType(2)    -configured
         "
     ::= { hwShdslPTPConfigEntry 4}
     
   hwShdslPTPErrAlarmSet OBJECT-TYPE
     SYNTAX      BITS{bit0(0),bit1(1),bit2(2),bit3(3),bit4(4),bit5(5)}
     MAX-ACCESS  read-write
     STATUS      current
     DESCRIPTION
         "
         Indicates set Shdsl error alarm switch,from left to right,each bit respresent a switch,default:111000.
         Options:
         1.bit0(0)  -indicates report pcm line fault alarm
         2.bit1(1)  -indicates when error rate reached ULF(Unconditional Line Fai2008-5-30 14:24lure)threshold,report pcm line fault alarm             
         3.bit2(2)  -indicates when error rate reached OLF(Optional Line Failure) threshold,report pcm line fault alarm
         4.bit3(3)  -indicates when error rate reached LDT(Line Disturbance Transient Event) threshold,report Shdsl digital line transient event alarm
         5.bit4(4)  -indicates when Shdsl frame slip frequency exceeded in observation interval reached degraded threshold,report event alarm
         6.bit5(5)  -indicates when any line temporary event occurs,report event alarm
         "
     ::= { hwShdslPTPConfigEntry 5}
  
   hwShdslPTPL2Monitor OBJECT-TYPE
     SYNTAX      INTEGER{disable(1),enable(2)}
     MAX-ACCESS  read-write
     STATUS      current
     DESCRIPTION
         "
         enable layer 2 error statistic of shdsl port or not,default:enable(2).
         Options:
         1.disable(1) -disable the layer 2 error statistic of shdsl port
         2.enable(2)  -enable the layer 2 error statistic of shdsl port
         "
     ::= { hwShdslPTPConfigEntry 6}
     
   hwShdslPTPOperTable OBJECT-TYPE
     SYNTAX      SEQUENCE OF HwShdslPTPOperEntry
     MAX-ACCESS  not-accessible
     STATUS      current
     DESCRIPTION
       "
       Indicates the operation table (management, maintenance, and status query) of the Shdsl PTP layer.
       The index of this table is hwShdslPTPOperIndex.
       "
     ::= { hwIASVoicePortObjects 18 }
 
   hwShdslPTPOperEntry OBJECT-TYPE
     SYNTAX      HwShdslPTPOperEntry
     MAX-ACCESS  not-accessible
     STATUS      current
     DESCRIPTION
       "
       Indicates the operation table (management, maintenance, and status query) of the Shdsl PTP layer.
       The index of this entry is hwShdslPTPOperIndex.
       "
     INDEX    {  
               hwShdslPTPOperIndex
              }
     ::= { hwShdslPTPOperTable 1 }
 
   HwShdslPTPOperEntry ::=
     SEQUENCE
     {
       hwShdslPTPOperIndex                Integer32,
       hwShdslPTPSrvState                 INTEGER,
       hwShdslPTPWarningState             Integer32,
       hwShdslPTPLicenseState             INTEGER
     }
 
   hwShdslPTPOperIndex OBJECT-TYPE
     SYNTAX      Integer32
     MAX-ACCESS  not-accessible
     STATUS      current
     DESCRIPTION
         "
         Indicates the shelf/slot/port index.
         "
     ::= { hwShdslPTPOperEntry 1 }
 
   hwShdslPTPSrvState OBJECT-TYPE
     SYNTAX      INTEGER{normal(1),fault(2),lineAbnormal(3)}
     MAX-ACCESS  read-only
     STATUS      current
     DESCRIPTION
         "
         Indicates the service running status of the Shdsl port.
         Options:
         1.normal(1)        -indicates the service running status of Shdsl port is normal
         2.fault(2)         -indicates the service running status of Shdsl port is fault         
         3.lineAbnormal(3)  -indicates the service running status of Shdsl port is line abnormal
         "
     ::= { hwShdslPTPOperEntry 2 }
 
   hwShdslPTPWarningState OBJECT-TYPE
     SYNTAX      Integer32
     MAX-ACCESS  read-only
     STATUS      current
     DESCRIPTION
         "
         Indicates the alarm status of the Shdsl line.
         Bit0: LOS (0: no LOS alarm; 1: LOS alarm occurs)
         Bit1: AIS (0: no AIS alarm; 1: AIS alarm occurs)
         Bit2: LFA (0: no LFA alarm; 1: LFA alarm occurs)
         Bit3: LMFA (0: no LMFA alarm; 1: LMFA alarm occurs)
         Bit4: RRA (0: no RRA alarm; 1: RRA alarm occurs)
         Bit5: CRCER (0: no CRCER alarm; 1: CRCER alarm occurs)
         Bit6:SCOL alarm
         Bit7:ULF alarm
         Bit8:OLF alarm
         Bit9:LDT alarm
         Bit10:error second alarm,in direction ET/LT to NT1
         Bit11:error second alarm,in direction NT1 to ET/LT 
         Bit12:sequential severe error second alarm,in direction ET/LT to NT1
         Bit13:sequential severe error second alarm,in direction NT1 to ET/LT
         Bit14:degrade minute alarm,in direction ET/LT to NT1
         Bit15:degrade minute alarm,in direction NT1 to ET/LT
         "
     ::= { hwShdslPTPOperEntry 3 }
    
    hwShdslPTPLicenseState OBJECT-TYPE
     SYNTAX      INTEGER{noconfigure(1),nolicense(2),licensed(3)}
     MAX-ACCESS  read-only
     STATUS      current
     DESCRIPTION
         "
         Indicates the service license status of the Shdsl port.
         Options:
         1.noconfigure(1) -indicates the service license status of the Shdsl port is no configuration       
         2.nolicense(2)   -indicates the service license status of the Shdsl port is no license
         3.licensed(3)    -indicates the service license status of the Shdsl port is licensed
         "
     ::= { hwShdslPTPOperEntry 4 }   

    hwPotsBoardToneDefineTable OBJECT-TYPE
        SYNTAX SEQUENCE OF HwPotsBoardToneDefineEntry
        MAX-ACCESS not-accessible
        STATUS current
        DESCRIPTION
                " 
                The index of this table is hwPotsBoardToneType.
                PstnBoard pots signal tone config table. 
                "  
        ::= { hwIASVoicePortObjects 19 }
        

        hwPotsBoardToneDefineEntry OBJECT-TYPE
        SYNTAX      HwPotsBoardToneDefineEntry
        MAX-ACCESS  not-accessible
        STATUS      current
        DESCRIPTION
            " 
            The index of this entry is hwPotsBoardToneType.
            PstnBoard pots signal tone config table.           
            "
        INDEX { hwPotsBoardToneType }
        ::= { hwPotsBoardToneDefineTable 1 }
        
        HwPotsBoardToneDefineEntry ::=
        SEQUENCE{
                hwPotsBoardToneType            
                        INTEGER,
                hwPotsBoardToneFreq1            
                        Integer32,
                hwPotsBoardToneFreq2            
                        Integer32,
                hwPotsBoardToneOnTime            
                        Integer32,
                hwPotsBoardToneOffTime            
                        Integer32,
                hwPotsBoardToneLevel            
                        Integer32                                                                                                                                                
                }
            
        hwPotsBoardToneType OBJECT-TYPE
        SYNTAX    INTEGER{busytone(1)}        
        MAX-ACCESS  read-write
        STATUS      current
        DESCRIPTION
            "
            Indicates the tone type of signal tone. 
            Options:
            1. busytone(1)        -Indicate the tone type
            "
        ::= { hwPotsBoardToneDefineEntry 1 }                

        hwPotsBoardToneFreq1 OBJECT-TYPE
        SYNTAX    Integer32 (100..3400)        
        MAX-ACCESS  read-write
        STATUS      current
        DESCRIPTION
            "
            Indicates the first frequency of signal tone.(Unit:Hz)
            "
        ::= { hwPotsBoardToneDefineEntry 2 }        
        
        hwPotsBoardToneFreq2 OBJECT-TYPE
        SYNTAX    Integer32 (0..3400)        
        MAX-ACCESS  read-write
        STATUS      current
        DESCRIPTION
            "
            Indicates the second frequency of signal tone.(Unit:Hz)
            "
        ::= { hwPotsBoardToneDefineEntry 3 }
        
        hwPotsBoardToneOnTime OBJECT-TYPE
        SYNTAX    Integer32 (10..60000)        
        MAX-ACCESS  read-write
        STATUS      current
        DESCRIPTION
            "
            Indicates the on-time of signal tone. (Unit:ms)
            "
        ::= { hwPotsBoardToneDefineEntry 4 }                

        hwPotsBoardToneOffTime OBJECT-TYPE
        SYNTAX    Integer32 (0..60000)        
        MAX-ACCESS  read-write
        STATUS      current
        DESCRIPTION
            "
            Indicates the off-time of signal tone. (Unit:ms)
            "
        ::= { hwPotsBoardToneDefineEntry 5 }
        
        hwPotsBoardToneLevel OBJECT-TYPE
        SYNTAX    Integer32 (0..20)        
        MAX-ACCESS  read-write
        STATUS      current
        DESCRIPTION
            "
            Indicates the level of signal tone. (Unit:-1dBm0)
            "
        ::= { hwPotsBoardToneDefineEntry 6 }                

   hwShdslPTPL1AlarmThresholdTable OBJECT-TYPE
     SYNTAX      SEQUENCE OF HwShdslPTPL1AlarmThresholdEntry
     MAX-ACCESS  not-accessible
     STATUS      current
     DESCRIPTION
       "
       degrade alarm threshold config table of e1 port layer 1 
       The index of this table is hwE1PTPAlarmIndex.
       "
     ::= { hwIASVoicePortObjects 20 }
 
   hwShdslPTPL1AlarmThresholdEntry OBJECT-TYPE
     SYNTAX      HwShdslPTPL1AlarmThresholdEntry
     MAX-ACCESS  not-accessible
     STATUS      current
     DESCRIPTION
       "
       degrade alarm threshold config table of e1 port layer 1 
       The index of this entry is hwE1PTPAlarmIndex.
       "
     INDEX    {  
           hwShdslPTPAlarmIndex 
              }
     ::= { hwShdslPTPL1AlarmThresholdTable 1 }
 
   HwShdslPTPL1AlarmThresholdEntry ::=
     SEQUENCE
     {
       hwShdslPTPAlarmIndex                  Integer32,
       hwShdslPTPDMAlarmThreshold            Integer32,
       hwShdslPTPESAlarmThreshold            Integer32,
       hwShdslPTPSESAlarmThreshold           Integer32,
       hwShdslPTPDegradeEndService           INTEGER       
     }
 
   hwShdslPTPAlarmIndex OBJECT-TYPE
     SYNTAX      Integer32
     MAX-ACCESS  not-accessible
     STATUS      current
     DESCRIPTION
         "
         Indicates the shelf/slot/port index.
         "
     ::= { hwShdslPTPL1AlarmThresholdEntry 1 }
     
   hwShdslPTPDMAlarmThreshold OBJECT-TYPE
     SYNTAX      Integer32(0..60)
     MAX-ACCESS  read-write
     STATUS      current
     DESCRIPTION
         "
         Indicates degrade minute alarm threshold, default:8.
         "
     ::= { hwShdslPTPL1AlarmThresholdEntry 2 }
  
   hwShdslPTPESAlarmThreshold OBJECT-TYPE
     SYNTAX      Integer32(0..3600)
     MAX-ACCESS  read-write
     STATUS      current
     DESCRIPTION
         "
         Indicates error second alarm threshold, default:432.
         "
     ::= { hwShdslPTPL1AlarmThresholdEntry 3 } 

   hwShdslPTPSESAlarmThreshold OBJECT-TYPE
     SYNTAX      Integer32(0..60)
     MAX-ACCESS  read-write
     STATUS      current
     DESCRIPTION
         "
         Indicates sequential severe error second alarm threshold, default:4.
         "
     ::= { hwShdslPTPL1AlarmThresholdEntry 4 } 
     
   hwShdslPTPDegradeEndService OBJECT-TYPE
     SYNTAX      INTEGER{enable(1),disable(2)}
     MAX-ACCESS  read-write
     STATUS      current
     DESCRIPTION
         "
         Whether port goes out of service when line quality gets worse. 
         Options:
         1.enable(1)  -indicates port goes out of service
         2.disable(2) -indicates port does not go out of service
         "
         DEFVAL      { enable }
     ::= { hwShdslPTPL1AlarmThresholdEntry 5 }
                
  --  /* Start hwIASVoicePortTrapsVbOids */

     hwVoicePTPFrame OBJECT-TYPE
         SYNTAX     Integer32(0..255)
         MAX-ACCESS accessible-for-notify
         STATUS current
         DESCRIPTION
             "
             Indicate the frame ID.
             "
          ::= { hwIASVoicePortTrapsVbOids 1 }
      
     hwVoicePTPSlot OBJECT-TYPE
         SYNTAX     Integer32(0..255)
         MAX-ACCESS accessible-for-notify
         STATUS current
         DESCRIPTION
             "
             Indicate the slot ID.
             "
          ::= { hwIASVoicePortTrapsVbOids 2 }
      
     hwVoicePTPPort OBJECT-TYPE
         SYNTAX     Integer32(0..255)
         MAX-ACCESS accessible-for-notify
         STATUS current
         DESCRIPTION
             "
             Indicate the port ID.
             "
          ::= { hwIASVoicePortTrapsVbOids 3 }
      
     hwVoicePortGtcStatus OBJECT-TYPE
         SYNTAX     INTEGER{ reserve(0), timeoutFinish(1), startserviceFinish(2), reserve2(3) }
         MAX-ACCESS accessible-for-notify
         STATUS current
         DESCRIPTION
             "
             The GTC test status. 
             Options:
             1. reserve(0)              -reserve       
             2. timeoutFinish(1)        -indicates the GTC test finish whit result of time out
             3. startserviceFinish(2)   -indicates the GTC test finish whit result of start service
             4. reserve2(3)             -reserve2
             "
          ::= { hwIASVoicePortTrapsVbOids 4 }
      
      
      
     hwVoicePortSequence OBJECT-TYPE
         SYNTAX     Integer32
         MAX-ACCESS accessible-for-notify
         STATUS current
         DESCRIPTION
             "
             The trap's sequence number.
             "
          ::= { hwIASVoicePortTrapsVbOids 5 }
      
      
     hwVoicePortOperateType OBJECT-TYPE
         SYNTAX     Integer32
         MAX-ACCESS accessible-for-notify
         STATUS current
         DESCRIPTION
             "
             The operate type of data change.
             "
          ::= { hwIASVoicePortTrapsVbOids 6 }
      
     hwVoicePortNum OBJECT-TYPE
         SYNTAX     Integer32
         MAX-ACCESS accessible-for-notify
         STATUS current
         DESCRIPTION
             "
             The port number of data change.
             "
          ::= { hwIASVoicePortTrapsVbOids 7 }     

     hwPortMask OBJECT-TYPE
         SYNTAX     Integer32
         MAX-ACCESS accessible-for-notify
         STATUS current
         DESCRIPTION
             "
             The mask of the changed port.
             "
          ::= { hwIASVoicePortTrapsVbOids 8 }          

     hwAttributeMask OBJECT-TYPE
         SYNTAX     Integer32
         MAX-ACCESS accessible-for-notify
         STATUS current
         DESCRIPTION
             "
             The mask of the changed Attribute.
             "
          ::= { hwIASVoicePortTrapsVbOids 9 }         

     hwChangepara1 OBJECT-TYPE
         SYNTAX     Integer32
         MAX-ACCESS accessible-for-notify
         STATUS current
         DESCRIPTION
             "
             The change value.
             "
          ::= { hwIASVoicePortTrapsVbOids 10 }   

     hwChangepara2 OBJECT-TYPE
         SYNTAX     Integer32
         MAX-ACCESS accessible-for-notify
         STATUS current
         DESCRIPTION
             "
             The change value.
             "
          ::= { hwIASVoicePortTrapsVbOids 11 }                   

     hwChangepara3 OBJECT-TYPE
         SYNTAX     Integer32
         MAX-ACCESS accessible-for-notify
         STATUS current
         DESCRIPTION
             "
             The change value.
             "
          ::= { hwIASVoicePortTrapsVbOids 12 } 

     hwChangepara4 OBJECT-TYPE
         SYNTAX     Integer32
         MAX-ACCESS accessible-for-notify
         STATUS current
         DESCRIPTION
             "
             The change value.
             "
          ::= { hwIASVoicePortTrapsVbOids 13 }
   
     hwChangepara5 OBJECT-TYPE
         SYNTAX     Integer32
         MAX-ACCESS accessible-for-notify
         STATUS current
         DESCRIPTION
             "
             The change value.
             "
          ::= { hwIASVoicePortTrapsVbOids 14 }
          
     hwChangepara6 OBJECT-TYPE
         SYNTAX     Integer32
         MAX-ACCESS accessible-for-notify
         STATUS current
         DESCRIPTION
             "
             The change value.
             "
          ::= { hwIASVoicePortTrapsVbOids 15 }
    
     hwChangepara7 OBJECT-TYPE
         SYNTAX     Integer32
         MAX-ACCESS accessible-for-notify
         STATUS current
         DESCRIPTION
             "
             The change value.
             "
          ::= { hwIASVoicePortTrapsVbOids 16 }
          
     hwChangepara8 OBJECT-TYPE
         SYNTAX     Integer32
         MAX-ACCESS accessible-for-notify
         STATUS current
         DESCRIPTION
             "
             The change value.
             "
          ::= { hwIASVoicePortTrapsVbOids 17 }
          
     hwChangepara9 OBJECT-TYPE
         SYNTAX     Integer32
         MAX-ACCESS accessible-for-notify
         STATUS current
         DESCRIPTION
             "
             The change value.
             "
          ::= { hwIASVoicePortTrapsVbOids 18 }
  
     hwChangepara10 OBJECT-TYPE
         SYNTAX     Integer32
         MAX-ACCESS accessible-for-notify
         STATUS current
         DESCRIPTION
             "
             The change value.
             "
          ::= { hwIASVoicePortTrapsVbOids 19 }
          
     hwChangepara11 OBJECT-TYPE
         SYNTAX     Integer32
         MAX-ACCESS accessible-for-notify
         STATUS current
         DESCRIPTION
             "
             The change value.
             "
          ::= { hwIASVoicePortTrapsVbOids 20 }
          
     hwChangepara12 OBJECT-TYPE
         SYNTAX     Integer32
         MAX-ACCESS accessible-for-notify
         STATUS current
         DESCRIPTION
             "
             The change value.
             "
          ::= { hwIASVoicePortTrapsVbOids 21 }
          
     hwChangepara13 OBJECT-TYPE
         SYNTAX     Integer32
         MAX-ACCESS accessible-for-notify
         STATUS current
         DESCRIPTION
             "
             The change value.
             "
          ::= { hwIASVoicePortTrapsVbOids 22 }
          
     hwChangepara14 OBJECT-TYPE
         SYNTAX     Integer32
         MAX-ACCESS accessible-for-notify
         STATUS current
         DESCRIPTION
             "
             The change value.
             "
          ::= { hwIASVoicePortTrapsVbOids 23 }
          
     hwChangepara15 OBJECT-TYPE
         SYNTAX     Integer32
         MAX-ACCESS accessible-for-notify
         STATUS current
         DESCRIPTION
             "
             The change value.
             "
          ::= { hwIASVoicePortTrapsVbOids 24 }
          
     hwChangepara16 OBJECT-TYPE
         SYNTAX     Integer32
         MAX-ACCESS accessible-for-notify
         STATUS current
         DESCRIPTION
             "
             The change value.
             "
          ::= { hwIASVoicePortTrapsVbOids 25 }
                                                                                                                                     
 --  /*  End  hwIASVoicePortTrapsVbOids */  
 
 --  /* Start hwIASVoicePortComTraps */

    hwIASVoicePortGtcFinishTraps OBJECT IDENTIFIER ::= { hwIASVoicePortComTraps 0 }
 
    hwIASVoicePortGtcFinishTrap NOTIFICATION-TYPE
        OBJECTS  { hwVoicePTPFrame, hwVoicePTPSlot, hwVoicePTPPort, hwVoicePortGtcStatus }
        STATUS      current
        DESCRIPTION    
            "
            The trap indicates that the GTC test is finished cause of time-out or user start service.
            "
        ::= { hwIASVoicePortGtcFinishTraps 1 }
  
 --  /*  End  hwIASVoicePortComTraps */ 
 
 
 
 --  /* Start hwIASVoicePortPstnTraps */

    hwIASVoicePortPstnAttributeTraps OBJECT IDENTIFIER ::= { hwIASVoicePortPstnTraps 0 }
 
    hwIASVoicePortPstnTrap NOTIFICATION-TYPE 
        OBJECTS  { hwConfigChangeIP, hwVoicePortSequence, hwVoicePortOperateType, hwVoicePortNum, 
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort,                
                    hwVoicePTPFrame, hwVoicePTPSlot, hwVoicePTPPort             
                }
        STATUS      current
        DESCRIPTION    
            "
            The Trap indicates that the PSTN port attribute configuratinon was changed.
            "
        ::= { hwIASVoicePortPstnAttributeTraps 1 }
  
 --  /*  End  hwIASVoicePortPstnTraps */ 
 
 --  /* Start hwIASVoicePortBraTraps */

    hwIASVoicePortBraAttributeTraps OBJECT IDENTIFIER ::= { hwIASVoicePortBraTraps 0 }
 
    hwIASVoicePortBraTrap NOTIFICATION-TYPE
        OBJECTS  { hwConfigChangeIP, hwVoicePortSequence, hwVoicePortOperateType, hwVoicePortNum, 
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort,                
                     hwVoicePTPFrame, hwVoicePTPSlot, hwVoicePTPPort             
                 }
         STATUS      current
         DESCRIPTION    
             "
             The Trap indicates that the BRA port attribute configuratinon was changed.
        "
    ::= { hwIASVoicePortBraAttributeTraps 1 }
  
 --  /*  End  hwIASVoicePortBraTraps */ 
 
 --  /* Start hwIASVoicePortE1Traps */

    hwIASVoicePortE1AttributeTraps OBJECT IDENTIFIER ::= { hwIASVoicePortE1Traps 0 }
 
    hwIASVoicePortE1Trap NOTIFICATION-TYPE
        OBJECTS  { hwConfigChangeIP, hwVoicePortSequence, hwVoicePortOperateType, hwVoicePortNum, hwVoicePTPFrame, hwVoicePTPSlot, hwVoicePTPPort }
        STATUS      current
        DESCRIPTION    
            "
            The Trap indicates that the E1 port attribute configuratinon was changed.
            "
        ::= { hwIASVoicePortE1AttributeTraps 1 }
  
 --  /*  End  hwIASVoicePortE1Traps */ 
 
 --  /* Start hwIASVoicePortE1AttributeCfgChgTrap */
  
     hwIASVoicePortE1AttributeCfgChgTrap NOTIFICATION-TYPE
        OBJECTS  { hwConfigChangeIP, hwVoicePortOperateType, hwVoicePTPFrame, hwVoicePTPSlot, hwPortMask, hwAttributeMask,
                   hwChangepara1, hwChangepara2, hwChangepara3, hwChangepara4, hwChangepara5, hwChangepara6, hwChangepara7, hwChangepara8,
                   hwChangepara9, hwChangepara10, hwChangepara11, hwChangepara12, hwChangepara13, hwChangepara14, hwChangepara15, hwChangepara16
                 }
        STATUS      current
        DESCRIPTION
            "
            The Trap indicates that the E1 port attribute configuratinon was changed.
            "
        ::= { hwIASVoicePortE1AttributeTraps 2 }

--  /*  End  hwIASVoicePortE1AttributeCfgChgTrap */
 
--  /* Start hwIASVoicePortE1AlarmCfgChgTrap */
   
     hwIASVoicePortE1AlarmCfgChgTrap NOTIFICATION-TYPE
        OBJECTS  { hwConfigChangeIP, hwVoicePortOperateType, hwVoicePTPFrame, hwVoicePTPSlot, hwPortMask, hwAttributeMask,
                   hwChangepara1, hwChangepara2, hwChangepara3, hwChangepara4, hwChangepara5, hwChangepara6, hwChangepara7, hwChangepara8,
                   hwChangepara9, hwChangepara10, hwChangepara11, hwChangepara12, hwChangepara13, hwChangepara14, hwChangepara15, hwChangepara16
                 }
        STATUS      current
        DESCRIPTION
            "
            The Trap indicates that the E1 and Shdsl port alarm configuratinon was changed.
            "
        ::= { hwIASVoicePortE1AttributeTraps 3 }

 --  /*  End  hwIASVoicePortE1AlarmCfgChgTrap */
 
 --  /* Start hwIASVoicePortShdslAttributeChgTrap */
   
     hwIASVoicePortShdslAttributeChgTrap NOTIFICATION-TYPE
        OBJECTS  { hwConfigChangeIP, hwVoicePortOperateType, hwVoicePTPFrame, hwVoicePTPSlot, hwPortMask, hwAttributeMask,
                   hwChangepara1, hwChangepara2, hwChangepara3, hwChangepara4, hwChangepara5, hwChangepara6, hwChangepara7, hwChangepara8,
                   hwChangepara9, hwChangepara10, hwChangepara11, hwChangepara12, hwChangepara13, hwChangepara14, hwChangepara15, hwChangepara16
                 }
        STATUS      current
        DESCRIPTION
            "
            The Trap indicates that the Shdsl port attribute configuratinon was changed.
            "
        ::= { hwIASVoicePortE1AttributeTraps 4 }

 --  /*  End  hwIASVoicePortShdslAttributeChgTrap */
 
 --  /* Start hwIASVoicePortPstnAlarmTraps */

    hwIASVoicePortPstnStateAlarmTraps OBJECT IDENTIFIER ::= { hwIASVoicePortPstnAlarmTraps 0 }
 
    hwIASVoicePortPstnLineFaultTrap NOTIFICATION-TYPE
        OBJECTS  { hwVoicePTPFrame, hwVoicePTPSlot, hwVoicePTPPort }
        STATUS      current
        DESCRIPTION    
            "
            The trap indicates that user line fault.
            "
        ::= { hwIASVoicePortPstnStateAlarmTraps 1 }
    
    hwIASVoicePortPstnLinenormalTrap NOTIFICATION-TYPE
        OBJECTS  { hwVoicePTPFrame, hwVoicePTPSlot, hwVoicePTPPort }
        STATUS      current
        DESCRIPTION    
            "
            The trap indicates that user line normal.
            "
        ::= { hwIASVoicePortPstnStateAlarmTraps 2 }
        
    hwVoicePstnBoardSlicLockedTrap NOTIFICATION-TYPE
        OBJECTS  { hwVoicePTPFrame, hwVoicePTPSlot}
        STATUS      current
        DESCRIPTION 
            "
            The trap indicates that the slic of the board is locked.
            "
        ::= { hwIASVoicePortPstnStateAlarmTraps 3 }
        
    hwVoicePstnBoardSlicUnlockedTrap NOTIFICATION-TYPE
        OBJECTS  { hwVoicePTPFrame, hwVoicePTPSlot}
        STATUS      current
        DESCRIPTION    
            "
            The trap indicates that the slic of the board is unlocked.
            "
        ::= { hwIASVoicePortPstnStateAlarmTraps 4 }     
        
    hwVoicePstnPortPowerAlarmTrap NOTIFICATION-TYPE
        OBJECTS  { hwVoicePTPFrame, hwVoicePTPSlot, hwVoicePTPPort }
        STATUS      current
        DESCRIPTION    
            "
            The trap indicates that A/B line has touch power line over 80V .
            "
        ::= { hwIASVoicePortPstnStateAlarmTraps 5 }   
        
    hwVoicePstnPortPowerAlarmRestoreTrap NOTIFICATION-TYPE
        OBJECTS  { hwVoicePTPFrame, hwVoicePTPSlot, hwVoicePTPPort }
        STATUS      current
        DESCRIPTION    
            "
            The trap indicates that A/B line power normal.
            "
        ::= { hwIASVoicePortPstnStateAlarmTraps 6 }
   
 --  /*  End  hwIASVoicePortPstnAlarmTraps */  
 
 --  /* Start hwIASVoicePortBraAlarmTraps */

    hwIASVoicePortBraStateAlarmTraps OBJECT IDENTIFIER ::= { hwIASVoicePortBraAlarmTraps 0 }
 
    hwIASVoicePortBraUniFaultTrap NOTIFICATION-TYPE
        OBJECTS  { hwVoicePTPFrame, hwVoicePTPSlot, hwVoicePTPPort }
        STATUS      current
        DESCRIPTION    
            "
            The trap indicates that the physical line of the BRA port fails.
            "
        ::= { hwIASVoicePortBraStateAlarmTraps 1 }
    
    hwIASVoicePortBraUniResumeTrap NOTIFICATION-TYPE
        OBJECTS  { hwVoicePTPFrame, hwVoicePTPSlot, hwVoicePTPPort }
        STATUS      current
        DESCRIPTION    
            "
            The trap indicates that BRA port Line Fault Alarm Clear.
            "
        ::= { hwIASVoicePortBraStateAlarmTraps 2 }
    
    hwIASVoicePortBraDegradeTrap NOTIFICATION-TYPE
        OBJECTS  { hwVoicePTPFrame, hwVoicePTPSlot, hwVoicePTPPort }
        STATUS      current
        DESCRIPTION    
            "
            The trap indicates that the number of CRC errors on the BRA port reaches the degraded threshold.
            "
        ::= { hwIASVoicePortBraStateAlarmTraps 3 }
    
    hwIASVoicePortBraDegradeResumeTrap NOTIFICATION-TYPE
        OBJECTS  { hwVoicePTPFrame, hwVoicePTPSlot, hwVoicePTPPort }
        STATUS      current
        DESCRIPTION    
            "
            The trap indicates that BRA Port CRC reached degraded threshold Clear.
            "
        ::= { hwIASVoicePortBraStateAlarmTraps 4 }
    
    hwIASVoicePortBraCrcAlarmTrap NOTIFICATION-TYPE
        OBJECTS  { hwVoicePTPFrame, hwVoicePTPSlot, hwVoicePTPPort }
        STATUS      current
        DESCRIPTION    
            "
            The trap indicates that the CRC errors on the BRA port reach the alarm threshold.
            "
        ::= { hwIASVoicePortBraStateAlarmTraps 5 }
    
    hwIASVoicePortBraCrcAlarmResumeTrap NOTIFICATION-TYPE
        OBJECTS  { hwVoicePTPFrame, hwVoicePTPSlot, hwVoicePTPPort }
        STATUS      current
        DESCRIPTION    
            "
            The trap indicates that BRA Port CRC reached alarm threshold Clear.
            "
        ::= { hwIASVoicePortBraStateAlarmTraps 6 }
   
 --  /*  End  hwIASVoicePortBraAlarmTraps */ 

 --  /* Start hwIASVoicePortE1AlarmTraps */

    hwIASVoicePortE1StateAlarmTraps OBJECT IDENTIFIER ::= { hwIASVoicePortE1AlarmTraps 0 }
 
    hwIASVoicePortE1FaultTrap NOTIFICATION-TYPE
        OBJECTS  { hwVoicePTPFrame, hwVoicePTPSlot, hwVoicePTPPort }
        STATUS      current
        DESCRIPTION    
            "
            The trap indicates that E1 line abnormal.
            "
        ::= { hwIASVoicePortE1StateAlarmTraps 1 }
    
    hwIASVoicePortE1ResumeTrap NOTIFICATION-TYPE
        OBJECTS  { hwVoicePTPFrame, hwVoicePTPSlot, hwVoicePTPPort }
        STATUS      current
        DESCRIPTION    
            "
            The trap indicates that E1 line recovery.
            "
        ::= { hwIASVoicePortE1StateAlarmTraps 2 }
    
    hwIASVoicePortE1DegradeTrap NOTIFICATION-TYPE
        OBJECTS  { hwVoicePTPFrame, hwVoicePTPSlot, hwVoicePTPPort }
        STATUS      current
        DESCRIPTION    
            "
            The trap indicates that the number of CRC errors on the E1 port reaches the degraded threshold.
            "
        ::= { hwIASVoicePortE1StateAlarmTraps 3 }
    
    hwIASVoicePortE1DegradeResumeTrap NOTIFICATION-TYPE
        OBJECTS  { hwVoicePTPFrame, hwVoicePTPSlot, hwVoicePTPPort }
        STATUS      current
        DESCRIPTION    
            "
            The trap indicates that E1 Port CRC reached degraded threshold Clear.
            "
        ::= { hwIASVoicePortE1StateAlarmTraps 4 }
    
    hwIASVoicePortE1CrcAlarmTrap NOTIFICATION-TYPE
        OBJECTS  { hwVoicePTPFrame, hwVoicePTPSlot, hwVoicePTPPort }
        STATUS      current
        DESCRIPTION    
            "
            The trap indicates that the CRC errors on the E1 port reach the alarm threshold.
            "
        ::= { hwIASVoicePortE1StateAlarmTraps 5 }
    
    hwIASVoicePortE1CrcAlarmResumeTrap NOTIFICATION-TYPE
        OBJECTS  { hwVoicePTPFrame, hwVoicePTPSlot, hwVoicePTPPort }
        STATUS      current
        DESCRIPTION    
            "
            The trap indicates that E1 Port CRC reached alarm threshold Clear.
            "
        ::= { hwIASVoicePortE1StateAlarmTraps 6 }
   
    hwIASVoicePortE1BitFaultTrap NOTIFICATION-TYPE
        OBJECTS  { hwVoicePTPFrame, hwVoicePTPSlot, hwVoicePTPPort }
        STATUS      current
        DESCRIPTION    
            "
            The trap indicates that the number of the error bits of the E1 port reaches the threshold.
            "
        ::= { hwIASVoicePortE1StateAlarmTraps 7 }
    
    hwIASVoicePortE1BitResumeTrap NOTIFICATION-TYPE
        OBJECTS  { hwVoicePTPFrame, hwVoicePTPSlot, hwVoicePTPPort }
        STATUS      current
        DESCRIPTION    
            "
            The trap indicates that E1 port Bit Error reached threshold clear.
            "
        ::= { hwIASVoicePortE1StateAlarmTraps 8 }
    
    hwIASVoicePortE1LdtTrap NOTIFICATION-TYPE
        OBJECTS  { hwVoicePTPFrame, hwVoicePTPSlot, hwVoicePTPPort }
        STATUS      current
        DESCRIPTION    
            "
            The trap indicates that the number of the transient error bits of the E1 port reaches the alarm threshold.
            "
        ::= { hwIASVoicePortE1StateAlarmTraps 9 }
    
    hwIASVoicePortE1FrmslipTrap NOTIFICATION-TYPE
        OBJECTS  { hwVoicePTPFrame, hwVoicePTPSlot, hwVoicePTPPort }
        STATUS      current
        DESCRIPTION    
            "
            The trap indicates that the out-of-synchronization frames of the E1 port reach the degraded threshold.
            "
        ::= { hwIASVoicePortE1StateAlarmTraps 10 }
   
 --  /*  End  hwIASVoicePortE1AlarmTraps */ 
 
 --  /* Start hwIASVoicePortIsdnL2AlarmTraps */ 
 
    hwIASVoicePortIsdnL2ErrorAlarmTraps OBJECT IDENTIFIER ::= { hwIASVoicePortIsdnL2AlarmTraps 0 }
 
    hwIASVoicePortIsdnL2ErrorTrap NOTIFICATION-TYPE
        OBJECTS  { hwVoicePTPFrame, hwVoicePTPSlot, hwVoicePTPPort }
        STATUS      current
        DESCRIPTION    
            "
            The trap indicates that the times of the receipt of Q.921 unsolicited response reach the alarm threshold.
            "
        ::= { hwIASVoicePortIsdnL2ErrorAlarmTraps 1 }     
        
  --  /*  End  hwIASVoicePortIsdnL2AlarmTraps */
  
       
  --  /*  Start  hwIASVoicePortFxoAlarmTraps */
  
    hwIASVoicePortFxoPowerAlarmTraps OBJECT IDENTIFIER ::= { hwIASVoicePortFxoAlarmTraps 0 }
  
    hwIASVoiceFxoPortPowerAlarmTrap NOTIFICATION-TYPE
        OBJECTS  { hwVoicePTPFrame, hwVoicePTPSlot, hwVoicePTPPort }
        STATUS      current
        DESCRIPTION    
            "
            The trap indicates that FXO port power fault.
            "
        ::= { hwIASVoicePortFxoPowerAlarmTraps 1 }     
        
    hwIASVoiceFxoPortPowerAlarmRestoreTrap NOTIFICATION-TYPE
        OBJECTS  { hwVoicePTPFrame, hwVoicePTPSlot, hwVoicePTPPort }
        STATUS      current
        DESCRIPTION    
            "
            The trap indicates that FXO port power restore.
            "
        ::= { hwIASVoicePortFxoPowerAlarmTraps 2 }
 
 --  /*  End  hwIASVoicePortFxoAlarmTraps */

 
     
END
