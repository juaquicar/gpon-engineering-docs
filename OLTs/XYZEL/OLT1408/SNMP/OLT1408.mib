-- ZyXEL Communications Corporation
-- Private Enterprise MIB definition

-- This file describes the ZyXEL Communications Corporation Enterprise MIB.
-- It contains ZyXEL products OIDs, and common managed objects.


ZYXEL-olt1408-MIB DEFINITIONS ::= BEGIN

    IMPORTS
	enterprises		FROM RFC1155-SMI

	OBJECT-TYPE
		FROM SNMPv2-SMI			-- RFC2578
	RowStatus, DateAndTime, TruthValue, StorageType, MacAddress
		FROM SNMPv2-TC			-- RFC2579
	DisplayString
	  	FROM RFC1213-MIB
	EnabledStatus
		FROM  P-BRIDGE-MIB
	PortList, dot1qVlanIndex
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB
    dot1agCfmMdIndex
		FROM IEEE8021-CFM-MIB
	dot1agCfmMaIndex
		FROM IEEE8021-CFM-MIB
	dot1agCfmMepIdentifier
		FROM IEEE8021-CFM-MIB
    IpAddress
        FROM SNMPv2-SMI
    ifIndex
    	FROM IF-MIB					-- RFC2863
    NOTIFICATION-TYPE
        FROM SNMPv2-SMI
    sysObjectID
        FROM RFC1213-MIB
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB;

  zyxel        OBJECT IDENTIFIER ::= { enterprises 890 }
	products     OBJECT IDENTIFIER ::= { zyxel 1 }
	accessSwitch OBJECT IDENTIFIER ::= { products 5 }
	gponSeries	 OBJECT IDENTIFIER ::= { accessSwitch 17 }
  olt1408		OBJECT IDENTIFIER ::= { gponSeries 6 }
  olt1408AC		OBJECT IDENTIFIER ::= { gponSeries 7 }
  olt1408B-IA   OBJECT IDENTIFIER ::= { gponSeries 9 }

	sysInfo     					OBJECT IDENTIFIER ::= { olt1408 1 }
	rateLimitSetup 					OBJECT IDENTIFIER ::= { olt1408 2 }
	brLimitSetup 					OBJECT IDENTIFIER ::= { olt1408 3 }
	portSecuritySetup 				OBJECT IDENTIFIER ::= { olt1408 4 }
	vlanTrunkSetup 					OBJECT IDENTIFIER ::= { olt1408 5 }
	ctlProtTransSetup 				OBJECT IDENTIFIER ::= { olt1408 6 }
	vlanStackSetup 					OBJECT IDENTIFIER ::= { olt1408 7 }
	dot1xSetup 						OBJECT IDENTIFIER ::= { olt1408 8 }
	hwMonitorInfo 					OBJECT IDENTIFIER ::= { olt1408 9 }
	snmpSetup 						OBJECT IDENTIFIER ::= { olt1408 10 }
	dateTimeSetup     				OBJECT IDENTIFIER ::= { olt1408 11 }
	sysMgmt     					OBJECT IDENTIFIER ::= { olt1408 12 }
	layer2Setup     				OBJECT IDENTIFIER ::= { olt1408 13 }
	ipSetup     					OBJECT IDENTIFIER ::= { olt1408 14 }
	filterSetup     				OBJECT IDENTIFIER ::= { olt1408 15 }
	mirrorSetup     				OBJECT IDENTIFIER ::= { olt1408 16 }
	aggrSetup     					OBJECT IDENTIFIER ::= { olt1408 17 }
	accessCtlSetup     				OBJECT IDENTIFIER ::= { olt1408 18 }
	queuingMethodSetup  			OBJECT IDENTIFIER ::= { olt1408 19 }
	dhcpSetup     					OBJECT IDENTIFIER ::= { olt1408 20 }
	arpInfo     					OBJECT IDENTIFIER ::= { olt1408 22 }
	portOpModeSetup     			OBJECT IDENTIFIER ::= { olt1408 23 }
	multicastPortSetup  			OBJECT IDENTIFIER ::= { olt1408 25 }
	multicastStatus    				OBJECT IDENTIFIER ::= { olt1408 26 }
--	igmpFilteringProfileSetup     	OBJECT IDENTIFIER ::= { olt1408 27 }
	mvrSetup     					OBJECT IDENTIFIER ::= { olt1408 28 }
--	clusterSetup     				OBJECT IDENTIFIER ::= { olt1408 29 }


	faultMIB MODULE-IDENTITY
    LAST-UPDATED "200411031200Z" -- YYYY/MM/DD, HH/MM
    ORGANIZATION "ZyXEL"
    CONTACT-INFO ""
    DESCRIPTION
            "Fault event table definitions"
    ::= { olt1408 30 }

	faultTrapsMIB MODULE-IDENTITY
    LAST-UPDATED "200411011200Z" -- YYYY/MM/DD, HH/MM
    ORGANIZATION "ZyXEL"
    CONTACT-INFO ""
    DESCRIPTION
            "Fault event trap definitions"
    ::= { olt1408 31 }


	protoBasedVlanSetup     		OBJECT IDENTIFIER ::= { olt1408 32 }
	sysLogSetup     				OBJECT IDENTIFIER ::= { olt1408 33 }
	l3Routing     					OBJECT IDENTIFIER ::= { olt1408 35 }
	ipStatus    					OBJECT IDENTIFIER ::= { olt1408 39 }
--	ospfExt    						OBJECT IDENTIFIER ::= { olt1408 41 }
--	mrstp     						OBJECT IDENTIFIER ::= { olt1408 42 }


	dhcpSnp							OBJECT IDENTIFIER ::= { olt1408 100 }
	ipsg							OBJECT IDENTIFIER ::= { olt1408 101 }
	arpInspect						OBJECT IDENTIFIER ::= { olt1408 102 }
	trTCMSetup						OBJECT IDENTIFIER ::= { olt1408 103 }
	loopGuardSetup					OBJECT IDENTIFIER ::= { olt1408 104 }
	subnetBasedVlanSetup			OBJECT IDENTIFIER ::= { olt1408 105 }
	macAuthenticationSetup			OBJECT IDENTIFIER ::= { olt1408 106 }
	mstp							OBJECT IDENTIFIER ::= { olt1408 107 }
	radiusServerSetup				OBJECT IDENTIFIER ::= { olt1408 108 }
	tacacsServerSetup				OBJECT IDENTIFIER ::= { olt1408 109 }
	aaaSetup						OBJECT IDENTIFIER ::= { olt1408 110 }
--	portIsolationSetup				OBJECT IDENTIFIER ::= { olt1408 112 }
--	l2ptSetup						OBJECT IDENTIFIER ::= { olt1408 115 }
	vlanTranslationSetup			OBJECT IDENTIFIER ::= { olt1408 116 }
	transceiverInfo					OBJECT IDENTIFIER ::= { olt1408 117 }
--	dot3OamSetup					OBJECT IDENTIFIER ::= { olt1408 118 }
	dot1agCfmSetup					OBJECT IDENTIFIER ::= { olt1408 119 }
--	vlanCounterSetup				OBJECT IDENTIFIER ::= { olt1408 122 }
	sysMemoryPool					OBJECT IDENTIFIER ::= { olt1408 124 }
	pppoe							OBJECT IDENTIFIER ::= { olt1408 125 }
	arpLearningSetup 				OBJECT IDENTIFIER ::= { olt1408 126 }
	staticRouteSetup     			OBJECT IDENTIFIER ::= { olt1408 127 }
	routingStatus    				OBJECT IDENTIFIER ::= { olt1408 128 }
	externalAlarmSetup    				OBJECT IDENTIFIER ::= { olt1408 129 }
	errdisable     					OBJECT IDENTIFIER ::= { olt1408 130 }
	cpuProtectionSetup    			OBJECT IDENTIFIER ::= { olt1408 131 }
--	policyRouteSetup     			OBJECT IDENTIFIER ::= { olt1408 132 }
--	privateVLANSetup				OBJECT IDENTIFIER ::= { olt1408 133 }
--	sFlowSetup     					OBJECT IDENTIFIER ::= { olt1408 134 }
	remoteOnt     					OBJECT IDENTIFIER ::= { olt1408 135 }
	remoteOntInfo                   OBJECT IDENTIFIER ::= { olt1408 136 }
	antiSpoofSetup	                                OBJECT IDENTIFIER ::= { olt1408 138 }
	multicastChannelSetup                           OBJECT IDENTIFIER ::= { olt1408 140 }
	ponSetup                           OBJECT IDENTIFIER ::= { olt1408 142 }
	ontFwUpgrade           	        OBJECT IDENTIFIER ::= { olt1408 143 }
	portBridgeSetup           	        OBJECT IDENTIFIER ::= { olt1408 144 }
	cdr           	                OBJECT IDENTIFIER ::= { olt1408 145 }
	classifierSetup           	        OBJECT IDENTIFIER ::= { olt1408 146 }
	policySetup           	                OBJECT IDENTIFIER ::= { olt1408 147 }
	uniPortOpModeSetup           	                OBJECT IDENTIFIER ::= { olt1408 148 }
	macInfo           	            OBJECT IDENTIFIER ::= { olt1408 149 }
	antiMacSpoofSetup           	        OBJECT IDENTIFIER ::= { olt1408 150 }
	protectSwitch           	            OBJECT IDENTIFIER ::= { olt1408 153 }
	rateThresholdSetup              OBJECT IDENTIFIER ::= { olt1408 157 }
	erpsSetup              OBJECT IDENTIFIER ::= { olt1408 158 }
	wred							              OBJECT IDENTIFIER ::= { olt1408 159 }
	dhcpClientTest					OBJECT IDENTIFIER ::= { olt1408 160 }
	sysTimeRef					OBJECT IDENTIFIER ::= { olt1408 161 }
	dhcpL2Agent					OBJECT IDENTIFIER ::= { olt1408 162 }
	macForcedForwarding			OBJECT IDENTIFIER ::= { olt1408 163 }
--  1.sysInfo

        sysSwPlatformMajorVers OBJECT-TYPE
        SYNTAX  INTEGER
        MAX-ACCESS  read-only
        STATUS  current
        DESCRIPTION
                      "SW platform major version, e.g. 3."
        ::= { sysInfo 1 }

        sysSwPlatformMinorVers OBJECT-TYPE
        SYNTAX  INTEGER
        MAX-ACCESS  read-only
        STATUS  current
        DESCRIPTION
                      "SW platform minor version, e.g. 50."
        ::= { sysInfo 2 }

        sysSwModelString OBJECT-TYPE
        SYNTAX  DisplayString
        MAX-ACCESS  read-only
        STATUS  current
        DESCRIPTION
                      "Model letters, e.g. TJ"
        ::= { sysInfo 3 }

        sysSwDay OBJECT-TYPE
        SYNTAX  INTEGER
        MAX-ACCESS  read-only
        STATUS  current
        DESCRIPTION
                      "SW compilation day, e.g. 19."
        ::= { sysInfo 4 }

        sysSwMonth OBJECT-TYPE
        SYNTAX  INTEGER
        MAX-ACCESS  read-only
        STATUS  current
        DESCRIPTION
                      "SW compilation month, e.g. 8."
        ::= { sysInfo 5 }

        sysSwYear OBJECT-TYPE
        SYNTAX  INTEGER
        MAX-ACCESS  read-only
        STATUS  current
        DESCRIPTION
                      "SW compilation year, e.g. 2004."
        ::= { sysInfo 6 }

        sysSerialNumber OBJECT-TYPE
        SYNTAX  DisplayString
        MAX-ACCESS  read-only
        STATUS  current
        DESCRIPTION
                      "Serial number"
        ::= { sysInfo 7 }

        sysSwBootUpImage OBJECT-TYPE
        SYNTAX  INTEGER{
         		image1(1),
         		image2(2)
        }
        MAX-ACCESS  read-only
        STATUS	current
        DESCRIPTION
                      "Current system boot up image"
--                      You can change the boot up image of next rebooting by setting sysMgmtBootupImage."
        ::= { sysInfo 8 }

        sysImage1FwVersion OBJECT-TYPE
        SYNTAX  DisplayString
        MAX-ACCESS  read-only
        STATUS	current
        DESCRIPTION
                      "OLT Image 1 Firmware Version"
        ::= { sysInfo 9 }

        sysImage2FwVersion OBJECT-TYPE
        SYNTAX  DisplayString
        MAX-ACCESS  read-only
        STATUS	current
        DESCRIPTION
                      "OLT Image 2 Firmware Version"
        ::= { sysInfo 10 }

        sysCurrentFwVersion OBJECT-TYPE
        SYNTAX  DisplayString
        MAX-ACCESS  read-only
        STATUS  current
        DESCRIPTION
                      "OLT Current Firmware Version."
        ::= { sysInfo 11 }


 --       sysSwVersionControlNbr OBJECT-TYPE
 --       SYNTAX  INTEGER
 --       MAX-ACCESS  read-only
 --       STATUS  current
 --       DESCRIPTION
 --                     "Version control number, e.g. 0."
 --       ::= { sysInfo 12 }

 --       sysHwMajorVers OBJECT-TYPE
 --       SYNTAX  INTEGER
 --       MAX-ACCESS  read-only
 --       STATUS  current
 --       DESCRIPTION
 --                     "HW major version number, e.g. 1."
 --       ::= { sysInfo 13 }

 --       sysHwMinorVers OBJECT-TYPE
 --       SYNTAX  INTEGER
 --       MAX-ACCESS  read-only
 --       STATUS  current
 --       DESCRIPTION
 --                     "HW minor version number, e.g. 0."
 --      ::= { sysInfo 14 }

        pwrInfo   			OBJECT IDENTIFIER ::= { sysInfo 18 }

        pwrInfoSource OBJECT-TYPE
          SYNTAX  INTEGER {
          		dc(0),
          		ac(1),
          		battery(2)
          }
          MAX-ACCESS read-only
          STATUS current
          DESCRIPTION
          	"The power source that provides power currently. AC first"
          ::= { pwrInfo 1 }

        pwrInfoSysPowerConsumption OBJECT-TYPE
    				SYNTAX  INTEGER
    				MAX-ACCESS read-only
    				STATUS current
    				DESCRIPTION
    					"The system power consumption.
    					Unit: mW"
    				::= { pwrInfo 2 }

        pwrInfoBatChargingPower OBJECT-TYPE
    				SYNTAX  INTEGER
    				MAX-ACCESS read-only
    				STATUS current
    				DESCRIPTION
    					"The power that is used by charging feature.
    					Unit: mW"
    				::= { pwrInfo 3 }

        pwrInfoBatExistence OBJECT-TYPE
    				SYNTAX  INTEGER {
    						exist(1),
    						noExist(0)
    				}
    				MAX-ACCESS read-only
    				STATUS current
    				DESCRIPTION
    					"The existence of battery."
    				::= { pwrInfo 4 }

        pwrInfoBatTemperature OBJECT-TYPE
    				SYNTAX  INTEGER
    				MAX-ACCESS read-only
    				STATUS current
    				DESCRIPTION
    					"The temperature of battery.
    					Unit: 0.1 Celsius
    					*Note that this value will always be 0 when no thermal sensor."
    				::= { pwrInfo 5 }

        pwrInfoBatRemainingPower OBJECT-TYPE
    				SYNTAX  INTEGER
    				MAX-ACCESS read-only
    				STATUS current
    				DESCRIPTION
    					"The remaining power of battery.
    					Unit: percentage (%)
    					*Note that this value will always be 0 when battery does not exist."
    				::= { pwrInfo 6 }

        pwrInfoBatVoltage OBJECT-TYPE
    				SYNTAX  INTEGER
    				MAX-ACCESS read-only
    				STATUS current
    				DESCRIPTION
    					"The voltage of battery.
    					Unit: mV
    					*Note that this value will always be 0 when battery does not exist."
    				::= { pwrInfo 7 }

        pwrInfoBatCapacityValidation OBJECT-TYPE
    				SYNTAX  INTEGER {
    						invalid(0),
    						valid(1)
    				}
    				MAX-ACCESS read-only
    				STATUS current
    				DESCRIPTION
    					"The validation of battery information (capacity).
    					*Note that this value will always be invalid(0) when battery does not exist."
    				::= { pwrInfo 8 }

        pwrInfoChargerStatus OBJECT-TYPE
    				SYNTAX  INTEGER {
    						on(1),
    						off(0)
    				}
    				MAX-ACCESS read-only
    				STATUS current
    				DESCRIPTION
    					"The status of charger."
    				::= { pwrInfo 9 }

        pwrInfoChargingCurrent OBJECT-TYPE
    				SYNTAX  INTEGER
    				MAX-ACCESS read-only
    				STATUS current
    				DESCRIPTION
    					"The charging current of charger.
    					Unit: mA
    					*Note that this value will always be 0 when charger is off."
    				::= { pwrInfo 10 }

        pwrInfoChargingVoltage OBJECT-TYPE
    				SYNTAX  INTEGER
    				MAX-ACCESS read-only
    				STATUS current
    				DESCRIPTION
    					"The charging voltage of charger.
    					Unit: mV
    					*Note that this value will always be 0 when charger is off."
    				::= { pwrInfo 11 }

        pwrInfoChargingTime OBJECT-TYPE
    				SYNTAX  INTEGER
    				MAX-ACCESS read-only
    				STATUS current
    				DESCRIPTION
    					"The time period since charger has been enabled.
    					Unit: second
    					*Note that this value will always be 0 when charger is off."
    				::= { pwrInfo 12 }

        pwrInfoTrickleChargerStatus OBJECT-TYPE
    				SYNTAX  INTEGER {
    						off(0),
    						on(1),
    						none(2)
    				}
    				MAX-ACCESS read-only
    				STATUS current
    				DESCRIPTION
    					"The status of trickle charger.
    					*Note that this value will always be 'none' when charger is off."
    				::= { pwrInfo 13 }


       batterySetting  OBJECT IDENTIFIER ::= { pwrInfo 14 }

    	 batteryCapacity OBJECT-TYPE
            SYNTAX INTEGER
            MAX-ACCESS read-write
            STATUS current
            DESCRIPTION
                "Set battery capacity, user has to set this value to enable charger feature.
				0: No user input, 7~18(Ah).
                When battery information is invalid, user needs to re-enter the batter capacity to continue charging procedure."
            ::= { batterySetting 1 }

    	 batteryTempThresholdHigh OBJECT-TYPE
            SYNTAX INTEGER (-15..50)
            MAX-ACCESS read-write
            STATUS current
            DESCRIPTION
            	"Battery high temperature threshold."
            ::= { batterySetting 2 }

    	 batteryTempThresholdLow OBJECT-TYPE
            SYNTAX INTEGER (-15..50)
            MAX-ACCESS read-write
            STATUS current
            DESCRIPTION
            	"Battery low temperature threshold."
            ::= { batterySetting 3 }


--  2.rateLimitSetup

        rateLimitState OBJECT-TYPE
        SYNTAX  EnabledStatus
        MAX-ACCESS  read-write
        STATUS  current
        DESCRIPTION
        	"Ingress/egress rate limiting enabled/disabled for the switch."
        ::= { rateLimitSetup 1 }

--  	rateLimitPortTable

        rateLimitPortTable OBJECT-TYPE
        SYNTAX	SEQUENCE OF RateLimitPortEntry
        MAX-ACCESS  not-accessible
        STATUS  current
        DESCRIPTION
                 	""
        ::= { rateLimitSetup 2 }

		rateLimitPortEntry OBJECT-TYPE
        SYNTAX	RateLimitPortEntry
        MAX-ACCESS	not-accessible
        STATUS	current
        DESCRIPTION    	"An entry in rateLimitPortTable."
        INDEX          	{ dot1dBasePort }
        ::= { rateLimitPortTable 1 }

        RateLimitPortEntry ::=
           SEQUENCE {
        	rateLimitPortState	EnabledStatus,
        	rateLimitPortCommitRate	INTEGER,
			rateLimitPortPeakRate	INTEGER,
			rateLimitPortEgrRate	INTEGER,
			rateLimitPortPeakState	EnabledStatus,
			rateLimitPortEgrState	EnabledStatus,
			rateLimitPortCommitState EnabledStatus
           }

        rateLimitPortState OBJECT-TYPE
        SYNTAX  EnabledStatus
        MAX-ACCESS  read-write
        STATUS  current
        DESCRIPTION
                      	"Ingress/egress rate limiting enabled/disabled on the port."
        ::= { rateLimitPortEntry 1 }

        rateLimitPortCommitRate OBJECT-TYPE
        SYNTAX  INTEGER
        MAX-ACCESS  read-write
        STATUS  current
        DESCRIPTION
                      	"Commit rate in Kbit/s.  The range of pon port is between 0 and 1,250,000.
						                                  For eth-1 ~ eth-8, the range is between 0 and 1,000,000.
														 For eth-9 ~ eth-16, the range is between 0 and 2,500,000.
														For eth-17 ~ eth-20, the range is between 0 and 10,000,000."
        ::= { rateLimitPortEntry 2 }

        rateLimitPortPeakRate OBJECT-TYPE
        SYNTAX  INTEGER
        MAX-ACCESS  read-write
        STATUS  current
        DESCRIPTION
                      	"Peak rate in Kbit/s.  The range of of pon port is between 0 and 1,250,000.
						                                  For eth-1 ~ eth-8, the range is between 0 and 1,000,000.
														 For eth-9 ~ eth-16, the range is between 0 and 2,500,000.
													    For eth-17 ~ eth-20, the range is between 0 and 10,000,000."
        ::= { rateLimitPortEntry 3 }

        rateLimitPortEgrRate OBJECT-TYPE
        SYNTAX  INTEGER
        MAX-ACCESS  read-write
        STATUS  current
        DESCRIPTION
                      	"Egress rate in Kbit/s.  The range of of pon port is between 0 and 2,500,000.
						                                  For eth-1 ~ eth-8, the range is between 0 and 1,000,000.
														 For eth-9 ~ eth-16, the range is between 0 and 2,500,000.
														For eth-17 ~ eth-20, the range is between 0 and 10,000,000."
        ::= { rateLimitPortEntry 4 }

        rateLimitPortPeakState OBJECT-TYPE
        SYNTAX  EnabledStatus
        MAX-ACCESS  read-write
        STATUS  current
        DESCRIPTION
                      	"Ingress peak rate limiting enabled/disabled on the port."
        ::= { rateLimitPortEntry 5 }

        rateLimitPortEgrState OBJECT-TYPE
        SYNTAX  EnabledStatus
        MAX-ACCESS  read-write
        STATUS  current
        DESCRIPTION
                      	"Egress rate limiting enabled/disabled on the port."
        ::= { rateLimitPortEntry 6 }

        rateLimitPortCommitState OBJECT-TYPE
        SYNTAX  EnabledStatus
        MAX-ACCESS  read-write
        STATUS  current
        DESCRIPTION
                      	"Ingress commit rate limiting enabled/disabled on the port."
        ::= { rateLimitPortEntry 7 }

--  3.brLimitSetup

        brLimitState OBJECT-TYPE
        SYNTAX  EnabledStatus
        MAX-ACCESS  read-write
        STATUS  current
        DESCRIPTION
                      	"Broadcast/multicast/DLF rate limiting enabled/disabled for the switch."
        ::= { brLimitSetup 1 }

-- 		brLimitPortTable
        brLimitPortTable OBJECT-TYPE
        SYNTAX	SEQUENCE OF BrLimitPortEntry
        MAX-ACCESS  not-accessible
        STATUS  current
        DESCRIPTION
                 	""
        ::= { brLimitSetup 2 }

		brLimitPortEntry OBJECT-TYPE
        SYNTAX	BrLimitPortEntry
        MAX-ACCESS	not-accessible
        STATUS	current
        DESCRIPTION    	"An entry in brLimitPortTable."
        INDEX          	{ dot1dBasePort }
        ::= { brLimitPortTable 1 }

        BrLimitPortEntry ::=
           SEQUENCE {
        	brLimitPortBrState	EnabledStatus,
			brLimitPortBrRate	INTEGER,
			brLimitPortMcState	EnabledStatus,
			brLimitPortMcRate	INTEGER,
			brLimitPortDlfState	EnabledStatus,
			brLimitPortDlfRate	INTEGER,
			brLimitPortCounter	EnabledStatus,
			brLimitPortLogging	EnabledStatus
           }

        brLimitPortBrState OBJECT-TYPE
        SYNTAX  EnabledStatus
        MAX-ACCESS  read-write
        STATUS  current
        DESCRIPTION
                      	"Broadcast rate limiting enabled/disabled on the port."
        ::= { brLimitPortEntry 1 }

        brLimitPortBrRate OBJECT-TYPE
        SYNTAX  INTEGER
        MAX-ACCESS  read-write
        STATUS  current
        DESCRIPTION
                      	"Allowed broadcast rate in pkts/s. The maximum value for pon port is 262143.
						                                   The maximum value for eth-1 ~ eth-16 is 262143.
														   The maximum value for eth-17 ~ eth-20 is 33554431."
        ::= { brLimitPortEntry 2 }

        brLimitPortMcState OBJECT-TYPE
        SYNTAX  EnabledStatus
        MAX-ACCESS  read-write
        STATUS  current
        DESCRIPTION
                      	"Multicast rate limiting enabled/disabled on the port."
        ::= { brLimitPortEntry 3 }

        brLimitPortMcRate OBJECT-TYPE
        SYNTAX  INTEGER
        MAX-ACCESS  read-write
        STATUS  current
        DESCRIPTION
                      	"AAllowed mullticast rate in pkts/s. The maximum value for pon port is 262143.
						                                   The maximum value for eth-1 ~ eth-16 is 262143.
														   The maximum value for eth-17 ~ eth-20 is 33554431."
        ::= { brLimitPortEntry 4 }

        brLimitPortDlfState OBJECT-TYPE
        SYNTAX  EnabledStatus
        MAX-ACCESS  read-write
        STATUS  current
        DESCRIPTION
                      	"Destination lookup failure frames rate limiting enabled/disabled on the port."
        ::= { brLimitPortEntry 5 }

        brLimitPortDlfRate OBJECT-TYPE
        SYNTAX  INTEGER
        MAX-ACCESS  read-write
        STATUS  current
        DESCRIPTION
                      	"Allowed destination lookup failure frames rate in pkts/s. The maximum value for pon port is 262143.
						                                   The maximum value for eth-1 ~ eth-16 is 262143.
														   The maximum value for eth-17 ~ eth-20 is 33554431."
        ::= { brLimitPortEntry 6 }

        brLimitPortCounter OBJECT-TYPE
        SYNTAX  EnabledStatus
        MAX-ACCESS  read-write
        STATUS  current
        DESCRIPTION
                      	"Broadcast/multicast/DLF drop counter enabled/disabled per port setting."
        ::= { brLimitPortEntry 7 }

        brLimitPortLogging OBJECT-TYPE
        SYNTAX  EnabledStatus
        MAX-ACCESS  read-write
        STATUS  current
        DESCRIPTION
                      	"Broadcast/multicast/DLF drop logging enabled/disabled per port setting."
        ::= { brLimitPortEntry 8 }

-- 		brLimitPortCounterTable
        brLimitPortCounterTable OBJECT-TYPE
        SYNTAX	SEQUENCE OF BrLimitPortCounterEntry
        MAX-ACCESS  not-accessible
        STATUS  current
        DESCRIPTION
                 	""
        ::= { brLimitSetup 3 }


		brLimitPortCounterEntry OBJECT-TYPE
        SYNTAX	BrLimitPortCounterEntry
        MAX-ACCESS	not-accessible
        STATUS	current
        DESCRIPTION    	"An entry in brLimitPortCounterTable."
        INDEX          	{ dot1dBasePort }
        ::= { brLimitPortCounterTable 1 }

        BrLimitPortCounterEntry ::=
           SEQUENCE {
			brLimitPortBrCounter	Counter64,
			brLimitPortMcCounter	Counter64,
			brLimitPortDlfCounter	Counter64,
          }

        brLimitPortBrCounter OBJECT-TYPE
        SYNTAX  Counter64
        MAX-ACCESS  read-only
        STATUS  current
        DESCRIPTION
                      	"broadcast drop counter for the port."
        ::= { brLimitPortCounterEntry 1 }

        brLimitPortMcCounter OBJECT-TYPE
        SYNTAX  Counter64
        MAX-ACCESS  read-only
        STATUS  current
        DESCRIPTION
                      	"multicast drop counter for the port."
        ::= { brLimitPortCounterEntry 2 }

        brLimitPortDlfCounter OBJECT-TYPE
        SYNTAX  Counter64
        MAX-ACCESS  read-only
        STATUS  current
        DESCRIPTION
                      	"DLF counter for the port."
        ::= { brLimitPortCounterEntry 3 }

        brLimitCounterClear OBJECT-TYPE
        SYNTAX  EnabledStatus
        MAX-ACCESS  read-write
        STATUS  current
        DESCRIPTION
                      	"Clear Broadcast/multicast/DLF drop counter, always return disable"
        ::= { brLimitSetup 4 }

--  4.portSecuritySetup

		portSecurityState OBJECT-TYPE
        SYNTAX  EnabledStatus
        MAX-ACCESS  read-write
        STATUS  current
        DESCRIPTION
                      	""
        ::= { portSecuritySetup 1 }

        portSecurityPortTable OBJECT-TYPE
        SYNTAX	SEQUENCE OF PortSecurityPortEntry
        MAX-ACCESS  not-accessible
        STATUS  current
        DESCRIPTION
                 	""
        ::= { portSecuritySetup 2 }

		portSecurityPortEntry OBJECT-TYPE
        SYNTAX	PortSecurityPortEntry
        MAX-ACCESS	not-accessible
        STATUS	current
        DESCRIPTION    	"An entry in portSecurityPortTable."
        INDEX          	{ dot1dBasePort }
        ::= { portSecurityPortTable 1 }

        PortSecurityPortEntry ::=
           SEQUENCE {
        	portSecurityPortState		EnabledStatus,
		portSecurityPortLearnState	EnabledStatus,
		portSecurityPortCount		INTEGER
--		portSecurityAntiMacSpoofState   EnabledStatus
           }

        portSecurityPortState OBJECT-TYPE
        SYNTAX  EnabledStatus
        MAX-ACCESS  read-write
        STATUS  current
        DESCRIPTION
                      	"Port Security enabled/disabled on the port.
                      	Active(1) means this port only accept frames from static MAC addresses that are configured for the port,
                      	and dynamic MAC address frames up to the number specified by portSecurityPortCount object."
        ::= { portSecurityPortEntry 1 }

        portSecurityPortLearnState OBJECT-TYPE
        SYNTAX  EnabledStatus
        MAX-ACCESS  read-write
        STATUS  current
        DESCRIPTION
                      	"MAC address learning  enabled/disable on the port."
        ::= { portSecurityPortEntry 2 }

        portSecurityPortCount OBJECT-TYPE
        SYNTAX  INTEGER
        MAX-ACCESS  read-write
        STATUS  current
        DESCRIPTION
                      	"Number of (dynamic) MAC addresses that may be learned on the port. The maximum value for pon port is 1023.
						                                   The maximum value for eth-1 ~ eth-20 is 8191"
        ::= { portSecurityPortEntry 3 }

--	portSecurityAntiMacSpoofState OBJECT-TYPE
--        SYNTAX  EnabledStatus
--        MAX-ACCESS  read-write
--        STATUS  current
--       DESCRIPTION
--                      	"Anti-MAC-Spoofing enabled/disable on the subscriber port."
--        ::= { portSecurityPortEntry 4 }

		portSecurityMacFreeze OBJECT-TYPE
        SYNTAX  PortList
        MAX-ACCESS  read-write
        STATUS  current
        DESCRIPTION
                      	"This entry is used to execute MacFreeze action to port.
                      	It's meaningless while reading this entry."
        ::= { portSecuritySetup 3 }


--    	portSecurityVMLTable OBJECT-TYPE
--        SYNTAX	SEQUENCE OF PortSecurityVMLEntry
--        MAX-ACCESS  not-accessible
--        STATUS  current
--        DESCRIPTION
--                 	""
--        ::= { portSecuritySetup 4 }
--
--		portSecurityVMLEntry OBJECT-TYPE
--        SYNTAX	PortSecurityVMLEntry
--        MAX-ACCESS	not-accessible
--        STATUS	current
--        DESCRIPTION    	"An entry in portSecurityVMLTable."
--        INDEX          	{ portSecurityVMLPort, portSecurityVMLVID }
--        ::= { portSecurityVMLTable 1 }
--
--        PortSecurityVMLEntry ::=
--           SEQUENCE {
--        	portSecurityVMLPort			INTEGER,
--			portSecurityVMLVID			INTEGER,
--			portSecurityVMLMacLimit		INTEGER,
--			portSecurityVMLRowStatus	RowStatus
--           }
--
--        portSecurityVMLPort OBJECT-TYPE
--        SYNTAX  INTEGER
--        MAX-ACCESS  read-only
--        STATUS  current
--        DESCRIPTION
--                      	"The configured port number of VLAN MAC Limit."
--        ::= { portSecurityVMLEntry 1 }
--
--        portSecurityVMLVID OBJECT-TYPE
--        SYNTAX  INTEGER
--        MAX-ACCESS  read-only
--        STATUS  current
--        DESCRIPTION
--                      	"The configured VLAN number of VLAN MAC Limit."
--        ::= { portSecurityVMLEntry 2 }
--
--        portSecurityVMLMacLimit OBJECT-TYPE
--        SYNTAX  INTEGER
--        MAX-ACCESS  read-write
--        STATUS  current
--        DESCRIPTION
--                      	"The MAC limit of specific port and VLAN."
--        ::= { portSecurityVMLEntry 3 }
--
--        portSecurityVMLRowStatus OBJECT-TYPE
--        SYNTAX  RowStatus
--        MAX-ACCESS  read-create
--        STATUS  current
--        DESCRIPTION
--                      	""
--        ::= { portSecurityVMLEntry 4 }


--  5.vlanTrunkPortTable

        vlanTrunkPortTable OBJECT-TYPE
        SYNTAX	SEQUENCE OF VlanTrunkPortEntry
        MAX-ACCESS  not-accessible
        STATUS  current
        DESCRIPTION
                 	""
        ::= { vlanTrunkSetup 1 }

		vlanTrunkPortEntry OBJECT-TYPE
        SYNTAX	VlanTrunkPortEntry
        MAX-ACCESS	not-accessible
        STATUS	current
        DESCRIPTION    	"An entry in vlanTrunkPortTable."
        INDEX          	{ dot1dBasePort }
        ::= { vlanTrunkPortTable 1 }

        VlanTrunkPortEntry ::=
           SEQUENCE {
        	vlanTrunkPortState		EnabledStatus
           }

        vlanTrunkPortState OBJECT-TYPE
        SYNTAX  EnabledStatus
        MAX-ACCESS  read-write
        STATUS  current
        DESCRIPTION
                      	"VlanTrunking enabled/disabled on the port.
                      	Active(1) to allow frames belonging to unknown
                      	VLAN groups to pass through the switch."
        ::= { vlanTrunkPortEntry 1 }

--  6.ctlProtTransSetup

        ctlProtTransState OBJECT-TYPE
        SYNTAX  EnabledStatus
        MAX-ACCESS  read-write
        STATUS  current
        DESCRIPTION
                      	"Bridge control protocol transparency enabled/disabled for the switch"
        ::= { ctlProtTransSetup 1 }

-- 		ctlProtTransTunnelPortTable

        ctlProtTransTunnelPortTable OBJECT-TYPE
        SYNTAX	SEQUENCE OF CtlProtTransTunnelPortEntry
        MAX-ACCESS  not-accessible
        STATUS  current
        DESCRIPTION
                 	""
        ::= { ctlProtTransSetup 2 }

		ctlProtTransTunnelPortEntry OBJECT-TYPE
        SYNTAX	CtlProtTransTunnelPortEntry
        MAX-ACCESS	not-accessible
        STATUS	current
        DESCRIPTION    	"An entry in ctlProtTransTunnelPortTable."
        INDEX          	{ dot1dBasePort }
        ::= { ctlProtTransTunnelPortTable 1 }

        CtlProtTransTunnelPortEntry ::=
           SEQUENCE {
        	ctlProtTransTunnelMode	INTEGER
           }

        ctlProtTransTunnelMode OBJECT-TYPE
        SYNTAX  INTEGER{
		peer(0),
		tunnel(1),
		discard(2),
		network(3)
        }
        MAX-ACCESS  read-write
        STATUS  current
        DESCRIPTION
                      	"Bridge control protocol transparency mode for the port.
                      	Modes:  Peer(0), Tunnel(1), Discard(2),  Network(3)"
        ::= { ctlProtTransTunnelPortEntry 1 }

--  7.vlanStackSetup

--        vlanStackState OBJECT-TYPE
--        SYNTAX  EnabledStatus
--        MAX-ACCESS  read-write
--        STATUS  current
--        DESCRIPTION
--                      "VLAN Stacking enabled/disabled for the switch."
--        ::= { vlanStackSetup 1 }

-- 		vlanStackPortTable

        vlanStackPortTable OBJECT-TYPE
        SYNTAX	SEQUENCE OF VlanStackPortEntry
        MAX-ACCESS  not-accessible
        STATUS  current
        DESCRIPTION
                 	""
        ::= { vlanStackSetup 3 }

		vlanStackPortEntry OBJECT-TYPE
        SYNTAX	VlanStackPortEntry
        MAX-ACCESS	not-accessible
        STATUS	current
        DESCRIPTION    	"An entry in vlanStackPortTable."
        INDEX          	{ dot1dBasePort }
        ::= { vlanStackPortTable 1 }

        VlanStackPortEntry ::=
           SEQUENCE {
        	vlanStackPortMode		INTEGER,
        	vlanStackPortVid		INTEGER,
        	vlanStackPortPrio		INTEGER,
        	vlanStackTunnelPortTpid	INTEGER
           }

        vlanStackPortMode OBJECT-TYPE
        SYNTAX  INTEGER {
		normal(1),
		access(2),
		tunnel(3)
		}
        MAX-ACCESS  read-write
        STATUS  current
        DESCRIPTION
                      	"Mode of the port. Set Normal to have the switch ignore frames received
                      	(or transmitted) on this port with VLAN stacking tags.
                      	Anything you configure in SPVID and Priority are ignored.
			Set Access mode to have the switch add the SP TPID tag to all incoming
			frames received on this port. Set Access  mode for ingress ports at the
			edge of the service provider's network. Set Tunnel mode (available for
			Gigabit ports only) for egress ports at the edge of the service provider's
			network. In order to support VLAN stacking on a port, the port must be able
			to allow frames of 1526 Bytes (1522 Bytes + 4 Bytes for the second tag)
			to pass through it. normal (1), Access (2),  tunnel (3)"
        ::= { vlanStackPortEntry 1 }

        vlanStackPortVid OBJECT-TYPE
        SYNTAX  INTEGER
        MAX-ACCESS  read-write
        STATUS  current
        DESCRIPTION
                      	"VLAN ID used in service provider tag."
        ::= { vlanStackPortEntry 2 }

        vlanStackPortPrio OBJECT-TYPE
        SYNTAX  INTEGER {
        		priority0(0),
        		priority1(1),
        		priority2(2),
        		priority3(3),
        		priority4(4),
        		priority5(5),
        		priority6(6),
        		priority7(7)
        }

        MAX-ACCESS  read-write
        STATUS  current
        DESCRIPTION
                      	"Priority value for service provider tag.
                      	0 is the lowest priority level and 7 is the highest."
        ::= { vlanStackPortEntry 3 }

        vlanStackTunnelPortTpid OBJECT-TYPE
        SYNTAX  INTEGER
        MAX-ACCESS  read-write
        STATUS  current
        DESCRIPTION
                      	"Tunnel Port TPID in hex format, e.g. 8100."
        ::= { vlanStackPortEntry 4 }

-- 		selectiveQinQTable
--        selectiveQinQTable OBJECT-TYPE
--        SYNTAX	SEQUENCE OF SelectiveQinQEntry
--        MAX-ACCESS  not-accessible
--        STATUS  current
--        DESCRIPTION
--                 	""
--        ::= { vlanStackSetup 4 }

--		selectiveQinQEntry OBJECT-TYPE
--        SYNTAX	SelectiveQinQEntry
--        MAX-ACCESS	not-accessible
--        STATUS	current
--        DESCRIPTION    	"An entry in selective qinq table"
--        INDEX          	{ selectiveQinQPort, selectiveQinQCvid, selectiveQinQGemvid}
--        ::= { selectiveQinQTable 1 }

--        SelectiveQinQEntry ::=
--           SEQUENCE {
--           	selectiveQinQName		DisplayString,
--        	selectiveQinQPort		INTEGER,
--        	selectiveQinQCvid		INTEGER,
--        	selectiveQinQGemvid	INTEGER,
--        	selectiveQinQSpvid		INTEGER,
--        	selectiveQinQPriority	INTEGER,
--        	selectiveQinQRowStatus	RowStatus
--           }

--        selectiveQinQName OBJECT-TYPE
--        SYNTAX  DisplayString
--        MAX-ACCESS  read-write
--        STATUS  current
--        DESCRIPTION
--                      	"The name of selective qinq entry"
--        ::= { selectiveQinQEntry 1 }

--        selectiveQinQPort OBJECT-TYPE
--        SYNTAX  INTEGER
--        MAX-ACCESS  read-only
--        STATUS  current
--        DESCRIPTION
--                     	"interface port id"
--        ::= { selectiveQinQEntry 2 }

--        selectiveQinQCvid OBJECT-TYPE
--        SYNTAX  INTEGER
--        MAX-ACCESS  read-only
--        STATUS  current
--        DESCRIPTION
--                     	"inner vid"
--        ::= { selectiveQinQEntry 3 }

--        selectiveQinQGemvid OBJECT-TYPE
--        SYNTAX  INTEGER
--        MAX-ACCESS  read-only
--        STATUS  current
--        DESCRIPTION
--                     	"gem vid"
--        ::= { selectiveQinQEntry 4 }

--        selectiveQinQSpvid OBJECT-TYPE
--        SYNTAX  INTEGER
--        MAX-ACCESS  read-write
--        STATUS  current
--        DESCRIPTION
--                     	"outer vid"
--        ::= { selectiveQinQEntry 5 }

--        selectiveQinQPriority OBJECT-TYPE
--        SYNTAX  INTEGER {
--        		priority0(0),
--        		priority1(1),
--        		priority2(2),
--        		priority3(3),
--        		priority4(4),
--        		priority5(5),
--        		priority6(6),
--        		priority7(7)
--        }

--        MAX-ACCESS  read-write
--        STATUS  current
--        DESCRIPTION
--                     	"priority"
--        ::= { selectiveQinQEntry 6 }


--        selectiveQinQRowStatus OBJECT-TYPE
--        SYNTAX  RowStatus
--        MAX-ACCESS  read-create
--        STATUS  current
--        DESCRIPTION
--                     	""
--        ::= { selectiveQinQEntry 7 }

--  8.dot1xSetup

--  	portAuthState
        portAuthState OBJECT-TYPE
        SYNTAX  EnabledStatus
        MAX-ACCESS  read-write
        STATUS  current
        DESCRIPTION
                      	"802.1x port authentication enabled/disabled for the switch."
        ::= { dot1xSetup 3 }

--  9.hardwareInfo

-- 		fanRpmTable

        fanRpmTable	OBJECT-TYPE
        SYNTAX	SEQUENCE OF FanRpmEntry
        MAX-ACCESS  not-accessible
        STATUS  current
        DESCRIPTION
                 	""
        ::= { hwMonitorInfo 1 }

		fanRpmEntry OBJECT-TYPE
        SYNTAX	FanRpmEntry
        MAX-ACCESS	not-accessible
        STATUS	current
        DESCRIPTION    	"An entry in fanRpmTable."
        INDEX          	{ fanRpmIndex }
        ::= { fanRpmTable 1 }

        FanRpmEntry ::=
           SEQUENCE {
        	fanRpmIndex	INTEGER,
            fanRpmName	DisplayString,
        	fanRpmCurValue	INTEGER,
        	fanRpmMaxValue	INTEGER,
        	fanRpmMinValue	INTEGER,
        	fanRpmLowThresh	INTEGER,
        	fanRpmDescr	DisplayString
           }

        fanRpmIndex OBJECT-TYPE
        SYNTAX  INTEGER
        MAX-ACCESS  read-only
        STATUS  current
        DESCRIPTION
                      	"Index of FAN."
        ::= { fanRpmEntry 1 }

        fanRpmName OBJECT-TYPE
        SYNTAX  DisplayString
        MAX-ACCESS  read-only
        STATUS  current
        DESCRIPTION
                      	"Name of Fan"
        ::= { fanRpmEntry 2 }

        fanRpmCurValue OBJECT-TYPE
        SYNTAX  INTEGER
        MAX-ACCESS  read-only
        STATUS  current
        DESCRIPTION
                      	"Current speed in Revolutions Per Minute (RPM) on the fan."
        ::= { fanRpmEntry 3 }

        fanRpmMaxValue OBJECT-TYPE
        SYNTAX  INTEGER
        MAX-ACCESS  read-only
        STATUS  current
        DESCRIPTION
                      	"Maximum speed measured in Revolutions Per Minute (RPM) on the fan."
        ::= { fanRpmEntry 4 }

        fanRpmMinValue OBJECT-TYPE
        SYNTAX  INTEGER
        MAX-ACCESS  read-only
        STATUS  current
        DESCRIPTION
                      	"Minimum speed measured in Revolutions Per Minute (RPM) on the fan."
        ::= { fanRpmEntry 5 }

        fanRpmLowThresh OBJECT-TYPE
        SYNTAX  INTEGER
        MAX-ACCESS  read-only
        STATUS  current
        DESCRIPTION
                      	"The minimum speed at which a normal fan should work."
        ::= { fanRpmEntry 6 }

        fanRpmDescr OBJECT-TYPE
        SYNTAX  DisplayString
        MAX-ACCESS  read-only
        STATUS  current
        DESCRIPTION
                      	"'Normal' indicates that this fan is functioning above the minimum speed.
                      	'Error' indicates that this fan is functioning below the minimum speed."
        ::= { fanRpmEntry 7 }

-- 		tempTable

        tempTable	OBJECT-TYPE
        SYNTAX	SEQUENCE OF TempEntry
        MAX-ACCESS  not-accessible
        STATUS  current
        DESCRIPTION
                 	""
        ::= { hwMonitorInfo 2 }

		tempEntry OBJECT-TYPE
        SYNTAX	TempEntry
        MAX-ACCESS	not-accessible
        STATUS	current
        DESCRIPTION    	"An entry in tempTable."
        INDEX          	{ tempIndex }
        ::= { tempTable 1 }

        TempEntry ::=
           SEQUENCE {
        	tempIndex       INTEGER,
        	tempName        DisplayString,
        	tempCurValue	INTEGER,
        	tempMaxValue	INTEGER,
        	tempMinValue	INTEGER,
        	tempHighThresh	INTEGER,
        	tempDescr       DisplayString
           }

        tempIndex OBJECT-TYPE
        SYNTAX  INTEGER
        MAX-ACCESS  read-only
        STATUS  current
        DESCRIPTION
                      	"Index of temperature unit."
        ::= { tempEntry 1 }

        tempName OBJECT-TYPE
        SYNTAX  DisplayString
        MAX-ACCESS  read-only
        STATUS  current
        DESCRIPTION
                      	"The name of temperature measured at this sensor."
        ::= { tempEntry 2 }

        tempCurValue OBJECT-TYPE
        SYNTAX  INTEGER
        MAX-ACCESS  read-only
        STATUS  current
        DESCRIPTION
                      	"The current temperature measured at this sensor."
        ::= { tempEntry 3 }

        tempMaxValue OBJECT-TYPE
        SYNTAX  INTEGER
        MAX-ACCESS  read-only
        STATUS  current
        DESCRIPTION
                      	"The maximum temperature measured at this sensor."
        ::= { tempEntry 4 }

        tempMinValue OBJECT-TYPE
        SYNTAX  INTEGER
        MAX-ACCESS  read-only
        STATUS  current
        DESCRIPTION
                      	"The minimum temperature measured at this sensor."
        ::= { tempEntry 5 }

        tempHighThresh OBJECT-TYPE
        SYNTAX  INTEGER
        MAX-ACCESS  read-only
        STATUS  current
        DESCRIPTION
                      	"The upper temperature limit at this sensor."
        ::= { tempEntry 6 }

        tempDescr OBJECT-TYPE
        SYNTAX  DisplayString
        MAX-ACCESS  read-only
        STATUS  current
        DESCRIPTION
                      	"'Normal' indicates temperatures below the threshold and 'Error' for those above."
        ::= { tempEntry 7 }

-- 		voltageTable

        voltageTable	OBJECT-TYPE
        SYNTAX	SEQUENCE OF VoltageEntry
        MAX-ACCESS  not-accessible
        STATUS  current
        DESCRIPTION
                 	""
        ::= { hwMonitorInfo 3 }

		voltageEntry OBJECT-TYPE
        SYNTAX	VoltageEntry
        MAX-ACCESS	not-accessible
        STATUS	current
        DESCRIPTION    	"An entry in voltageTable."
        INDEX          	{ voltageIndex }
        ::= { voltageTable 1 }

        VoltageEntry ::=
           SEQUENCE {
        	voltageIndex		INTEGER,
            voltageName         DisplayString,
        	voltageCurValue		INTEGER,
        	voltageMaxValue		INTEGER,
        	voltageMinValue		INTEGER,
        	voltageNominalValue	INTEGER,
        	voltageLowThresh	INTEGER,
        	voltageDescr		DisplayString
           }

        voltageIndex OBJECT-TYPE
        SYNTAX  INTEGER
        MAX-ACCESS  read-only
        STATUS  current
        DESCRIPTION
                      	"Index of voltage."
        ::= { voltageEntry 1 }

        voltageName OBJECT-TYPE
        SYNTAX  DisplayString
        MAX-ACCESS  read-only
        STATUS  current
        DESCRIPTION
                      	"Name of voltage."
        ::= { voltageEntry 2 }

        voltageCurValue OBJECT-TYPE
        SYNTAX  INTEGER
        MAX-ACCESS  read-only
        STATUS  current
        DESCRIPTION
                      	"The current voltage reading."
        ::= { voltageEntry 3 }

        voltageMaxValue OBJECT-TYPE
        SYNTAX  INTEGER
        MAX-ACCESS  read-only
        STATUS  current
        DESCRIPTION
                      	"The maximum voltage measured at this point."
        ::= { voltageEntry 4 }

        voltageMinValue OBJECT-TYPE
        SYNTAX  INTEGER
        MAX-ACCESS  read-only
        STATUS  current
        DESCRIPTION
                      	"The minimum voltage measured at this point."
        ::= { voltageEntry 5 }

        voltageNominalValue OBJECT-TYPE
        SYNTAX  INTEGER
        MAX-ACCESS  read-only
        STATUS  current
        DESCRIPTION
                      	"The normal voltage at wchich the switch work."
        ::= { voltageEntry 6 }

        voltageLowThresh OBJECT-TYPE
        SYNTAX  INTEGER
        MAX-ACCESS  read-only
        STATUS  current
        DESCRIPTION
                      	"The minimum voltage at which the switch should work."
        ::= { voltageEntry 7 }

        voltageDescr OBJECT-TYPE
        SYNTAX  DisplayString
        MAX-ACCESS  read-only
        STATUS  current
        DESCRIPTION
                      	"'Normal' indicates that the voltage is within an acceptable operating range
                      	at this point; otherwise 'Error' is displayed."
        ::= { voltageEntry 8 }

-- 	10.snmpSetup

        snmpGetCommunity OBJECT-TYPE
        SYNTAX  DisplayString
        MAX-ACCESS  read-write
        STATUS  current
        DESCRIPTION
                      	""
        ::= { snmpSetup 1 }

        snmpSetCommunity OBJECT-TYPE
        SYNTAX  DisplayString
        MAX-ACCESS  read-write
        STATUS  current
        DESCRIPTION
                      	""
        ::= { snmpSetup 2 }

        snmpTrapCommunity OBJECT-TYPE
        SYNTAX  DisplayString
        MAX-ACCESS  read-write
        STATUS  current
        DESCRIPTION
                      	""
        ::= { snmpSetup 3 }

--  	snmpTrapDestTable
        snmpTrapDestTable	OBJECT-TYPE
        SYNTAX	SEQUENCE OF SnmpTrapDestEntry
        MAX-ACCESS  not-accessible
        STATUS  current
        DESCRIPTION
                 	""
        ::= { snmpSetup 4 }

		snmpTrapDestEntry OBJECT-TYPE
        SYNTAX	SnmpTrapDestEntry
        MAX-ACCESS	not-accessible
        STATUS	current
        DESCRIPTION    	"An entry in snmpTrapDestTable."
        INDEX          	{ snmpTrapDestIP }
        ::= { snmpTrapDestTable 1 }

        SnmpTrapDestEntry ::=
           SEQUENCE {
        	snmpTrapDestIP			IpAddress,
        	snmpTrapDestRowStatus 	RowStatus,
        	snmpTrapDestPort		INTEGER,
        	snmpTrapVersion			INTEGER,
        	snmpTrapUserName		DisplayString
           }

        snmpTrapDestIP OBJECT-TYPE
        SYNTAX  IpAddress
        MAX-ACCESS  read-only
        STATUS  current
        DESCRIPTION
                      	"IP address of trap destination."
        ::= { snmpTrapDestEntry 1 }

        snmpTrapDestRowStatus OBJECT-TYPE
        SYNTAX  RowStatus
        MAX-ACCESS  read-create
        STATUS  current
        DESCRIPTION
                      	""
        ::= { snmpTrapDestEntry 2 }

        snmpTrapDestPort OBJECT-TYPE
        SYNTAX INTEGER
        MAX-ACCESS read-write
        STATUS  current
        DESCRIPTION
                      	"The UDP port of the trap destination."
        ::= { snmpTrapDestEntry 3 }

        snmpTrapVersion OBJECT-TYPE
        SYNTAX  INTEGER {
			v1(0),
			v2c(1),
			v3(2)
		}
        MAX-ACCESS read-write
        STATUS  current
        DESCRIPTION
                      	"The SNMP protocol version to send traps."
        ::= { snmpTrapDestEntry 4 }

        snmpTrapUserName OBJECT-TYPE
        SYNTAX DisplayString
        MAX-ACCESS read-write
        STATUS  current
        DESCRIPTION
                      	"The user name for sending SNMPv3 traps."
        ::= { snmpTrapDestEntry 5 }

        snmpVersion OBJECT-TYPE
		SYNTAX 	INTEGER {
			v2c(0),
			v3(1),
			v3v2c(2)
		}
        MAX-ACCESS  read-write
        STATUS  current
        DESCRIPTION
		"The SNMP version to be used. v3v2c means that the manager
		can get/set by SNMPv3 and can get by SNMPv2c."
        ::= { snmpSetup 5 }

-- 		snmpUserTable

		snmpUserTable OBJECT-TYPE
    	SYNTAX SEQUENCE OF SnmpUserEntry
    	MAX-ACCESS not-accessible
    	STATUS current
    	DESCRIPTION
                "A table that contains SNMPv3 user information."
    	::= { snmpSetup 6 }

    	snmpUserEntry OBJECT-TYPE
        SYNTAX SnmpUserEntry
        MAX-ACCESS not-accessible
        STATUS current
        DESCRIPTION
        	"An entry of snmpUserTable."
        INDEX { snmpUserName }
        ::= { snmpUserTable 1 }

   		SnmpUserEntry ::=
        SEQUENCE {
         	snmpUserName			DisplayString,
           	snmpUserSecurityLevel	INTEGER,
          	snmpUserAuthProtocol	INTEGER,
            snmpUserPrivProtocol	INTEGER,
			snmpUserGroup	        DisplayString
--         	snmpUserAuthPassword	DisplayString,
--	     	snmpUserPrivPassword	DisplayString,
--			snmpUserRowStatus	    RowStatus
       	}

		snmpUserName OBJECT-TYPE
		SYNTAX DisplayString
		MAX-ACCESS read-only
		STATUS current
		DESCRIPTION
			"The user name."
		::= { snmpUserEntry 1 }

		snmpUserSecurityLevel OBJECT-TYPE
		SYNTAX  INTEGER {
			noAuthNoPriv(0),
			authNoPriv(1),
			authPriv(2)
		}
		MAX-ACCESS read-write
		STATUS current
		DESCRIPTION
			"The level of security at which SNMP messages can be sent or
			with which operations are being processed."
		::= { snmpUserEntry 2 }

		snmpUserAuthProtocol OBJECT-TYPE
		SYNTAX  INTEGER {
			md5(0),
			sha(1)
		}
		MAX-ACCESS read-write
		STATUS current
		DESCRIPTION
			"The type of authentication protocol to be used."
		::= { snmpUserEntry 3 }

		snmpUserPrivProtocol OBJECT-TYPE
		SYNTAX 	INTEGER {
			des(0),
			aes(1)
		}
		MAX-ACCESS read-write
		STATUS current
		DESCRIPTION
			"The type of privacy protocol to be used."
		::= { snmpUserEntry 4 }

		snmpUserGroup OBJECT-TYPE
		SYNTAX DisplayString
		MAX-ACCESS read-only
		STATUS current
		DESCRIPTION
			"The group name which this user belongs to."
		::= { snmpUserEntry 5 }

--		snmpUserAuthPassword OBJECT-TYPE
--		SYNTAX DisplayString
--		MAX-ACCESS read-write
--		STATUS current
--		DESCRIPTION
--			"The authentication password."
--		::= { snmpUserEntry 6 }

--		snmpUserPrivPassword OBJECT-TYPE
--		SYNTAX DisplayString
--		MAX-ACCESS read-write
--		STATUS current
--		DESCRIPTION
--			"The privacy password."
--		::= { snmpUserEntry 7 }

--        snmpUserRowStatus OBJECT-TYPE
--        SYNTAX  RowStatus
--        MAX-ACCESS  read-create
--        STATUS  current
--        DESCRIPTION
--                      	""
--        ::= { snmpUserEntry 8 }

--  	snmpTrapGroupTable
        snmpTrapGroupTable	OBJECT-TYPE
        SYNTAX	SEQUENCE OF SnmpTrapGroupEntry
        MAX-ACCESS  not-accessible
        STATUS  current
        DESCRIPTION
                 	""
        ::= { snmpSetup 7 }

		snmpTrapGroupEntry OBJECT-TYPE
        SYNTAX	SnmpTrapGroupEntry
        MAX-ACCESS	not-accessible
        STATUS	current
        DESCRIPTION    	"An entry in snmpTrapGroupTable."
        INDEX          	{ snmpTrapDestIP }
        ::= { snmpTrapGroupTable 1 }

        SnmpTrapGroupEntry ::=
           SEQUENCE {
        	snmpTrapSystemGroup	 		BITS,
        	snmpTrapInterfaceGroup	 	BITS,
        	snmpTrapAAAGroup  			BITS,
        	snmpTrapIPGroup	 			BITS,
        	snmpTrapSwitchGroup	 		BITS
           }

        snmpTrapSystemGroup OBJECT-TYPE
        SYNTAX	BITS {
			coldStart(0),
			warmStart(1),
			fanSpeed(2),
			temperature(3),
			voltage(4),
			reset (5),
			timeSync (6),
			intrusionlock(7),
			externalAlarm(10),
			loopGuard(13)
		}
        MAX-ACCESS  read-write
        STATUS  current
        DESCRIPTION
                      	""
        ::= { snmpTrapGroupEntry 1 }

        snmpTrapInterfaceGroup OBJECT-TYPE
       	SYNTAX	BITS {
			linkup(0),
			linkdown(1),
			autonegotiation(2),
			lldp(3),
			transceiverDdm(4),
			ploam(6),
			omci(7),
			rogue(8),
			remoteOnt(9)
		}
        MAX-ACCESS  read-write
        STATUS  current
        DESCRIPTION
                      	""
        ::= { snmpTrapGroupEntry 2 }

        snmpTrapAAAGroup OBJECT-TYPE
       	SYNTAX	BITS {
			authentication(0),
			accounting(1)
		}
        MAX-ACCESS  read-write
        STATUS  current
        DESCRIPTION
                      	""
        ::= { snmpTrapGroupEntry 3 }

        snmpTrapIPGroup OBJECT-TYPE
       	SYNTAX	BITS {
			ping(0),
			traceroute(1)
		}
        MAX-ACCESS  read-write
        STATUS  current
        DESCRIPTION
                      	""
        ::= { snmpTrapGroupEntry 4 }

        snmpTrapSwitchGroup OBJECT-TYPE
       	SYNTAX	BITS {
			stp(0),
			mactable(1),
			rmon(2),
			cfm(3)
		}
        MAX-ACCESS  read-write
        STATUS  current
        DESCRIPTION
                      	""
        ::= { snmpTrapGroupEntry 5 }


--  11.dateTimeSetup

        dateTimeServerType OBJECT-TYPE
        SYNTAX  INTEGER {
        	none(1),
			daytime(2),
			time(3),
			ntp(4)
        }
        MAX-ACCESS  read-write
        STATUS  current
        DESCRIPTION
                      "The time service protocol."
        ::= { dateTimeSetup 1 }

        dateTimeServerIP OBJECT-TYPE
        SYNTAX  IpAddress
        MAX-ACCESS  read-write
        STATUS  current
        DESCRIPTION
                      "IP address of time server."
        ::= { dateTimeSetup 2 }

        dateTimeZone OBJECT-TYPE
        SYNTAX  INTEGER
        MAX-ACCESS  read-write
        STATUS  current
        DESCRIPTION
                      	"The time zone UTC
                      	       -1200 -1100 -1000 -900 -800 -700 -600 -500 -400
                      	       -330 -300 -200 -100 0 100 200 300 330 400 430 500 
                      	        530 600 630 700 800 900 930 1000 1030 1100 1200
                      	"				  
        ::= { dateTimeSetup 3 }

        dateTimeNewDateYear OBJECT-TYPE
        SYNTAX  INTEGER
        MAX-ACCESS  read-write
        STATUS  current
        DESCRIPTION
                      "The new date in year."
        ::= { dateTimeSetup 4 }

        dateTimeNewDateMonth OBJECT-TYPE
        SYNTAX  INTEGER
        MAX-ACCESS  read-write
        STATUS  current
        DESCRIPTION
                      "The new date in month."
        ::= { dateTimeSetup 5 }

        dateTimeNewDateDay OBJECT-TYPE
        SYNTAX  INTEGER
        MAX-ACCESS  read-write
        STATUS  current
        DESCRIPTION
                      "The new date in day."
        ::= { dateTimeSetup 6 }

        dateTimeNewTimeHour OBJECT-TYPE
        SYNTAX  INTEGER
        MAX-ACCESS  read-write
        STATUS  current
        DESCRIPTION
                      "The new time in hour."
        ::= { dateTimeSetup 7 }

        dateTimeNewTimeMinute OBJECT-TYPE
        SYNTAX  INTEGER
        MAX-ACCESS  read-write
        STATUS  current
        DESCRIPTION
                      "The new time in minute."
        ::= { dateTimeSetup 8 }

        dateTimeNewTimeSecond OBJECT-TYPE
        SYNTAX  INTEGER
        MAX-ACCESS  read-write
        STATUS  current
        DESCRIPTION
                      "The new time in second."
        ::= { dateTimeSetup 9 }

-- 		dateTimeDaylightSavingTimeSetup OBJECT-TYPE
		dateTimeDaylightSavingTimeSetup     	OBJECT IDENTIFIER ::= { dateTimeSetup 10 }

        daylightSavingTimeState OBJECT-TYPE
        SYNTAX  EnabledStatus
        MAX-ACCESS  read-write
        STATUS  current
        DESCRIPTION
                      "Daylight saving time service enabled/disabled for the switch."
        ::= { dateTimeDaylightSavingTimeSetup 1 }

        daylightSavingTimeStartDateWeek OBJECT-TYPE
        SYNTAX  INTEGER {
         	first(1),
         	second(2),
         	third(3),
         	fourth(4),
         	last(5)
        }
        MAX-ACCESS  read-write
        STATUS  current
        DESCRIPTION
                      "Daylight saving time service start week."
        ::= { dateTimeDaylightSavingTimeSetup 2 }

        daylightSavingTimeStartDateDay OBJECT-TYPE
        SYNTAX  INTEGER {
         		sunday(0),
         		monday(1),
         		tuesday(2),
         		wednesday(3),
         		thursday(4),
         		friday(5),
         		saturday(6)
        }
        MAX-ACCESS  read-write
        STATUS  current
        DESCRIPTION
                      "Daylight saving time service start day."
        ::= { dateTimeDaylightSavingTimeSetup 3 }

        daylightSavingTimeStartDateMonth OBJECT-TYPE
        SYNTAX  INTEGER {
         		january(1),
         		february(2),
         		march(3),
         		april(4),
         		may(5),
         		june(6),
         		july(7),
         		august(8),
         		september(9),
         		october(10),
         		november(11),
         		december(12)
        }
        MAX-ACCESS  read-write
        STATUS  current
        DESCRIPTION
                      "Daylight saving time service start month."
        ::= { dateTimeDaylightSavingTimeSetup 4 }

        daylightSavingTimeStartDateHour OBJECT-TYPE
        SYNTAX  INTEGER
        MAX-ACCESS  read-write
        STATUS  current
        DESCRIPTION
                      "Daylight saving time service start time."
        ::= { dateTimeDaylightSavingTimeSetup 5 }

        daylightSavingTimeEndDateWeek OBJECT-TYPE
        SYNTAX  INTEGER {
         		first(1),
         		second(2),
         		third(3),
         		fourth(4),
         		last(5)
        }
        MAX-ACCESS  read-write
        STATUS  current
        DESCRIPTION
                      "Daylight saving time service end week."
        ::= { dateTimeDaylightSavingTimeSetup 6 }

        daylightSavingTimeEndDateDay OBJECT-TYPE
        SYNTAX  INTEGER {
         		sunday(0),
         		monday(1),
         		tuesday(2),
         		wednesday(3),
         		thursday(4),
         		friday(5),
         		saturday(6)
        }
        MAX-ACCESS  read-write
        STATUS  current
        DESCRIPTION
                      "Daylight saving time service end day."
        ::= { dateTimeDaylightSavingTimeSetup 7 }

        daylightSavingTimeEndDateMonth OBJECT-TYPE
        SYNTAX  INTEGER {
         		january(1),
         		february(2),
         		march(3),
         		april(4),
         		may(5),
         		june(6),
         		july(7),
         		august(8),
         		september(9),
         		october(10),
         		november(11),
         		december(12)
        }
        MAX-ACCESS  read-write
        STATUS  current
        DESCRIPTION
                      "Daylight saving time service end month."
        ::= { dateTimeDaylightSavingTimeSetup 8 }

        daylightSavingTimeEndDateHour OBJECT-TYPE
        SYNTAX  INTEGER
        MAX-ACCESS  read-write
        STATUS  current
        DESCRIPTION
                      "Daylight saving time service end time."
        ::= { dateTimeDaylightSavingTimeSetup 9 }

--  12.sysMgmt

        sysMgmtConfigSave OBJECT-TYPE
        SYNTAX  INTEGER {
         		config1(1),
         		config2(2)
        }
        MAX-ACCESS  read-write
        STATUS  current
        DESCRIPTION
                      "If setting value is given, the variable write index will be set and running-config will be written to the assigned configuration file.
                      If not, running-config will be written to the booting one.
                      Note: This action can access all configuration includes user account and AA configuration."
        ::= { sysMgmt 1 }

        sysMgmtBootupConfig OBJECT-TYPE
        SYNTAX  INTEGER {
         		config1(1),
         		config2(2)
        }
        MAX-ACCESS  read-write
        STATUS  current
        DESCRIPTION
                      "The setting value (read index) will be written into non-volatile memory.
                      While rebooting, the variable write index is equal to read index initially.
                      You can change the value of write index by CLI / MIB."
        ::= { sysMgmt 2 }

        sysMgmtReboot OBJECT-TYPE
        SYNTAX  INTEGER {
        		nothing(0),
        		reboot(1)
        }
        MAX-ACCESS  read-write
        STATUS  current
        DESCRIPTION
                      "Reboot switch from SNMP. 1:Reboot, 0:Nothing"
        ::= { sysMgmt 3 }

		sysMgmtDefaultConfig OBJECT-TYPE
        SYNTAX  INTEGER {
        		nothing(0),
        		resetToDefault(1),
        		resetToDefaultWithoutIp(2)
        }
        MAX-ACCESS  read-write
        STATUS  current
        DESCRIPTION
                      "Erase running config and reset to default.
                       Note: This action can access all configuration includes user account and AA configuration."
        ::= { sysMgmt 4 }

		sysMgmtLastActionStatus OBJECT-TYPE
        SYNTAX  INTEGER {
        		none(0),
        		success(1),
        		fail(2)
        }
        MAX-ACCESS  read-only
        STATUS  current
        DESCRIPTION
                      "Display status of last mgmt action."
        ::= { sysMgmt 5 }

		sysMgmtSystemStatus OBJECT-TYPE
		SYNTAX	BITS {
			sysAlarmDetected(0),
			sysTemperatureError(1),
			sysFanRPMError(2),
			sysVoltageRangeError(3)
		}
       	MAX-ACCESS  read-only
        STATUS  current
        DESCRIPTION
		"This variable indicates the status of the system.
 		The sysMgmtAlarmStatus is a bit map represented
 		a sum, therefore, it can represent multiple defects
 		simultaneously. The sysNoDefect should be set if and only if
 		no other flag is set.

	 	The various bit positions are:
			0   sysAlarmDetected
			1   sysTemperatureError
			2   sysFanRPMError
			3   sysVoltageRangeError"
        ::= { sysMgmt 6 }

		sysMgmtCPUUsage OBJECT-TYPE
		SYNTAX  INTEGER
		MAX-ACCESS  read-only
		STATUS  current
		DESCRIPTION
			"Show device CPU load in %, it's the snapshot of CPU load when
			getting the values."
		::= { sysMgmt 7 }

		sysMgmtBootupImage OBJECT-TYPE
        SYNTAX  INTEGER {
         		image1(1),
         		image2(2)
        }
        MAX-ACCESS  read-write
        STATUS  current
        DESCRIPTION
                      "The setting value (read index) will be written into non-volatile memory.
                      When rebooting, the selected image will be used.
                      You can change the value of write index by CLI / MIB."
        ::= { sysMgmt 8 }

		sysMgmtCounterReset OBJECT-TYPE
        SYNTAX  INTEGER {
         		enable(1),
         		disable(2)
        }
        MAX-ACCESS  read-write
        STATUS  current
        DESCRIPTION
                      "Reset all port counters."
        ::= { sysMgmt 9 }

-- 		Tftp service
        sysMgmtTftpServiceSetup OBJECT IDENTIFIER ::= { sysMgmt 10 }

        sysMgmtTftpServerIp OBJECT-TYPE
        SYNTAX  IpAddress
        MAX-ACCESS  read-write
        STATUS  current
        DESCRIPTION
                      	" IP address of TFTP server"
        ::= { sysMgmtTftpServiceSetup 1 }

        sysMgmtTftpRemoteFileName OBJECT-TYPE
        SYNTAX  DisplayString
        MAX-ACCESS  read-write
        STATUS  current
        DESCRIPTION
                      	"The file name that you want to backup to or restore from TFTP server"
        ::= { sysMgmtTftpServiceSetup 2 }

        sysMgmtTftpConfigIndex OBJECT-TYPE
        SYNTAX  INTEGER {
        	    config1(1),
        	    config2(2)
        }
        MAX-ACCESS  read-write
        STATUS  current
        DESCRIPTION
                      	"Index of system configuration which you want to restore."
        ::= { sysMgmtTftpServiceSetup 3 }

        sysMgmtTftpAction OBJECT-TYPE
        SYNTAX  INTEGER {
        		none(0),
         		backupConfig(1),
         		restoreConfig(2),
				mergeConfig(3)
        }
        MAX-ACCESS  read-write
        STATUS  current
        DESCRIPTION
                      	" Action of tftp service. 1: Backup running-config to tftp server, 2: Restore config from tftp server, 3: Merge config from tftp server.
						Note: This action can access all configuration includes user account and AA configuration."
        ::= { sysMgmtTftpServiceSetup 4 }


		sysMgmtTftpActionStatus OBJECT-TYPE
        SYNTAX  INTEGER {
        		none(0),
        		success(1),
        		fail(2),
        		underAction(3)
        }
        MAX-ACCESS  read-only
        STATUS  current
        DESCRIPTION
                      "Display status of mgmt action."
        ::= { sysMgmtTftpServiceSetup 5 }

    sysMgmtTftpActionPrivilege13 OBJECT-TYPE
        SYNTAX  INTEGER {
        		none(0),
         		backupConfig(1),
				restoreConfig(2),
				mergeConfig(3)
        }
        MAX-ACCESS  read-write
        STATUS  current
		DESCRIPTION
                      	" Action of tftp service. 1: Backup running-config to tftp server, 2: Restore config from tftp server, 3: Merge config from tftp server.
						  Note: This action can access configuration with privilege 13."
        ::= { sysMgmtTftpServiceSetup 113 }

--  sysLoginSetup
	sysLoginSetup     	OBJECT IDENTIFIER ::= { sysMgmt 11 }

	loginLimitMaxNumberOfUser OBJECT-TYPE
        SYNTAX  INTEGER
        MAX-ACCESS  read-only
        STATUS  current
        DESCRIPTION
                      	""
        ::= { sysLoginSetup 1 }

        sysLoginSetupTable	OBJECT-TYPE
        SYNTAX	SEQUENCE OF SysLoginSetupEntry
        MAX-ACCESS  not-accessible
        STATUS  current
        DESCRIPTION
                 	""
        ::= { sysLoginSetup 2 }

	sysLoginSetupEntry OBJECT-TYPE
        SYNTAX	SysLoginSetupEntry
        MAX-ACCESS	not-accessible
        STATUS	current
        DESCRIPTION    	"An entry in LoginLimitMaxNumberOfUser."
        INDEX          	{ sysLoginName }
        ::= { sysLoginSetupTable 1 }

        SysLoginSetupEntry ::=
	SEQUENCE {
        	sysLoginName		DisplayString,
        	sysLoginPassword	DisplayString,
        	sysLoginPrivilege	INTEGER,
        	sysLoginRowStatus	RowStatus
        }

        sysLoginName OBJECT-TYPE
        SYNTAX  DisplayString
        MAX-ACCESS  read-only
        STATUS  current
        DESCRIPTION
                      	""
        ::= { sysLoginSetupEntry 1 }

        sysLoginPassword OBJECT-TYPE
        SYNTAX  DisplayString
        MAX-ACCESS  read-write
        STATUS  current
        DESCRIPTION
	""
        ::= { sysLoginSetupEntry 2 }

        sysLoginPrivilege OBJECT-TYPE
        SYNTAX  INTEGER
        MAX-ACCESS  read-write
        STATUS  current
        DESCRIPTION
        ""
        ::= { sysLoginSetupEntry 3 }


        sysLoginRowStatus OBJECT-TYPE
        SYNTAX  RowStatus
        MAX-ACCESS  read-create
        STATUS  current
        DESCRIPTION
                      	""
        ::= { sysLoginSetupEntry 4 }

	 sysMgmtCPUUsageThreshold OBJECT-TYPE
        SYNTAX  INTEGER (0..100)
	 MAX-ACCESS  read-write
	 STATUS  current
	 DESCRIPTION
		" Set CPU Threshold value"
	 ::= { sysMgmt 12 }

	 sysMgmtMemoryUsageThreshold OBJECT-TYPE
        SYNTAX  INTEGER (0..100)
	 MAX-ACCESS  read-write
	 STATUS  current
	 DESCRIPTION
		" Set memory usage Threshold value"
	 ::= { sysMgmt 13 }

        sysMgmtUartLogoutTime OBJECT-TYPE
        SYNTAX  INTEGER
        MAX-ACCESS  read-write
        STATUS  current
        DESCRIPTION
                      	"This entry is the timer of uart logout. and rnage is 1 ~ 60 minutes"
        ::= { sysMgmt 14 }

-- sysMgmt action with Privilege
        sysMgmtConfigSavePrivilege13 OBJECT-TYPE
        SYNTAX  INTEGER {
         		config1(1),
         		config2(2)
        }
        MAX-ACCESS  read-write
        STATUS  current
        DESCRIPTION
                      "If setting value is given, the variable write index will be set and running-config will be written to the assigned configuration file.
                      If not, running-config will be written to the booting one.
                      Note: This action can access configuration with privilege 13."
        ::= { sysMgmt 113 }

		sysMgmtDefaultConfigPrivilege13 OBJECT-TYPE
        SYNTAX  INTEGER {
        		nothing(0),
        		resetToDefault(1)
        }
        MAX-ACCESS  read-write
        STATUS  current
        DESCRIPTION
                      "Erase running config and reset to default.
					  Note: This action can access configuration with privilege 13."
        ::= { sysMgmt 213 }

--  13.layer2Setup

        vlanTypeSetup OBJECT-TYPE
        SYNTAX  INTEGER {
--         		dot1Q(1),
         		dot1Q(1)
--         		portBased(2)
        }
        MAX-ACCESS  read-write
        STATUS  current
        DESCRIPTION
                      ""
        ::= { layer2Setup 1 }

        igmpSnoopingStateSetup OBJECT-TYPE
        SYNTAX  INTEGER {
         		disabled(1),
         		enableIgmpSnooping(2),
         		enableIgmpProxying(3)
        }
        MAX-ACCESS  read-write
        STATUS  current
        DESCRIPTION
                      ""
        ::= { layer2Setup 2 }

        tagVlanPortIsolationState OBJECT-TYPE
        SYNTAX  EnabledStatus
        MAX-ACCESS  read-write
        STATUS  current
        DESCRIPTION
                      ""
        ::= { layer2Setup 3 }

        stpState OBJECT-TYPE
        SYNTAX  EnabledStatus
        MAX-ACCESS  read-write
        STATUS  current
        DESCRIPTION
                      ""
        ::= { layer2Setup 4 }

--        igmpFilteringStateSetup OBJECT-TYPE
--        SYNTAX  EnabledStatus
--        MAX-ACCESS  read-write
--        STATUS  current
--        DESCRIPTION
--                      ""
--        ::= { layer2Setup 5 }

        unknownMulticastFrameForwarding OBJECT-TYPE
        SYNTAX  INTEGER {
         	flooding(1),
         	drop(2)
        }
        MAX-ACCESS  read-write
        STATUS  current
        DESCRIPTION
                      ""
        ::= { layer2Setup 6 }

        multicastGrpHostTimeout OBJECT-TYPE
        SYNTAX  INTEGER
        MAX-ACCESS  read-write
        STATUS  current
        DESCRIPTION
                      "Specify host timeout for all multicast groups when the specific port is in auto mode."
        ::= { layer2Setup 7 }

        multicastLeaveTimeout OBJECT-TYPE
        SYNTAX  INTEGER
        MAX-ACCESS  read-write
        STATUS  current
        DESCRIPTION
                      "Specify leave timeout for all multicast groups."
        ::= { layer2Setup 8 }

        reservedMulticastFrameForwarding OBJECT-TYPE
        SYNTAX  INTEGER {
         	flooding(1),
         	drop(2)
        }
        MAX-ACCESS  read-write
        STATUS  current
        DESCRIPTION
                      ""
        ::= { layer2Setup 9 }

        igmpsnp8021pPriority OBJECT-TYPE
        SYNTAX  INTEGER
        MAX-ACCESS  read-write
        STATUS  current
        DESCRIPTION
                      "Set the 802.1p priority of control messages for igmp-snooping(0~8, 8-No Change)"
        ::= { layer2Setup 10 }

--      igmpsnpVlanMode OBJECT-TYPE
--      SYNTAX  INTEGER {
--          auto(1),
--          fixed(2)
--      }
--      MAX-ACCESS  read-write
--      STATUS  current
--      DESCRIPTION
--                    ""
--      ::= { layer2Setup 11 }


        stpMode OBJECT-TYPE
        SYNTAX  INTEGER {
         	rstp(1),
--         	mrstp(2),
         	mstp (2)
        }
        MAX-ACCESS  read-write
        STATUS  current
        DESCRIPTION
                      ""
        ::= { layer2Setup 12 }

--  13.13 igmpsnpVlanTable
--      igmpsnpVlanTable    OBJECT-TYPE
--      SYNTAX  SEQUENCE OF IgmpsnpVlanEntry
--      MAX-ACCESS  not-accessible
--      STATUS  current
--      DESCRIPTION
--                  ""
--      ::= { layer2Setup 13 }

--      igmpsnpVlanEntry OBJECT-TYPE
--      SYNTAX  IgmpsnpVlanEntry
--      MAX-ACCESS  not-accessible
--      STATUS  current
--      DESCRIPTION     "An entry in IgmpsnpVlanTable."
--      INDEX           { igmpsnpVid }
--      ::= { igmpsnpVlanTable 1 }

--      IgmpsnpVlanEntry ::=
--         SEQUENCE {
--          igmpsnpVid            INTEGER,
--          igmpsnpVlanName       DisplayString,
--          igmpsnpVlanRowStatus  RowStatus
--         }

--      igmpsnpVid OBJECT-TYPE
--      SYNTAX  INTEGER
--      MAX-ACCESS  read-only
--      STATUS  current
--      DESCRIPTION
--                      ""
--      ::= { igmpsnpVlanEntry 1 }

--      igmpsnpVlanName OBJECT-TYPE
--      SYNTAX  DisplayString
--      MAX-ACCESS  read-write
--      STATUS  current
--      DESCRIPTION
--                      ""
--      ::= { igmpsnpVlanEntry 2 }

--      igmpsnpVlanRowStatus OBJECT-TYPE
--      SYNTAX  RowStatus
--      MAX-ACCESS  read-create
--      STATUS  current
--      DESCRIPTION
--                      ""
--      ::= {  igmpsnpVlanEntry 3 }

--		igmpsnpQuerierMode OBJECT-TYPE
--        SYNTAX  EnabledStatus
--        MAX-ACCESS  read-write
--        STATUS  current
--        DESCRIPTION
--                      ""
--        ::= { layer2Setup 14 }

        ethernetCfmStateSetup OBJECT-TYPE
        SYNTAX  EnabledStatus
        MAX-ACCESS  read-write
        STATUS  current
        DESCRIPTION
                      ""
        ::= { layer2Setup 15 }

        lldpStateSetup OBJECT-TYPE
        SYNTAX  EnabledStatus
        MAX-ACCESS  read-write
        STATUS  current
        DESCRIPTION
                      ""
        ::= { layer2Setup 16 }

--    	igmpSnpReportProxySetup OBJECT-TYPE
--        SYNTAX  EnabledStatus
--        MAX-ACCESS  read-write
--        STATUS  current
--        DESCRIPTION
--                      "IGMP Snooping report-proxy mode"
--        ::= { layer2Setup 17 }

       	smartIsolationState OBJECT-TYPE
        SYNTAX  EnabledStatus
        MAX-ACCESS  read-write
        STATUS  current
        DESCRIPTION
                      ""
        ::= { layer2Setup 18 }

        mgmdMLDsupport OBJECT-TYPE
        SYNTAX  EnabledStatus
        MAX-ACCESS  read-write
        STATUS  current
        DESCRIPTION
        "Enable MLD / Disable MLD"
        ::= { layer2Setup 19 }

        mgmdv3mode OBJECT-TYPE
        SYNTAX  EnabledStatus
        MAX-ACCESS  read-write
        STATUS  current
        DESCRIPTION
        "Enable MLDv2 and IGMPv3 mode / Disable MLDv2 and IGMPv3 mode"
        ::= { layer2Setup 20 }

        mgmdReportTag OBJECT-TYPE
        SYNTAX INTEGER {
         	mvlan (0),
         	aniVlan (1)
        }
        MAX-ACCESS  read-write
        STATUS  current
        DESCRIPTION
        "Configure the Report tag"
        ::= { layer2Setup 21 }

		mgmdIgmpProxyWorkingIP OBJECT-TYPE
        SYNTAX IpAddress
        MAX-ACCESS  read-write
        STATUS  current
        DESCRIPTION
        "Configure the IGMP Proxy Working IP"
        ::= { layer2Setup 22 }

        mgmdQueryTag OBJECT-TYPE
        SYNTAX INTEGER {
         	mvlan (0),
         	aniVlan (1)
        }
        MAX-ACCESS  read-write
        STATUS  current
        DESCRIPTION
        "Configure the Query tag"
        ::= { layer2Setup 23 }

        dsMeterMacroMode OBJECT-TYPE
        SYNTAX INTEGER {
         	pir (0),
         	cir (1)
        }
        MAX-ACCESS  read-write
        STATUS  current
        DESCRIPTION
        "Configure downstream meter macro mode
        pir: micro flow pir can take macro cir and pir
        cir: micro flow cir take macro cir first
             micro flow pir can take macro pir only"
        ::= { layer2Setup 24 }

        dsMeterShaperMode OBJECT-TYPE
        SYNTAX  EnabledStatus
        MAX-ACCESS  read-write
        STATUS  current
        DESCRIPTION
        "Configure downstream meter shaper mode
		The setting will be applied to next bootup
		Note: Need write memory"
        ::= { layer2Setup 25 }

        dsMeterRunningShaperMode OBJECT-TYPE
        SYNTAX  EnabledStatus
        MAX-ACCESS  read-only
        STATUS  current
        DESCRIPTION
        "Current running downstream meter shaper mode"
        ::= { layer2Setup 26 }

--  14.ipSetup

        dnsIpAddress OBJECT-TYPE
        SYNTAX  IpAddress
        MAX-ACCESS  read-write
        STATUS  current
        DESCRIPTION
                      ""
        ::= { ipSetup 1 }

        defaultMgmt OBJECT-TYPE
        SYNTAX  INTEGER {
        	inBand(0),
        	outOfBand(1)
        }
        MAX-ACCESS  read-write
        STATUS  current
        DESCRIPTION
                      ""
        ::= { ipSetup 2 }

        defaultGateway OBJECT-TYPE
        SYNTAX  IpAddress
        MAX-ACCESS  read-write
        STATUS  current
        DESCRIPTION
                      	""
        ::= { ipSetup 3 }


		outOfBandIpSetup     	OBJECT IDENTIFIER ::= { ipSetup 4 }

        outOfBandIp OBJECT-TYPE
        SYNTAX  IpAddress
        MAX-ACCESS  read-write
        STATUS  current
        DESCRIPTION
                      ""
        ::= { outOfBandIpSetup 1 }

        outOfBandSubnetMask OBJECT-TYPE
        SYNTAX  IpAddress
        MAX-ACCESS  read-write
        STATUS  current
        DESCRIPTION
                      ""
        ::= { outOfBandIpSetup 2 }

        outOfBandGateway OBJECT-TYPE
        SYNTAX  IpAddress
        MAX-ACCESS  read-write
        STATUS  current
        DESCRIPTION
                      ""
        ::= { outOfBandIpSetup 3 }

--  	inbandIpTable
        maxNumOfInbandIp OBJECT-TYPE
        SYNTAX  INTEGER
        MAX-ACCESS  read-only
        STATUS  current
        DESCRIPTION
                      	""
        ::= { ipSetup 5 }

        inbandIpTable	OBJECT-TYPE
        SYNTAX	SEQUENCE OF InbandIpEntry
        MAX-ACCESS  not-accessible
        STATUS  current
        DESCRIPTION
                 	""
        ::= { ipSetup 6 }

		inbandIpEntry OBJECT-TYPE
        SYNTAX	InbandIpEntry
        MAX-ACCESS	not-accessible
        STATUS	current
        DESCRIPTION    	"An entry in inbandIpTable."
        INDEX          	{ inbandEntryIp, inbandEntrySubnetMask }
        ::= { inbandIpTable 1 }

        InbandIpEntry ::=
		SEQUENCE {
        	inbandEntryIp		IpAddress,
        	inbandEntrySubnetMask	IpAddress,
        	inbandEntryVid		INTEGER,
        	inbandEntryRowStatus	RowStatus
        }

        inbandEntryIp OBJECT-TYPE
        SYNTAX  IpAddress
        MAX-ACCESS  read-write
        STATUS  current
        DESCRIPTION
                      	""
        ::= { inbandIpEntry 1 }

        inbandEntrySubnetMask OBJECT-TYPE
        SYNTAX  IpAddress
        MAX-ACCESS  read-write
        STATUS  current
        DESCRIPTION
                      	""
        ::= { inbandIpEntry 2 }


        inbandEntryVid OBJECT-TYPE
        SYNTAX  INTEGER
        MAX-ACCESS  read-write
        STATUS  current
        DESCRIPTION
                      	""
        ::= { inbandIpEntry 3 }

        inbandEntryRowStatus OBJECT-TYPE
        SYNTAX  RowStatus
        MAX-ACCESS  read-create
        STATUS  current
        DESCRIPTION
                      	""
        ::= { inbandIpEntry 4 }

--  15.filterSetup

--  	filterTable
       	filterTable	OBJECT-TYPE
        SYNTAX	SEQUENCE OF FilterEntry
        MAX-ACCESS  not-accessible
        STATUS  current
        DESCRIPTION
                 	""
        ::= { filterSetup 1 }

		filterEntry OBJECT-TYPE
        SYNTAX	FilterEntry
        MAX-ACCESS	not-accessible
        STATUS	current
        DESCRIPTION    	"An entry in filterTable."
        INDEX          	{ filterMacAddr, filterVid }
        ::= { filterTable 1 }

        FilterEntry ::=
           SEQUENCE {
         	filterName		DisplayString,
        	filterActionState	INTEGER,
        	filterMacAddr		MacAddress,
        	filterVid		INTEGER,
        	filterRowStatus		RowStatus
           }

        filterName OBJECT-TYPE
        SYNTAX  DisplayString
        MAX-ACCESS  read-write
        STATUS  current
        DESCRIPTION
                      	""
        ::= { filterEntry 1 }

        filterActionState OBJECT-TYPE
        SYNTAX  INTEGER {
			discardSource(1),
			discardDestination(2),
			both(3)
		}
        MAX-ACCESS  read-write
        STATUS  current
        DESCRIPTION
                      	""
        ::= { filterEntry 2 }

        filterMacAddr OBJECT-TYPE
        SYNTAX  MacAddress
        MAX-ACCESS  not-accessible
        STATUS  current
        DESCRIPTION
                      	""
        ::= { filterEntry 3 }

   		filterVid OBJECT-TYPE
        SYNTAX  INTEGER
        MAX-ACCESS  not-accessible
        STATUS  current
        DESCRIPTION
                      	""
        ::= { filterEntry 4 }

   		filterRowStatus OBJECT-TYPE
        SYNTAX  RowStatus
        MAX-ACCESS  read-create
        STATUS  current
        DESCRIPTION
                      	""
        ::= { filterEntry 5 }

--  16.mirrorSetup

--  	mirrorState
        mirrorState OBJECT-TYPE
        SYNTAX  EnabledStatus
        MAX-ACCESS  read-write
        STATUS  current
        DESCRIPTION
                      	""
        ::= { mirrorSetup 1 }

        mirrorMonitorPort OBJECT-TYPE
        SYNTAX  INTEGER
        MAX-ACCESS  read-write
        STATUS  current
        DESCRIPTION
                      	""
        ::= { mirrorSetup 2 }

-- 		mirrorTable

        mirrorTable OBJECT-TYPE
        SYNTAX	SEQUENCE OF MirrorEntry
        MAX-ACCESS  not-accessible
        STATUS  current
        DESCRIPTION
                 	""
        ::= { mirrorSetup 3 }

		mirrorEntry OBJECT-TYPE
        SYNTAX	MirrorEntry
        MAX-ACCESS	not-accessible
        STATUS	current
        DESCRIPTION    	"An entry in mirrorTable."
        INDEX          	{ dot1dBasePort }
        ::= { mirrorTable 1 }

        MirrorEntry ::=
           SEQUENCE {
        	mirrorMirroredState	EnabledStatus,
        	mirrorDirection		INTEGER
           }

        mirrorMirroredState OBJECT-TYPE
        SYNTAX  EnabledStatus
        MAX-ACCESS  read-write
        STATUS  current
        DESCRIPTION
                      	""
        ::= { mirrorEntry 1 }

        mirrorDirection OBJECT-TYPE
        SYNTAX  INTEGER {
        	ingress(0),
        	egress(1),
        	both(2)
        }
        MAX-ACCESS  read-write
        STATUS  current
        DESCRIPTION
                      	""
        ::= { mirrorEntry 2 }

        mirrorVlan OBJECT-TYPE
        SYNTAX  INTEGER (0..4094)
        MAX-ACCESS  read-write
        STATUS  current
        DESCRIPTION
                      	"vlan 0 = vlan all"
        ::= { mirrorSetup 4 }

--  17.aggrSetup

        aggrState OBJECT-TYPE
        SYNTAX  EnabledStatus
        MAX-ACCESS  read-write
        STATUS  current
        DESCRIPTION
                      	"Link aggregation enabled/disabled."
        ::= { aggrSetup 1 }

        aggrSystemPriority OBJECT-TYPE
        SYNTAX  INTEGER (1..65535)
        MAX-ACCESS  read-write
        STATUS  current
        DESCRIPTION
                      	"Set the priority of an active port using LACP."
        ::= { aggrSetup 2 }

-- 		aggrGroupTable

        aggrGroupTable OBJECT-TYPE
        SYNTAX	SEQUENCE OF AggrGroupEntry
        MAX-ACCESS  not-accessible
        STATUS  current
        DESCRIPTION
                 	""
        ::= { aggrSetup 3 }

		aggrGroupEntry OBJECT-TYPE
        SYNTAX	AggrGroupEntry
        MAX-ACCESS	not-accessible
        STATUS	current
        DESCRIPTION    	"An entry in aggrGroupTable."
        INDEX          	{ aggrGroupIndex }
        ::= { aggrGroupTable 1 }

        AggrGroupEntry ::=
           SEQUENCE {
        	aggrGroupIndex			INTEGER,
        	aggrGroupState			EnabledStatus,
        	aggrGroupDynamicState	EnabledStatus,
        	aggrGroupCriteria    	INTEGER
           }

        aggrGroupIndex OBJECT-TYPE
        SYNTAX  INTEGER
        MAX-ACCESS  read-only
        STATUS  current
        DESCRIPTION
                      	"Index of the trunk group."
        ::= { aggrGroupEntry 1 }

        aggrGroupState OBJECT-TYPE
        SYNTAX  EnabledStatus
        MAX-ACCESS  read-write
        STATUS  current
        DESCRIPTION
                     	"Enable/Disable trunk group."
        ::= { aggrGroupEntry 2 }

        aggrGroupDynamicState OBJECT-TYPE
        SYNTAX  EnabledStatus
        MAX-ACCESS  read-write
        STATUS  current
        DESCRIPTION
                     	"Enable/Disable LACP in the specified trunk group."
        ::= { aggrGroupEntry 3 }

        aggrGroupCriteria OBJECT-TYPE
        SYNTAX  INTEGER  {
        srcMac (1),
        dstMac (2),
        srcDstMac (3),
        srcIp  (4),
        dstIp  (5),
        srcDstIp (6)
        }
        MAX-ACCESS  read-write
        STATUS  current
        DESCRIPTION
                  	"Set the traffic distribution type used for the specified trunk group."
        ::= { aggrGroupEntry 4 }


-- 		aggrPortTable

        aggrPortTable OBJECT-TYPE
        SYNTAX	SEQUENCE OF AggrPortEntry
        MAX-ACCESS  not-accessible
        STATUS  current
        DESCRIPTION
                 	""
        ::= { aggrSetup 4 }

		aggrPortEntry OBJECT-TYPE
        SYNTAX	AggrPortEntry
        MAX-ACCESS	not-accessible
        STATUS	current
        DESCRIPTION    	"An entry in aggrPortTable."
        INDEX          	{ dot1dBasePort }
        ::= { aggrPortTable 1 }

        AggrPortEntry ::=
           SEQUENCE {
        	aggrPortGroup			INTEGER,
        	aggrPortDynamicStateTimeout	INTEGER
           }

        aggrPortGroup OBJECT-TYPE
        SYNTAX  INTEGER {
        	none(0),
        	t1(1),
        	t2(2)
        }
        MAX-ACCESS  read-write
        STATUS  current
        DESCRIPTION
                      	"Display the port belongs to the specified trunk group."
        ::= { aggrPortEntry 1 }

        aggrPortDynamicStateTimeout OBJECT-TYPE
        SYNTAX  INTEGER (1 | 30)
        MAX-ACCESS  read-write
        STATUS  current
        DESCRIPTION
                     	"Define LACP timeout period (in seconds) for the specified port(s)."
        ::= { aggrPortEntry 2 }


-- 		aggrStatusTable

        aggrStatusTable OBJECT-TYPE
        SYNTAX	SEQUENCE OF AggrStatusEntry
        MAX-ACCESS  not-accessible
        STATUS  current
        DESCRIPTION
                 	""
        ::= { aggrSetup 5 }

		aggrStatusEntry OBJECT-TYPE
        SYNTAX	AggrStatusEntry
        MAX-ACCESS	not-accessible
        STATUS	current
        DESCRIPTION    	"An entry in aggrStatusTable."
        INDEX          	{ aggrGroupIndex }
        ::= { aggrStatusTable 1 }

        AggrStatusEntry ::=
           SEQUENCE {
        	aggrStatusActorID			DisplayString,
        	aggrStatusPartnerID		DisplayString,
        	aggrStatusLinkPorts		PortList,
        	aggrStatusSyncPorts		PortList
           }

        aggrStatusActorID OBJECT-TYPE
        SYNTAX  DisplayString
        MAX-ACCESS  read-only
        STATUS  current
        DESCRIPTION
                      	"LACP Actor ID. 0000,00-00-00-00-00-00,0000,00,0000 (priority,mac,key,00,0000)"
        ::= { aggrStatusEntry 1 }

        aggrStatusPartnerID OBJECT-TYPE
        SYNTAX  DisplayString
        MAX-ACCESS  read-only
        STATUS  current
        DESCRIPTION
                      	"LACP Partner ID. 0000,00-00-00-00-00-00,0000,00,0000 (priority,mac,key,00,0000)"
        ::= { aggrStatusEntry 2 }

        aggrStatusLinkPorts OBJECT-TYPE
        SYNTAX  PortList
        MAX-ACCESS  read-only
        STATUS  current
        DESCRIPTION
                      	"Link Ports Port List"
        ::= { aggrStatusEntry 3 }

        aggrStatusSyncPorts OBJECT-TYPE
        SYNTAX  PortList
        MAX-ACCESS  read-only
        STATUS  current
        DESCRIPTION
                      	"Sync Ports Port List"
        ::= { aggrStatusEntry 4 }


--  18.accessCtlSetup

-- 		accessCtlTable

        accessCtlTable OBJECT-TYPE
        SYNTAX	SEQUENCE OF AccessCtlEntry
        MAX-ACCESS  not-accessible
        STATUS  current
        DESCRIPTION
                 	""
        ::= { accessCtlSetup 1 }

		accessCtlEntry OBJECT-TYPE
        SYNTAX	AccessCtlEntry
        MAX-ACCESS	not-accessible
        STATUS	current
        DESCRIPTION    	"An entry in accessCtlTable."
        INDEX          	{ accessCtlService }
        ::= { accessCtlTable 1 }

        AccessCtlEntry ::=
           SEQUENCE {
        	accessCtlService	INTEGER,
        	accessCtlEnable	EnabledStatus,
        	accessCtlServicePort	INTEGER,
        	accessCtlTimeout	INTEGER
           }

        accessCtlService OBJECT-TYPE
        SYNTAX  INTEGER {
        	telnet(1),
        	ssh(2),
        	ftp(3),
        	http(4),
        	https(5),
        	icmp(6),
        	snmp(7)
        }
        MAX-ACCESS  read-only
        STATUS  current
        DESCRIPTION
                      	""
        ::= { accessCtlEntry 1 }

        accessCtlEnable OBJECT-TYPE
        SYNTAX  EnabledStatus
        MAX-ACCESS  read-write
        STATUS  current
        DESCRIPTION
                     	""
        ::= { accessCtlEntry 2 }

        accessCtlServicePort OBJECT-TYPE
        SYNTAX  INTEGER
        MAX-ACCESS  read-write
        STATUS  current
        DESCRIPTION
                     	""
        ::= { accessCtlEntry 3 }

        accessCtlTimeout OBJECT-TYPE
        SYNTAX  INTEGER
        MAX-ACCESS  read-write
        STATUS  current
        DESCRIPTION
                     	""
        ::= { accessCtlEntry 4 }

-- 		securedClientTable
        securedClientTable OBJECT-TYPE
        SYNTAX	SEQUENCE OF SecuredClientEntry
        MAX-ACCESS  not-accessible
        STATUS  current
        DESCRIPTION
                 	""
        ::= { accessCtlSetup 2 }

		securedClientEntry OBJECT-TYPE
        SYNTAX	SecuredClientEntry
        MAX-ACCESS	not-accessible
        STATUS	current
        DESCRIPTION    	"An entry in securedClientTable."
        INDEX          	{ securedClientIndex }
        ::= { securedClientTable 1 }

        SecuredClientEntry ::=
           SEQUENCE {
           	securedClientIndex	INTEGER,
           	securedClientEnable	EnabledStatus,
        	securedClientStartIp	IpAddress,
        	securedClientEndIp	IpAddress,
        	securedClientService	BITS
           }

        securedClientIndex OBJECT-TYPE
        SYNTAX  INTEGER
        MAX-ACCESS  read-only
        STATUS  current
        DESCRIPTION
                      	""
        ::= { securedClientEntry 1 }

        securedClientEnable OBJECT-TYPE
        SYNTAX  EnabledStatus
        MAX-ACCESS  read-write
        STATUS  current
        DESCRIPTION
                      	""
        ::= { securedClientEntry 2 }

        securedClientStartIp OBJECT-TYPE
        SYNTAX  IpAddress
        MAX-ACCESS  read-write
        STATUS  current
        DESCRIPTION
                      	""
        ::= { securedClientEntry 3 }

        securedClientEndIp OBJECT-TYPE
        SYNTAX  IpAddress
        MAX-ACCESS  read-write
        STATUS  current
        DESCRIPTION
                     	""
        ::= { securedClientEntry 4 }

        securedClientService OBJECT-TYPE
        SYNTAX	BITS {
			telnet(0),
			ftp(1),
			http(2),
			icmp(3),
			snmp(4),
			ssh(5),
			https(6)
		}
        MAX-ACCESS  read-write
        STATUS  current
        DESCRIPTION
                     	""
        ::= { securedClientEntry 5 }

--  19. queuingMethodSetup

--  portQueuingMethodTable
        portQueuingMethodTable OBJECT-TYPE
        SYNTAX	SEQUENCE OF PortQueuingMethodEntry
        MAX-ACCESS  not-accessible
        STATUS  current
        DESCRIPTION
                 	""
        ::= { queuingMethodSetup 1 }

		portQueuingMethodEntry OBJECT-TYPE
        SYNTAX	PortQueuingMethodEntry
        MAX-ACCESS	not-accessible
        STATUS	current
        DESCRIPTION    	"An entry in portQueuingMethodTable."
        INDEX          	{ dot1dBasePort, portQueuingMethodQueue }
        ::= {portQueuingMethodTable 1}

        PortQueuingMethodEntry ::=
           SEQUENCE {
        	portQueuingMethodQueue	INTEGER,
        	portQueuingMethodWeight	INTEGER,
        	portQueuingMethodMode	INTEGER
           }

        portQueuingMethodQueue OBJECT-TYPE
        SYNTAX  INTEGER
        MAX-ACCESS  read-only
        STATUS  current
        DESCRIPTION
                      	"0...7"
        ::= { portQueuingMethodEntry 1 }

        portQueuingMethodWeight OBJECT-TYPE
        SYNTAX  INTEGER
        MAX-ACCESS  read-write
        STATUS  current
        DESCRIPTION
                     	"0...15"
        ::= { portQueuingMethodEntry 2 }

        portQueuingMethodMode OBJECT-TYPE
        SYNTAX  INTEGER {
        	strictlyPriority(0),
        	weightedFairScheduling(1)
        }
        MAX-ACCESS  read-write
        STATUS  current
        DESCRIPTION
                     	""
        ::= { portQueuingMethodEntry 3 }

        portQueuingMethodHybridSpqTable OBJECT-TYPE
        SYNTAX	SEQUENCE OF	PortQueuingMethodHybridSpqEntry
        MAX-ACCESS  not-accessible
        STATUS  current
        DESCRIPTION
                 	""
        ::= { queuingMethodSetup 2 }

		portQueuingMethodHybridSpqEntry OBJECT-TYPE
        SYNTAX	PortQueuingMethodHybridSpqEntry
        MAX-ACCESS	not-accessible
        STATUS	current
        DESCRIPTION    	"An entry in portQueuingMethodTable."
        INDEX          	{ dot1dBasePort }
        ::= { portQueuingMethodHybridSpqTable 1 }

        PortQueuingMethodHybridSpqEntry ::=
           SEQUENCE {
        		portQueuingMethodHybridSpq		INTEGER
           }

        portQueuingMethodHybridSpq	OBJECT-TYPE
        SYNTAX  INTEGER {
        	none(0),
        	q0(1),
        	q1(2),
        	q2(3),
        	q3(4),
        	q4(5),
        	q5(6),
        	q6(7),
        	q7(8)
        }
        MAX-ACCESS  read-write
        STATUS  current
        DESCRIPTION
                      	""
        ::= { portQueuingMethodHybridSpqEntry 1 }



--  20.dhcpSetup

        globalDhcpRelay OBJECT IDENTIFIER ::= { dhcpSetup 1 }

        globalDhcpRelayEnable OBJECT-TYPE
        SYNTAX  EnabledStatus
        MAX-ACCESS  read-write
        STATUS  current
        DESCRIPTION
                      	"Enable/Disable DHCP relay for all broadcast domains on the Switch."
        ::= { globalDhcpRelay 1 }

        globalDhcpRelayOption82Enable OBJECT-TYPE
        SYNTAX  EnabledStatus
        MAX-ACCESS  read-write
        STATUS  current
        DESCRIPTION
                      	"Enable/Disable the Switch to add option 82 to agent information."
        ::= { globalDhcpRelay 2 }

        globalDhcpRelayInfoEnable OBJECT-TYPE
        SYNTAX  EnabledStatus
        MAX-ACCESS  read-write
        STATUS  current
        DESCRIPTION
                      	"Enable/Disable the Switch to add system name to agent information."
        ::= { globalDhcpRelay 3 }

        globalDhcpRelayInfoData OBJECT-TYPE
        SYNTAX  DisplayString
        MAX-ACCESS  read-only
        STATUS  current
        DESCRIPTION
                      	"System name of the Switch."
        ::= { globalDhcpRelay 4 }

-- 		globalDhcpRelayRemoteServer

        maxNumberOfGlobalDhcpRelayRemoteServer OBJECT-TYPE
        SYNTAX  INTEGER
        MAX-ACCESS  read-only
        STATUS  current
        DESCRIPTION
                      	"The maximun number of global relay remote server."
        ::= { globalDhcpRelay 5 }

-- 		globalDhcpRelayRemoteServerTable
        globalDhcpRelayRemoteServerTable OBJECT-TYPE
        SYNTAX	SEQUENCE OF GlobalDhcpRelayRemoteServerEntry
        MAX-ACCESS  not-accessible
        STATUS  current
        DESCRIPTION
                 	""
        ::= { globalDhcpRelay 6 }

		globalDhcpRelayRemoteServerEntry OBJECT-TYPE
        SYNTAX	GlobalDhcpRelayRemoteServerEntry
        MAX-ACCESS	not-accessible
        STATUS	current
        DESCRIPTION    	"An entry in globalDhcpRelayRemoteServerTable."
        INDEX          	{ globalDhcpRelayRemoteServerIp }
        ::= { globalDhcpRelayRemoteServerTable 1 }

        GlobalDhcpRelayRemoteServerEntry ::=
           SEQUENCE {
        	globalDhcpRelayRemoteServerIp		IpAddress,
        	globalDhcpRelayRemoteServerRowStatus	RowStatus
           }

        globalDhcpRelayRemoteServerIp OBJECT-TYPE
        SYNTAX  IpAddress
        MAX-ACCESS  read-only
        STATUS  current
        DESCRIPTION
                      	"The server IP of the global dhcp relay entry."
        ::= { globalDhcpRelayRemoteServerEntry 1 }

        globalDhcpRelayRemoteServerRowStatus OBJECT-TYPE
        SYNTAX  RowStatus
        MAX-ACCESS  read-create
        STATUS  current
        DESCRIPTION
                     	"The status of specified global dhcp relay server entry."
        ::= { globalDhcpRelayRemoteServerEntry 2 }

        globalDhcpRelayOption82Format OBJECT-TYPE
        SYNTAX  INTEGER (0..1)
        MAX-ACCESS  read-write
        STATUS  current
        DESCRIPTION
                      	"Enable/Disable the Switch to add option 82 with specific format to agent information.
                      	 Note : (A) globalDhcpRelayOption82Enable
                      	        (B) globalDhcpRelayInfoEnable
                      	        (C) globalDhcpRelayOption82Format
                      	        (D) dhcpL2AgentOpt82CircuitIdInfo or dhcpL2AgentOpt82RemoteIdInfo
                      	        For pon ports, OLT uses below rules as dhcp option-82 configurations.
                      	            (D) > (C) > (A) = (B)
                      	"
        ::= { globalDhcpRelay 7 }


		dhcpServer OBJECT IDENTIFIER ::= { dhcpSetup 2 }

        maxNumberOfDhcpServers OBJECT-TYPE
        SYNTAX  INTEGER
        MAX-ACCESS  read-only
        STATUS  current
        DESCRIPTION
                      	"The maximum number of DHCP server entries that can be created.
                      	A value of 0 for this object implies that there exists settings for
                      	global DHCP relay."
        ::= { dhcpServer 1 }

-- 		dhcpServerTable
        dhcpServerTable OBJECT-TYPE
        SYNTAX	SEQUENCE OF DhcpServerEntry
        MAX-ACCESS  not-accessible
        STATUS  current
        DESCRIPTION
                 	""
        ::= { dhcpServer 2 }

		dhcpServerEntry OBJECT-TYPE
        SYNTAX	DhcpServerEntry
        MAX-ACCESS	not-accessible
        STATUS	current
        DESCRIPTION    	"An entry in dhcpServerTable."
        INDEX          	{ dhcpServerVid }
        ::= { dhcpServerTable 1 }

        DhcpServerEntry ::=
           SEQUENCE {
        	dhcpServerVid		INTEGER,
        	dhcpServerStartAddr	IpAddress,
        	dhcpServerPoolSize	INTEGER,
        	dhcpServerMask		IpAddress,
        	dhcpServerGateway	IpAddress,
        	dhcpServerPrimaryDNS 	IpAddress,
        	dhcpServerSecondaryDNS	IpAddress,
        	dhcpServerRowStatus	RowStatus
           }

        dhcpServerVid OBJECT-TYPE
        SYNTAX  INTEGER
        MAX-ACCESS  read-only
        STATUS  current
        DESCRIPTION
                      	""
        ::= { dhcpServerEntry 1 }

        dhcpServerStartAddr OBJECT-TYPE
        SYNTAX  IpAddress
        MAX-ACCESS  read-write
        STATUS  current
        DESCRIPTION
                     	""
        ::= { dhcpServerEntry 2 }

        dhcpServerPoolSize OBJECT-TYPE
        SYNTAX  INTEGER
        MAX-ACCESS  read-write
        STATUS  current
        DESCRIPTION
                     	""
        ::= { dhcpServerEntry 3 }

        dhcpServerMask OBJECT-TYPE
        SYNTAX  IpAddress
        MAX-ACCESS  read-write
        STATUS  current
        DESCRIPTION
                     	""
        ::= { dhcpServerEntry 4 }

        dhcpServerGateway OBJECT-TYPE
        SYNTAX  IpAddress
        MAX-ACCESS  read-write
        STATUS  current
        DESCRIPTION
                     	""
        ::= { dhcpServerEntry 5 }

        dhcpServerPrimaryDNS OBJECT-TYPE
        SYNTAX  IpAddress
        MAX-ACCESS  read-write
        STATUS  current
        DESCRIPTION
                     	""
        ::= { dhcpServerEntry 6 }

        dhcpServerSecondaryDNS OBJECT-TYPE
        SYNTAX  IpAddress
        MAX-ACCESS  read-write
        STATUS  current
        DESCRIPTION
                     	""
        ::= { dhcpServerEntry 7 }

        dhcpServerRowStatus OBJECT-TYPE
        SYNTAX  RowStatus
        MAX-ACCESS  read-create
        STATUS  current
        DESCRIPTION
                     	""
        ::= { dhcpServerEntry 8 }


		dhcpRelay OBJECT IDENTIFIER ::= { dhcpSetup 3 }

   		dhcpRelayInfoData OBJECT-TYPE
        SYNTAX  DisplayString
        MAX-ACCESS  read-only
        STATUS  current
        DESCRIPTION
                      	"System name of the Switch."
        ::= { dhcpRelay 1 }

	 	maxNumberOfDhcpRelay OBJECT-TYPE
        SYNTAX  INTEGER
        MAX-ACCESS  read-only
        STATUS  current
        DESCRIPTION
                      	"The maximum number of DHCP relay entries that can be created.
                      	A value of 0 for this object implies that there exists settings for
                      	global DHCP relay."
        ::= { dhcpRelay 2 }

     	maxNumberOfDhcpRelayRemoteServer OBJECT-TYPE
        SYNTAX  INTEGER
        MAX-ACCESS  read-only
        STATUS  current
        DESCRIPTION
                      	"The maximum number of DHCP relay remote server."
        ::= { dhcpRelay 3 }

-- 		dhcpRelayRemoteServerTable
        dhcpRelayRemoteServerTable OBJECT-TYPE
        SYNTAX	SEQUENCE OF DhcpRelayRemoteServerEntry
        MAX-ACCESS  not-accessible
        STATUS  current
        DESCRIPTION
                 	""
        ::= { dhcpRelay 4 }

		dhcpRelayRemoteServerEntry OBJECT-TYPE
        SYNTAX	DhcpRelayRemoteServerEntry
        MAX-ACCESS	not-accessible
        STATUS	current
        DESCRIPTION    	"An entry in dhcpRelayRemoteServerTable."
        INDEX          	{  dhcpRelayVid, dhcpRelayRemoteServerIp }
        ::= { dhcpRelayRemoteServerTable 1 }

        DhcpRelayRemoteServerEntry ::=
           SEQUENCE {
            	dhcpRelayVid		          INTEGER,
           	dhcpRelayRemoteServerIp		IpAddress,
        		dhcpRelayRemoteServerRowStatus	RowStatus
           }

        dhcpRelayVid OBJECT-TYPE
        SYNTAX  INTEGER
        MAX-ACCESS  read-only
        STATUS  current
        DESCRIPTION
                      	"The vlan id of the dhcp relay entry."
        ::= { dhcpRelayRemoteServerEntry 1 }

        dhcpRelayRemoteServerIp OBJECT-TYPE
        SYNTAX  IpAddress
        MAX-ACCESS  read-only
        STATUS  current
        DESCRIPTION
                      	"The server IP of the dhcp relay entry."
        ::= { dhcpRelayRemoteServerEntry 2 }

        dhcpRelayRemoteServerRowStatus OBJECT-TYPE
        SYNTAX  RowStatus
        MAX-ACCESS  read-create
        STATUS  current
        DESCRIPTION
                     	"The status of specified dhcp relay server entry."
        ::= { dhcpRelayRemoteServerEntry 3 }

-- 		dhcpRelayTable

        dhcpRelayTable OBJECT-TYPE
        SYNTAX	SEQUENCE OF DhcpRelayEntry
        MAX-ACCESS  not-accessible
        STATUS  current
        DESCRIPTION
                    "A. dhcpRelayOption82Enable
                           append [ponport vlan] into circuit-id of dhcp option-82
                           append [client's mac] into remote-id of dhcp option-82
                     B. dhcpRelayInfoEnable
                           append [system_name] behind [ponport vlan] into circuit-id of dhcp option-82
                           If (A) & (B) are enabled at the same time, the circuit-id format would be [ponport vlan system_name]
                     C. dhcpRelayOption82Format
                           append specific format into circuit-id and remote-id, shown as below
                        => circuit-id : [SYS_ID /PONPORT:NNISVID.SNISVID ONTID/SN]
                        => remote-id  : Unnecessary
                     D. dhcpL2AgentOpt82CircuitIdInfo or dhcpL2AgentOpt82RemoteIdInfo
                     Note :
                        For pon ports, OLT uses below rules as dhcp option-82 configurations.
                            (D) > (C) > (A) = (B)
                     "
        ::= { dhcpRelay 5 }


        dhcpRelayEntry OBJECT-TYPE
        SYNTAX	DhcpRelayEntry
        MAX-ACCESS	not-accessible
        STATUS	current
        DESCRIPTION    	"An entry in dhcpRelayTable."
        INDEX          	{ dhcpRelayVid }
        ::= { dhcpRelayTable 1 }

        DhcpRelayEntry ::=
           SEQUENCE {
        	dhcpRelayOption82Enable   EnabledStatus,
        	dhcpRelayInfoEnable       EnabledStatus,
        	dhcpRelayOption82Format   INTEGER
           }

        dhcpRelayOption82Enable OBJECT-TYPE
        SYNTAX  EnabledStatus
        MAX-ACCESS  read-write
        STATUS  current
        DESCRIPTION
                      	"Enable/Disable DHCP relay option 82."
        ::= { dhcpRelayEntry 1 }

        dhcpRelayInfoEnable OBJECT-TYPE
        SYNTAX  EnabledStatus
        MAX-ACCESS  read-write
        STATUS  current
        DESCRIPTION
                      	"Enable/Disable DHCP relay information."
        ::= { dhcpRelayEntry 2 }

        dhcpRelayOption82Format OBJECT-TYPE
        SYNTAX  INTEGER (0..1)
        MAX-ACCESS  read-write
        STATUS  current
        DESCRIPTION
                      	"Enable/Disable DHCP relay option 82 with specific format."
        ::= { dhcpRelayEntry 3 }

--  22.arpInfo

--  	arpTable
      	arpTable	OBJECT-TYPE
        SYNTAX	SEQUENCE OF ArpEntry
        MAX-ACCESS  not-accessible
        STATUS  current
        DESCRIPTION
                 	""
        ::= { arpInfo 1 }

		arpEntry OBJECT-TYPE
        SYNTAX	ArpEntry
        MAX-ACCESS	not-accessible
        STATUS	current
        DESCRIPTION    	"An entry in arpTable."
        INDEX          	{ arpIpAddr, arpMacVid }
        ::= { arpTable 1 }

        ArpEntry ::=
           SEQUENCE {
           	arpIndex	INTEGER,
        	arpIpAddr	IpAddress,
        	arpMacAddr	MacAddress,
        	arpMacVid	INTEGER,
        	arpType		INTEGER,
			arpPort		DisplayString,
			arpAge		INTEGER
           }

        arpIndex OBJECT-TYPE
        SYNTAX  INTEGER
        MAX-ACCESS  read-only
        STATUS  current
        DESCRIPTION
                      	"The index of the arp table."
        ::= { arpEntry 1 }

        arpIpAddr OBJECT-TYPE
        SYNTAX  IpAddress
        MAX-ACCESS  read-only
        STATUS  current
        DESCRIPTION
                      	"The IP address of the Switch on specified vlan."
        ::= { arpEntry 2 }

        arpMacAddr OBJECT-TYPE
        SYNTAX  MacAddress
        MAX-ACCESS  read-only
        STATUS  current
        DESCRIPTION
                      	"The MAC address of the Switch on specified vlan. Each Switch has unique MAC address."
        ::= { arpEntry 3 }

        arpMacVid OBJECT-TYPE
        SYNTAX  INTEGER
        MAX-ACCESS  read-only
        STATUS  current
        DESCRIPTION
                      	"The vlan id of specified arp entry."
        ::= { arpEntry 4 }

        arpType OBJECT-TYPE
        SYNTAX  INTEGER
        MAX-ACCESS  read-only
        STATUS  current
        DESCRIPTION
                      	"Display how the entry was learned.
                      	 Dynamic: The Switch learned this entry from ARP packets."
        ::= { arpEntry 5 }

		arpPort OBJECT-TYPE
        SYNTAX  DisplayString
        MAX-ACCESS  read-only
        STATUS  current
        DESCRIPTION
                      	"The port of the arp entry."
        ::= { arpEntry 6 }

		arpAge OBJECT-TYPE
        SYNTAX  INTEGER
        MAX-ACCESS  read-only
        STATUS  current
        DESCRIPTION
                      	"arp entry age timer."
        ::= { arpEntry 7 }

--  23.portOpModeSetup

-- 		portOpModePortTable

        portOpModePortTable  OBJECT-TYPE
        SYNTAX	SEQUENCE OF PortOpModePortEntry
        MAX-ACCESS  not-accessible
        STATUS  current
        DESCRIPTION
                 	""
        ::= { portOpModeSetup 1 }

		portOpModePortEntry  OBJECT-TYPE
        SYNTAX	PortOpModePortEntry
        MAX-ACCESS	not-accessible
        STATUS	current
        DESCRIPTION    	"An entry in portOpModePortTable."
        INDEX          	{ dot1dBasePort }
        ::= { portOpModePortTable 1 }

        PortOpModePortEntry ::=
           SEQUENCE {
        	portOpModePortSpeedDuplex		INTEGER,
        	portOpModePortFlowCntl			INTEGER,
        	portOpModePortName			OCTET STRING,
        	portOpModePortModuleType		INTEGER,
        	portOpModePortLinkUpType		INTEGER,
--        	portOpModePortIntrusionLock		EnabledStatus,
--        	portOpModePortLBTestStatus		INTEGER,
        	portOpModePortCounterReset		INTEGER,
--        	portOpModePortCX4CableLength		INTEGER
        	portOpModePortMaxFrameSize		INTEGER
           }

        portOpModePortSpeedDuplex OBJECT-TYPE
        SYNTAX  INTEGER {
            auto(0),
--        	speed10Half(1),
--        	speed10Full(2),
--        	speed100Half(3),
        	speed100Full(4),
        	speed1000Full(5),
        	speed10000Full(6),
--        	speed12000Full(7)
        	speed2500Full(8)
        }
        MAX-ACCESS  read-write
        STATUS  current
        DESCRIPTION
                      	"PON card speed duplex should be <speed2500Full>
                         GE card speed duplex should be <auto|speed100Half|speed100Full|speed1000Full>
                         MSC card GE port speed duplex should be <auto|speed100Half|speed100Full|speed1000Full>
                         MSC card 10G port speed duplex should be <auto|speed100Full|speed1000Full>"
        ::= { portOpModePortEntry 1 }

        portOpModePortFlowCntl OBJECT-TYPE
        SYNTAX  INTEGER {
        	off(0),
        	on(1)
        }
        MAX-ACCESS  read-write
        STATUS  current
        DESCRIPTION
                     	""
        ::= { portOpModePortEntry 2 }

        portOpModePortName  OBJECT-TYPE
        SYNTAX  OCTET STRING (SIZE(0..64))
        MAX-ACCESS  read-write
        STATUS  current
        DESCRIPTION
                      	""
        ::= { portOpModePortEntry 3 }

        portOpModePortModuleType  OBJECT-TYPE
        SYNTAX  INTEGER {
        	fastEthernet10or100(0),
        	gigabitEthernet100or1000(1),
        	xgEthernet10000(2)
        }
        MAX-ACCESS  read-only
        STATUS  current
        DESCRIPTION
                      	""
        ::= { portOpModePortEntry 4 }

        portOpModePortLinkUpType  OBJECT-TYPE
        SYNTAX  INTEGER {
       		down(0),
        	utp(1),
        	sfp(2),
        	xfp(3),
        	cx4(4)
        }
        MAX-ACCESS  read-only
        STATUS  current
        DESCRIPTION
                      	""
        ::= { portOpModePortEntry 5 }

--		portOpModePortIntrusionLock OBJECT-TYPE
--        SYNTAX  EnabledStatus
--        MAX-ACCESS  read-write
--        STATUS  current
--        DESCRIPTION
--                      	""
--        ::= { portOpModePortEntry 6 }

--		portOpModePortLBTestStatus OBJECT-TYPE
--    	SYNTAX  INTEGER {
--    	  none(0),
--    	  underTesting(1),
--    	  success(2),
--    	  fail(3)
--    	}
--    	MAX-ACCESS  read-only
--    	STATUS  current
--   	DESCRIPTION
--      "This entry display latest loopback test status of port while performing loopback test."
-- 		::= { portOpModePortEntry 7 }

		portOpModePortCounterReset OBJECT-TYPE
        SYNTAX  INTEGER {
        	enable(1),
        	disable(2)
        }
        MAX-ACCESS  read-write
        STATUS  current
        DESCRIPTION
               "This entry resets port counter."
        ::= { portOpModePortEntry 8 }

--        portOpModePortCX4CableLength OBJECT-TYPE
--        SYNTAX  INTEGER {
--        	halfMeter (0),
--        	oneMeter  (1),
--        	threeMeters(2),
--        	fiveMeters (3),
--        	tenMeters  (4),
--        	fifteenMeters (5)
--        }
--        MAX-ACCESS  read-write
--        STATUS  optional
--        DESCRIPTION
--               "The length of CX4 Cable."
--        ::= { portOpModePortEntry 9 }

        portOpModePortMaxFrameSize OBJECT-TYPE
        SYNTAX  INTEGER
        MAX-ACCESS  read-write
        STATUS  current
        DESCRIPTION
               "This entry is the max frame size can be passed on the port.( 64 ~9216 bytes and Default: 9216 bytes)"
        ::= { portOpModePortEntry 10 }

-- 		ifGponTable

        ifGponTable  OBJECT-TYPE
        SYNTAX	SEQUENCE OF IfGponEntry
        MAX-ACCESS  not-accessible
        STATUS  current
        DESCRIPTION
                 	""
        ::= { portOpModeSetup 2 }

		ifGponEntry  OBJECT-TYPE
        SYNTAX	IfGponEntry
        MAX-ACCESS	not-accessible
        STATUS	current
        DESCRIPTION    	"An entry in ifGponTable."
        INDEX          	{ ifGponAlias }
        ::= { ifGponTable 1 }

        IfGponEntry ::=
           SEQUENCE {
        	ifGponAlias		OCTET STRING,
        	ifGponPortName	OCTET STRING
           }

        ifGponAlias OBJECT-TYPE
        SYNTAX  OCTET STRING (SIZE(0..64))
        MAX-ACCESS  read-write
        STATUS  current
        DESCRIPTION
                      	""
        ::= { ifGponEntry 1 }

        ifGponPortName  OBJECT-TYPE
        SYNTAX  OCTET STRING (SIZE(0..64))
        MAX-ACCESS  read-only
        STATUS  current
        DESCRIPTION
                      	""
        ::= { ifGponEntry 2 }

--  25.multicastPortSetup

        multicastPortTable	OBJECT-TYPE
        SYNTAX	SEQUENCE OF MulticastPortEntry
        MAX-ACCESS  not-accessible
        STATUS  current
        DESCRIPTION
                 	""
        ::= { multicastPortSetup 1 }

		multicastPortEntry OBJECT-TYPE
        SYNTAX	MulticastPortEntry
        MAX-ACCESS	not-accessible
        STATUS	current
        DESCRIPTION    	"An entry in multicastPortTable."
        INDEX          	{ dot1dBasePort }
        ::= { multicastPortTable 1 }

        MulticastPortEntry ::=
		SEQUENCE {
            multicastPortImmediateLeave          EnabledStatus,
--        	multicastPortMaxGroupLimited		EnabledStatus,
--        	multicastPortMaxOfGroup				INTEGER,
--        	multicastPortIgmpFilteringProfile	DisplayString,
            multicastPortQueryMode               INTEGER,
--            igmpMsgMaxLimited                    EnabledStatus,
--            igmpMsgLimit                         INTEGER
        }

        multicastPortImmediateLeave OBJECT-TYPE
        SYNTAX  EnabledStatus
        MAX-ACCESS  read-write
        STATUS  current
        DESCRIPTION
                      	""
        ::= { multicastPortEntry 1 }

--        multicastPortMaxGroupLimited OBJECT-TYPE
--        SYNTAX  EnabledStatus
--        MAX-ACCESS  read-write
--        STATUS  current
--        DESCRIPTION
--                      	""
--        ::= { multicastPortEntry 2 }

--        multicastPortMaxOfGroup OBJECT-TYPE
--        SYNTAX  INTEGER
--        MAX-ACCESS  read-write
--        STATUS  current
--        DESCRIPTION
--                      	"0..255"
--        ::= { multicastPortEntry 3 }

--        multicastPortIgmpFilteringProfile OBJECT-TYPE
--        SYNTAX  DisplayString
--        MAX-ACCESS  read-write
--        STATUS  current
--        DESCRIPTION
--                      	""
--        ::= { multicastPortEntry 4 }


        multicastPortQueryMode OBJECT-TYPE
        SYNTAX  INTEGER {
        	autoMode(1),
        	fixMode(2),
        	edgeMode(3)
        }
        MAX-ACCESS  read-write
        STATUS  current
        DESCRIPTION
                      	"Specify query mode for each port"
        ::= { multicastPortEntry 5 }

--        igmpMsgMaxLimited OBJECT-TYPE
--        SYNTAX  EnabledStatus
--        MAX-ACCESS  read-write
--        STATUS  current
--        DESCRIPTION
--                      	""
--        ::= { multicastPortEntry 6 }

--        igmpMsgLimit OBJECT-TYPE
--        SYNTAX  INTEGER
--        MAX-ACCESS  read-write
--        STATUS  current
--        DESCRIPTION
--                      	"0..255"
--        ::= { multicastPortEntry 7 }


--  26.multicastStatus

       multicastStatusTable	OBJECT-TYPE
        SYNTAX	SEQUENCE OF MulticastStatusEntry
        MAX-ACCESS  not-accessible
        STATUS  current
        DESCRIPTION
                 	""
        ::= { multicastStatus 1 }

		multicastStatusEntry OBJECT-TYPE
        SYNTAX	MulticastStatusEntry
        MAX-ACCESS	not-accessible
        STATUS	current
        DESCRIPTION    	"An entry in multicastStatusTable."
        INDEX          	{ multicastStatusVlanID, multicastStatusPort, multicastStatusGroup }
        ::= { multicastStatusTable 1 }

        MulticastStatusEntry ::=
		SEQUENCE {
        	multicastStatusIndex    INTEGER,
        	multicastStatusVlanID	INTEGER,
        	multicastStatusPort	INTEGER,
        	multicastStatusGroup	IpAddress
--        	multicastStatusJoinCounter    INTEGER,
--        	multicastStatusLeaveCounter    INTEGER
         }

        multicastStatusIndex OBJECT-TYPE
        SYNTAX  INTEGER
        MAX-ACCESS  read-only
        STATUS  current
        DESCRIPTION
                      	""
        ::= { multicastStatusEntry 1 }

        multicastStatusVlanID OBJECT-TYPE
        SYNTAX  INTEGER
        MAX-ACCESS  read-only
        STATUS  current
        DESCRIPTION
                      	""
        ::= { multicastStatusEntry 2 }

        multicastStatusPort OBJECT-TYPE
        SYNTAX  INTEGER
        MAX-ACCESS  read-only
        STATUS  current
        DESCRIPTION
                      	""
        ::= { multicastStatusEntry 3 }

        multicastStatusGroup OBJECT-TYPE
        SYNTAX  IpAddress
        MAX-ACCESS  read-only
        STATUS  current
        DESCRIPTION
                      	""
        ::= { multicastStatusEntry 4 }

--        multicastStatusJoinCounter OBJECT-TYPE
--        SYNTAX  INTEGER
--        MAX-ACCESS  read-only
--        STATUS  current
--        DESCRIPTION
--                      	""
--        ::= { multicastStatusEntry 5 }
--
--        multicastStatusLeaveCounter OBJECT-TYPE
--        SYNTAX  INTEGER
--        MAX-ACCESS  read-only
--        STATUS  current
--        DESCRIPTION
--                      	""
--        ::= { multicastStatusEntry 6 }

        igmpCountTable	OBJECT-TYPE
        SYNTAX	SEQUENCE OF IgmpCountEntry
        MAX-ACCESS  not-accessible
        STATUS  current
        DESCRIPTION
                 	"A count table of igmp query/report/leave message."
        ::= { multicastStatus 2 }

-- igmpCountStatus
	igmpCountEntry OBJECT-TYPE
        SYNTAX	IgmpCountEntry
        MAX-ACCESS	not-accessible
        STATUS	current
        DESCRIPTION    	"An entry in igmpCountTable."
        INDEX          	{ igmpCountIndex }
        ::= { igmpCountTable 1 }

        IgmpCountEntry ::=
		SEQUENCE {
        	igmpCountIndex    		INTEGER,
        	igmpCountInQuery		INTEGER,
        	igmpCountInReport		INTEGER,
        	igmpCountInLeave		INTEGER,
        	igmpCountInQueryDrop   	INTEGER,
        	igmpCountInReportDrop   INTEGER,
        	igmpCountInLeaveDrop   	INTEGER,
        	igmpCountOutQuery   	INTEGER,
        	igmpCountOutReport   	INTEGER,
        	igmpCountOutLeave   	INTEGER
        }

        igmpCountIndex OBJECT-TYPE
        SYNTAX  INTEGER
        MAX-ACCESS  read-only
        STATUS  current
        DESCRIPTION
                      	"Index of IgmpCountEntry. 0 means total count in whole system"
        ::= { igmpCountEntry 1 }

        igmpCountInQuery OBJECT-TYPE
        SYNTAX  INTEGER
        MAX-ACCESS  read-only
        STATUS  current
        DESCRIPTION
                      	""
        ::= { igmpCountEntry 2 }

        igmpCountInReport OBJECT-TYPE
        SYNTAX  INTEGER
        MAX-ACCESS  read-only
        STATUS  current
        DESCRIPTION
                      	""
        ::= { igmpCountEntry 3 }

        igmpCountInLeave OBJECT-TYPE
        SYNTAX  INTEGER
        MAX-ACCESS  read-only
        STATUS  current
        DESCRIPTION
                      	""
        ::= { igmpCountEntry 4 }

        igmpCountInQueryDrop OBJECT-TYPE
        SYNTAX  INTEGER
        MAX-ACCESS  read-only
        STATUS  current
        DESCRIPTION
                      	""
        ::= { igmpCountEntry 5 }

        igmpCountInReportDrop OBJECT-TYPE
        SYNTAX  INTEGER
        MAX-ACCESS  read-only
        STATUS  current
        DESCRIPTION
                      	""
        ::= { igmpCountEntry 6 }

        igmpCountInLeaveDrop OBJECT-TYPE
        SYNTAX  INTEGER
        MAX-ACCESS  read-only
        STATUS  current
        DESCRIPTION
                      	""
        ::= { igmpCountEntry 7 }

        igmpCountOutQuery OBJECT-TYPE
        SYNTAX  INTEGER
        MAX-ACCESS  read-only
        STATUS  current
        DESCRIPTION
                      	""
        ::= { igmpCountEntry 8 }

        igmpCountOutReport OBJECT-TYPE
        SYNTAX  INTEGER
        MAX-ACCESS  read-only
        STATUS  current
        DESCRIPTION
                      	""
        ::= { igmpCountEntry 9 }

        igmpCountOutLeave OBJECT-TYPE
        SYNTAX  INTEGER
        MAX-ACCESS  read-only
        STATUS  current
        DESCRIPTION
                      	""
        ::= { igmpCountEntry 10 }

        multicastVlanStatusTable	OBJECT-TYPE
        SYNTAX	SEQUENCE OF MulticastVlanStatusEntry
        MAX-ACCESS  not-accessible
        STATUS  current
        DESCRIPTION
                 	""
        ::= { multicastStatus 3 }

-- multicastVlanStatusTable
		multicastVlanStatusEntry OBJECT-TYPE
        SYNTAX	MulticastVlanStatusEntry
        MAX-ACCESS	not-accessible
        STATUS	current
        DESCRIPTION    	"An entry in multicastVlanStatusTable."
        INDEX          	{ multicastVlanStatusVlanID }
        ::= { multicastVlanStatusTable 1 }

        MulticastVlanStatusEntry ::=
		SEQUENCE {
        	multicastVlanStatusVlanID   INTEGER,
        	multicastVlanStatusType		INTEGER,
        	multicastVlanQueryPort	PortList,
        	multicastVlanQuerySrcIp	IpAddress
         }

        multicastVlanStatusVlanID OBJECT-TYPE
        SYNTAX  INTEGER
        MAX-ACCESS  read-only
        STATUS  current
        DESCRIPTION
                      	""
        ::= { multicastVlanStatusEntry 1 }

        multicastVlanStatusType OBJECT-TYPE
        SYNTAX  INTEGER {
   		dynamic(1),
 		mvr (2),
		static(3)
        }
        MAX-ACCESS  read-only
        STATUS  current
        DESCRIPTION
                      	""
        ::= { multicastVlanStatusEntry 2 }

        multicastVlanQueryPort OBJECT-TYPE
        SYNTAX  PortList
        MAX-ACCESS  read-only
        STATUS  current
        DESCRIPTION
                      	""
        ::= { multicastVlanStatusEntry 3 }

		multicastVlanQuerySrcIp OBJECT-TYPE
		SYNTAX  IpAddress
        MAX-ACCESS  read-only
        STATUS  current
		DESCRIPTION
						""
		::= { multicastVlanStatusEntry 4 }

-- igmpCounterPortTable

        igmpCounterPortTable OBJECT-TYPE
        SYNTAX	SEQUENCE OF IgmpCounterPortEntry
        MAX-ACCESS  not-accessible
        STATUS  current
        DESCRIPTION
                 	""
        ::= { multicastStatus 4 }

	igmpCounterPortEntry OBJECT-TYPE
        SYNTAX	IgmpCounterPortEntry
        MAX-ACCESS	not-accessible
        STATUS	current
        DESCRIPTION    	"An entry in igmpCounterPortTable."
        INDEX          	{ dot1dBasePort }
        ::= { igmpCounterPortTable 1 }

        IgmpCounterPortEntry ::=
		SEQUENCE {
        	igmpCounterPortJoin		    Counter32,
		    igmpCounterPortLeave		Counter32,
	  	    igmpCounterPortActiveGroup	INTEGER,
		    igmpCounterPortQuery		Counter32
        }

        igmpCounterPortJoin OBJECT-TYPE
        SYNTAX  Counter32
        MAX-ACCESS  read-only
        STATUS  current
        DESCRIPTION
                      	"Join counter for the port."
        ::= { igmpCounterPortEntry 1 }

        igmpCounterPortLeave OBJECT-TYPE
        SYNTAX  Counter32
        MAX-ACCESS  read-only
        STATUS  current
        DESCRIPTION
                      	"Leave counter for the port."
        ::= { igmpCounterPortEntry 2 }

        igmpCounterPortActiveGroup OBJECT-TYPE
        SYNTAX  INTEGER
        MAX-ACCESS  read-only
        STATUS  current
        DESCRIPTION
                      	"Current active group for the port"
        ::= { igmpCounterPortEntry 3 }

        igmpCounterPortQuery OBJECT-TYPE
        SYNTAX  Counter32
        MAX-ACCESS  read-only
        STATUS  current
        DESCRIPTION
                      	"Query counter for the port."
        ::= { igmpCounterPortEntry 4 }
------------------------------------------
--  igmp counters for specific vid
-- igmpCounterVlanTable

        igmpCounterVlanTable OBJECT-TYPE
        SYNTAX	SEQUENCE OF IgmpCounterVlanEntry
        MAX-ACCESS  not-accessible
        STATUS  current
        DESCRIPTION
                 	""
        ::= { multicastStatus 5 }

	igmpCounterVlanEntry OBJECT-TYPE
        SYNTAX	IgmpCounterVlanEntry
        MAX-ACCESS	not-accessible
        STATUS	current
        DESCRIPTION    	"An entry in igmpCounterVlanTable."
        INDEX          	{ dot1qVlanIndex  }
        ::= { igmpCounterVlanTable 1 }

        IgmpCounterVlanEntry ::=
           SEQUENCE {
        	igmpCounterVlanJoin		Counter32,
		igmpCounterVlanLeave		Counter32,
		igmpCounterVlanActiveGroup	INTEGER,
		igmpCounterVlanQuery		Counter32
           }

        igmpCounterVlanJoin OBJECT-TYPE
        SYNTAX  Counter32
        MAX-ACCESS  read-only
        STATUS  current
        DESCRIPTION
                      	"Join counter for the Vlan."
        ::= { igmpCounterVlanEntry 1 }

        igmpCounterVlanLeave OBJECT-TYPE
        SYNTAX  Counter32
        MAX-ACCESS  read-only
        STATUS  current
        DESCRIPTION
                      	"Leave counter for the Vlan."
        ::= { igmpCounterVlanEntry 2 }

        igmpCounterVlanActiveGroup OBJECT-TYPE
        SYNTAX  INTEGER
        MAX-ACCESS  read-only
        STATUS  current
        DESCRIPTION
                      	"Current active group for the Vlan"
        ::= { igmpCounterVlanEntry 3 }

        igmpCounterVlanQuery OBJECT-TYPE
        SYNTAX  Counter32
        MAX-ACCESS  read-only
        STATUS  current
        DESCRIPTION
                      	"Query counter for the Vlan."
        ::= { igmpCounterVlanEntry 4 }

        multicastCurrentGroupStatusTable	OBJECT-TYPE
        SYNTAX	SEQUENCE OF MulticastCurrentGroupStatusEntry
        MAX-ACCESS  not-accessible
        STATUS  current
        DESCRIPTION
                      	""
        ::= { multicastStatus 6 }

	multicastCurrentGroupStatusEntry OBJECT-TYPE
        SYNTAX	MulticastCurrentGroupStatusEntry
        MAX-ACCESS	not-accessible
        STATUS	current
        DESCRIPTION    	"An entry in multicastCurrentGroupStatusTable."
        INDEX          	{ multicastStatusVlanID, multicastStatusGroup }
        ::= { multicastCurrentGroupStatusTable 1 }

        MulticastCurrentGroupStatusEntry ::=
	SEQUENCE {
        	multicastCurrentNumberOfActivePort    INTEGER
         }

        multicastCurrentNumberOfActivePort OBJECT-TYPE
        SYNTAX  INTEGER
        MAX-ACCESS  read-only
        STATUS  current
        DESCRIPTION
                      	"Current number Of active port."
        ::= { multicastCurrentGroupStatusEntry 1 }

-- multicastClientSrcIp

        multicastClientSrcIpTable	OBJECT-TYPE
        SYNTAX	SEQUENCE OF MulticastClientSrcIpEntry
        MAX-ACCESS  not-accessible
        STATUS  current
        DESCRIPTION
                      	""
        ::= { multicastStatus 7 }

	multicastClientSrcIpEntry OBJECT-TYPE
        SYNTAX	MulticastClientSrcIpEntry
        MAX-ACCESS	not-accessible
        STATUS	current
        DESCRIPTION    	"An entry in multicastClientSrcIpTable."
        INDEX          	{ multicastStatusVlanID, multicastStatusPort, multicastStatusGroup, multicastClientSrcIpIndex }
        ::= { multicastClientSrcIpTable 1 }

        MulticastClientSrcIpEntry ::=
	SEQUENCE {
        	multicastClientSrcIpIndex    INTEGER,
        	multicastClientSrcIpAddress	IpAddress
         }

        multicastClientSrcIpIndex OBJECT-TYPE
        SYNTAX  INTEGER
        MAX-ACCESS  read-only
        STATUS  current
        DESCRIPTION
                      	""
        ::= { multicastClientSrcIpEntry 1 }

        multicastClientSrcIpAddress OBJECT-TYPE
        SYNTAX  IpAddress
        MAX-ACCESS  read-only
        STATUS  current
        DESCRIPTION
                      	""
        ::= { multicastClientSrcIpEntry 2 }

-- mgmdStatusTable

        mgmdStatusTable	OBJECT-TYPE
        SYNTAX	SEQUENCE OF MGMDStatusEntry
        MAX-ACCESS  not-accessible
        STATUS  current
        DESCRIPTION
                 	""
        ::= { multicastStatus 8 }

	mgmdStatusEntry OBJECT-TYPE
        SYNTAX	MGMDStatusEntry
        MAX-ACCESS	not-accessible
        STATUS	current
        DESCRIPTION    	"An entry in mgmdStatusTable."
        INDEX          	{ mgmdStatusVlanID, mgmdStatusPort, mgmdStatusGroupAddressType, mgmdStatusGroupAddress }
        ::= { mgmdStatusTable 1 }

        MGMDStatusEntry ::=
	SEQUENCE {
        	mgmdStatusIndex			INTEGER,
        	mgmdStatusVlanID		INTEGER,
        	mgmdStatusPort			INTEGER,
    		mgmdStatusGroupAddressType	InetAddressType,
   			mgmdStatusGroupAddress		InetAddress ,
   			mgmdStatusGroupFilterMode	INTEGER,
   			mgmdStatusGroupUpTime	DisplayString
         }

        mgmdStatusIndex OBJECT-TYPE
        SYNTAX  INTEGER
        MAX-ACCESS  read-only
        STATUS  current
        DESCRIPTION
                      	""
        ::= { mgmdStatusEntry 1 }

        mgmdStatusVlanID OBJECT-TYPE
        SYNTAX  INTEGER
        MAX-ACCESS  read-only
        STATUS  current
        DESCRIPTION
                      	""
        ::= { mgmdStatusEntry 2 }

        mgmdStatusPort OBJECT-TYPE
        SYNTAX  INTEGER
        MAX-ACCESS  read-only
        STATUS  current
        DESCRIPTION
                      	""
        ::= { mgmdStatusEntry 3 }

        mgmdStatusGroupAddressType OBJECT-TYPE
        SYNTAX  InetAddressType { ipv4(1), ipv6(2) }
        MAX-ACCESS  read-only
        STATUS  current
        DESCRIPTION
              "The address type of the mgmdStatusGroupAddress entry."
        ::= { mgmdStatusEntry 4 }

        mgmdStatusGroupAddress OBJECT-TYPE
        SYNTAX  InetAddress (SIZE(4|16))
        MAX-ACCESS  read-only
        STATUS  current
        DESCRIPTION
                      	""
        ::= { mgmdStatusEntry 5 }

 		mgmdStatusGroupFilterMode OBJECT-TYPE
    	SYNTAX     INTEGER {include (1),exclude (2) }
		MAX-ACCESS read-only
		STATUS     current
		DESCRIPTION
            "The current cache state, applicable to MGMDv3-compatible
            nodes.  The value indicates whether the state is INCLUDE or
            EXCLUDE."

		::= { mgmdStatusEntry 6 }

	     mgmdStatusGroupUpTime OBJECT-TYPE
    	SYNTAX     DisplayString
		MAX-ACCESS read-only
		STATUS     current
		DESCRIPTION
            "The value specifies the group up time of indicated
            multicast group."

		::= { mgmdStatusEntry 7 }

-- mgmdCountTable
        mgmdCountTable	OBJECT-TYPE
        SYNTAX	SEQUENCE OF MGMDCountEntry
        MAX-ACCESS  not-accessible
        STATUS  current
        DESCRIPTION
                 	"A count table of igmp/MLD query/report/leave message."
        ::= { multicastStatus 9 }

	mgmdCountEntry OBJECT-TYPE
        SYNTAX	MGMDCountEntry
        MAX-ACCESS	not-accessible
        STATUS	current
        DESCRIPTION    	"An entry in mgmdCountTable."
        INDEX          	{ mgmdCountIndex }
        ::= { mgmdCountTable 1 }

        MGMDCountEntry ::=
		SEQUENCE {
        	mgmdCountIndex    		INTEGER,
        	mgmdCountInQuery		INTEGER,
        	mgmdCountInReport		INTEGER,
        	mgmdCountInLeave		INTEGER,
        	mgmdCountInQueryDrop   	INTEGER,
        	mgmdCountInReportDrop   INTEGER,
        	mgmdCountInLeaveDrop   	INTEGER,
        	mgmdCountOutQuery   	INTEGER,
        	mgmdCountOutReport   	INTEGER,
        	mgmdCountOutLeave   	INTEGER
        }

        mgmdCountIndex OBJECT-TYPE
        SYNTAX  INTEGER
        MAX-ACCESS  read-only
        STATUS  current
        DESCRIPTION
                      	"Index of mgmdCountEntry. 0 means total count in whole system"
        ::= { mgmdCountEntry 1 }

        mgmdCountInQuery OBJECT-TYPE
        SYNTAX  INTEGER
        MAX-ACCESS  read-only
        STATUS  current
        DESCRIPTION
                      	""
        ::= { mgmdCountEntry 2 }

        mgmdCountInReport OBJECT-TYPE
        SYNTAX  INTEGER
        MAX-ACCESS  read-only
        STATUS  current
        DESCRIPTION
                      	""
        ::= { mgmdCountEntry 3 }

        mgmdCountInLeave OBJECT-TYPE
        SYNTAX  INTEGER
        MAX-ACCESS  read-only
        STATUS  current
        DESCRIPTION
                      	""
        ::= { mgmdCountEntry 4 }

        mgmdCountInQueryDrop OBJECT-TYPE
        SYNTAX  INTEGER
        MAX-ACCESS  read-only
        STATUS  current
        DESCRIPTION
                      	""
        ::= { mgmdCountEntry 5 }

        mgmdCountInReportDrop OBJECT-TYPE
        SYNTAX  INTEGER
        MAX-ACCESS  read-only
        STATUS  current
        DESCRIPTION
                      	""
        ::= { mgmdCountEntry 6 }

        mgmdCountInLeaveDrop OBJECT-TYPE
        SYNTAX  INTEGER
        MAX-ACCESS  read-only
        STATUS  current
        DESCRIPTION
                      	""
        ::= { mgmdCountEntry 7 }

        mgmdCountOutQuery OBJECT-TYPE
        SYNTAX  INTEGER
        MAX-ACCESS  read-only
        STATUS  current
        DESCRIPTION
                      	""
        ::= { mgmdCountEntry 8 }

        mgmdCountOutReport OBJECT-TYPE
        SYNTAX  INTEGER
        MAX-ACCESS  read-only
        STATUS  current
        DESCRIPTION
                      	""
        ::= { mgmdCountEntry 9 }

        mgmdCountOutLeave OBJECT-TYPE
        SYNTAX  INTEGER
        MAX-ACCESS  read-only
        STATUS  current
        DESCRIPTION
                      	""
        ::= { mgmdCountEntry 10 }

-- mgmdVlanStatusTable
       mgmdVlanStatusTable	OBJECT-TYPE
        SYNTAX	SEQUENCE OF MGMDVlanStatusEntry
        MAX-ACCESS  not-accessible
        STATUS  current
        DESCRIPTION
                 	""
        ::= { multicastStatus 10 }


	mgmdVlanStatusEntry OBJECT-TYPE
        SYNTAX	MGMDVlanStatusEntry
        MAX-ACCESS	not-accessible
        STATUS	current
        DESCRIPTION    	"An entry in mgmdVlanStatusTable."
        INDEX          	{ mgmdVlanStatusVlanID }
        ::= { mgmdVlanStatusTable 1 }

        MGMDVlanStatusEntry ::=
	SEQUENCE {
        	mgmdVlanStatusVlanID    INTEGER,
        	mgmdVlanStatusType	INTEGER,
        	mgmdVlanQueryPort	PortList,
        	mgmdVlanQuerySrcIpType	InetAddressType,
        	mgmdVlanQuerySrcIp	InetAddress
         }

        mgmdVlanStatusVlanID OBJECT-TYPE
        SYNTAX  INTEGER
        MAX-ACCESS  read-only
        STATUS  current
        DESCRIPTION
                      	""
        ::= { mgmdVlanStatusEntry 1 }

        mgmdVlanStatusType OBJECT-TYPE
        SYNTAX  INTEGER {
			dynamic(1),
			mvr (2),
			static(3)
        }
        MAX-ACCESS  read-only
        STATUS  current
        DESCRIPTION
                      	""
        ::= { mgmdVlanStatusEntry 2 }

        mgmdVlanQueryPort OBJECT-TYPE
        SYNTAX  PortList
        MAX-ACCESS  read-only
        STATUS  current
        DESCRIPTION
                      	""
        ::= { mgmdVlanStatusEntry 3 }

        mgmdVlanQuerySrcIpType OBJECT-TYPE
        SYNTAX  InetAddressType { ipv4(1), ipv6(2) }
        MAX-ACCESS  read-only
        STATUS  current
        DESCRIPTION
              "The address type of the mgmdVlanQuerySrcIp entry."
        ::= { mgmdVlanStatusEntry 4 }

        mgmdVlanQuerySrcIp OBJECT-TYPE
        SYNTAX  InetAddress (SIZE(4|16))
        MAX-ACCESS  read-only
        STATUS  current
        DESCRIPTION
                      	""
        ::= { mgmdVlanStatusEntry 5 }

-- mgmdCounterPortTable

        mgmdCounterPortTable OBJECT-TYPE
        SYNTAX	SEQUENCE OF MGMDCounterPortEntry
        MAX-ACCESS  not-accessible
        STATUS  current
        DESCRIPTION
                 	""
        ::= { multicastStatus 11 }

	mgmdCounterPortEntry OBJECT-TYPE
        SYNTAX	MGMDCounterPortEntry
        MAX-ACCESS	not-accessible
        STATUS	current
        DESCRIPTION    	"An entry in mgmdCounterPortTable."
        INDEX          	{ dot1dBasePort }
        ::= { mgmdCounterPortTable 1 }

        MGMDCounterPortEntry ::=
		SEQUENCE {
        	mgmdCounterPortV1ReportIn				Counter32,
        	mgmdCounterPortV2ReportIn				Counter32,
        	mgmdCounterPortV3ReportIn				Counter32,
        	mgmdCounterPortLeaveIn		    		Counter32,
        	mgmdCounterPortTotalReportIn			Counter32,
        	mgmdCounterPortV1ReportOut				Counter32,
        	mgmdCounterPortV2ReportOut				Counter32,
        	mgmdCounterPortV3ReportOut				Counter32,
        	mgmdCounterPortLeaveOut		    		Counter32,
        	mgmdCounterPortTotalReportOut			Counter32,
        	mgmdCounterPortV1QueryIn				Counter32,
        	mgmdCounterPortV2QueryIn				Counter32,
        	mgmdCounterPortV3QueryIn				Counter32,
        	mgmdCounterPortTotalQueryIn				Counter32,
        	mgmdCounterPortV1QueryOut				Counter32,
        	mgmdCounterPortV2QueryOut				Counter32,
        	mgmdCounterPortV3QueryOut				Counter32,
        	mgmdCounterPortTotalQueryOut			Counter32,
		    mgmdCounterPortRecordDropMaxGrpLimit	Counter32,
		    mgmdCounterPortRecordDropGrpFilter		Counter32,
		    mgmdCounterPortRecordDropMVR	   		Counter32,
		    mgmdCounterPortRecordDropOther	   		Counter32,
			    mgmdCounterPortDropRateLimit		Counter32,
		    mgmdCounterPortReportDropOther	   		Counter32,
		    mgmdCounterPortQueryDropOther    		Counter32
       }

        mgmdCounterPortV1ReportIn OBJECT-TYPE
        SYNTAX  Counter32
        MAX-ACCESS  read-only
        STATUS  current
        DESCRIPTION
                      	"Received V1 Report counter for indicated port."
        ::= { mgmdCounterPortEntry 1 }

        mgmdCounterPortV2ReportIn OBJECT-TYPE
        SYNTAX  Counter32
        MAX-ACCESS  read-only
        STATUS  current
        DESCRIPTION
                      	"Received V2 Report counter for indicated port."
        ::= { mgmdCounterPortEntry 2 }

        mgmdCounterPortV3ReportIn OBJECT-TYPE
        SYNTAX  Counter32
        MAX-ACCESS  read-only
        STATUS  current
        DESCRIPTION
                      	"Received V3 Report counter for indicated port."
        ::= { mgmdCounterPortEntry 3 }

        mgmdCounterPortLeaveIn OBJECT-TYPE
        SYNTAX  Counter32
        MAX-ACCESS  read-only
        STATUS  current
        DESCRIPTION
                      	"Received Leave counter for indicated port."
        ::= { mgmdCounterPortEntry 4 }

        mgmdCounterPortTotalReportIn OBJECT-TYPE
        SYNTAX  Counter32
        MAX-ACCESS  read-only
        STATUS  current
        DESCRIPTION
                      	"Received total Report counter for indicated port."
        ::= { mgmdCounterPortEntry 5 }

        mgmdCounterPortV1ReportOut OBJECT-TYPE
        SYNTAX  Counter32
	   MAX-ACCESS 	read-only
	   STATUS	current
        DESCRIPTION
                      	"Transmitted V1 Report counter for indicated port."
        ::= { mgmdCounterPortEntry 6 }

        mgmdCounterPortV2ReportOut OBJECT-TYPE
        SYNTAX  Counter32
        MAX-ACCESS  read-only
        STATUS  current
        DESCRIPTION
                      	"Transmitted V2 Report counter for indicated port."
        ::= { mgmdCounterPortEntry 7 }

        mgmdCounterPortV3ReportOut OBJECT-TYPE
        SYNTAX  Counter32
	   MAX-ACCESS 	read-only
	   STATUS	current
        DESCRIPTION
                      	"Transmitted V3 Report counter for indicated port."
        ::= { mgmdCounterPortEntry 8 }

        mgmdCounterPortLeaveOut OBJECT-TYPE
        SYNTAX  Counter32
	   MAX-ACCESS 	read-only
	   STATUS	current
        DESCRIPTION
                      	"Transmitted Leave counter for indicated port."
        ::= { mgmdCounterPortEntry 9 }

        mgmdCounterPortTotalReportOut OBJECT-TYPE
        SYNTAX  Counter32
	   MAX-ACCESS 	read-only
	   STATUS	current
        DESCRIPTION
                      	"Transmitted total Report counter for indicated port."
        ::= { mgmdCounterPortEntry 10 }

        mgmdCounterPortV1QueryIn OBJECT-TYPE
        SYNTAX  Counter32
	   MAX-ACCESS 	read-only
	   STATUS	current
        DESCRIPTION
                      	"Received V1 Query counter for indicated port."
        ::= { mgmdCounterPortEntry 11 }

        mgmdCounterPortV2QueryIn OBJECT-TYPE
        SYNTAX  Counter32
	   MAX-ACCESS 	read-only
	   STATUS	current
        DESCRIPTION
                      	"Received V2 Query counter for indicated port."
        ::= { mgmdCounterPortEntry 12 }

        mgmdCounterPortV3QueryIn OBJECT-TYPE
        SYNTAX  Counter32
	   MAX-ACCESS 	read-only
	   STATUS	current
        DESCRIPTION
                      	"Received V3 Query counter for indicated port."
        ::= { mgmdCounterPortEntry 13 }

        mgmdCounterPortTotalQueryIn OBJECT-TYPE
        SYNTAX  Counter32
	   MAX-ACCESS 	read-only
	   STATUS	current
        DESCRIPTION
                      	"Received total Query counter for indicated port."
        ::= { mgmdCounterPortEntry 14 }

        mgmdCounterPortV1QueryOut OBJECT-TYPE
        SYNTAX  Counter32
	   MAX-ACCESS 	read-only
	   STATUS	current
        DESCRIPTION
                      	"Transmitted V1 Query counter for indicated port."
        ::= { mgmdCounterPortEntry 15 }

        mgmdCounterPortV2QueryOut OBJECT-TYPE
        SYNTAX  Counter32
	   MAX-ACCESS 	read-only
	   STATUS	current
        DESCRIPTION
                      	"Transmitted V2 Query counter for indicated port."
        ::= { mgmdCounterPortEntry 16 }

        mgmdCounterPortV3QueryOut OBJECT-TYPE
        SYNTAX  Counter32
	   MAX-ACCESS 	read-only
	   STATUS	current
        DESCRIPTION
                      	"Transmitted V3 Query counter for indicated port."
        ::= { mgmdCounterPortEntry 17 }

        mgmdCounterPortTotalQueryOut OBJECT-TYPE
        SYNTAX  Counter32
	   MAX-ACCESS 	read-only
	   STATUS	current
        DESCRIPTION
                      	"Transmitted total Query counter for indicated port."
        ::= { mgmdCounterPortEntry 18 }

        mgmdCounterPortRecordDropMaxGrpLimit OBJECT-TYPE
        SYNTAX  Counter32
        MAX-ACCESS  read-only
        STATUS  current
        DESCRIPTION
                      	"Record drop by max group limit counter for indicated port."
        ::= { mgmdCounterPortEntry 19 }

        mgmdCounterPortRecordDropGrpFilter OBJECT-TYPE
        SYNTAX  Counter32
	   MAX-ACCESS 	read-only
	   STATUS	current
        DESCRIPTION
                      	"Record drop by group filter counter for indicated port."
        ::= { mgmdCounterPortEntry 20 }

        mgmdCounterPortRecordDropMVR OBJECT-TYPE
        SYNTAX  Counter32
	   MAX-ACCESS 	read-only
	   STATUS	current
        DESCRIPTION
                      	"Record drop by MVR counter for indicated port."
        ::= { mgmdCounterPortEntry 21 }

        mgmdCounterPortRecordDropOther OBJECT-TYPE
        SYNTAX  Counter32
        MAX-ACCESS  read-only
        STATUS  current
        DESCRIPTION
                      	"Record drop by other counter for indicated port."
        ::= { mgmdCounterPortEntry 22 }

        mgmdCounterPortDropRateLimit OBJECT-TYPE
        SYNTAX  Counter32
	   MAX-ACCESS 	read-only
	   STATUS	current
        DESCRIPTION
                      	"Packet drop by rate limit counter for indicated port."
        ::= { mgmdCounterPortEntry 23 }

        mgmdCounterPortReportDropOther OBJECT-TYPE
        SYNTAX  Counter32
	   MAX-ACCESS 	read-only
	   STATUS	current
        DESCRIPTION
                      	"Report drop by other counter for indicated port."
        ::= { mgmdCounterPortEntry 24 }


        mgmdCounterPortQueryDropOther OBJECT-TYPE
        SYNTAX  Counter32
        MAX-ACCESS  read-only
        STATUS  current
        DESCRIPTION
                      	"Query drop by other counter for indicated port."
        ::= { mgmdCounterPortEntry 25 }

------------------------------------------
--  mgmd counters for specific vid
-- mgmdCounterVlanTable

        mgmdCounterVlanTable OBJECT-TYPE
        SYNTAX	SEQUENCE OF MGMDCounterVlanEntry
        MAX-ACCESS  not-accessible
        STATUS  current
        DESCRIPTION
                 	""
        ::= { multicastStatus 12 }

	mgmdCounterVlanEntry OBJECT-TYPE
        SYNTAX	MGMDCounterVlanEntry
        MAX-ACCESS	not-accessible
        STATUS	current
        DESCRIPTION    	"An entry in mgmdCounterVlanTable."
        INDEX          	{ dot1qVlanIndex  }
        ::= { mgmdCounterVlanTable 1 }

        MGMDCounterVlanEntry ::=
		SEQUENCE {
        	mgmdCounterVlanV1ReportIn				Counter32,
        	mgmdCounterVlanV2ReportIn				Counter32,
        	mgmdCounterVlanV3ReportIn				Counter32,
        	mgmdCounterVlanLeaveIn		    		Counter32,
        	mgmdCounterVlanTotalReportIn			Counter32,
        	mgmdCounterVlanV1ReportOut				Counter32,
        	mgmdCounterVlanV2ReportOut				Counter32,
        	mgmdCounterVlanV3ReportOut				Counter32,
        	mgmdCounterVlanLeaveOut				Counter32,
        	mgmdCounterVlanTotalReportOut			Counter32,
        	mgmdCounterVlanV1QueryIn				Counter32,
        	mgmdCounterVlanV2QueryIn				Counter32,
        	mgmdCounterVlanV3QueryIn				Counter32,
        	mgmdCounterVlanTotalQueryIn				Counter32,
        	mgmdCounterVlanV1QueryOut				Counter32,
        	mgmdCounterVlanV2QueryOut				Counter32,
        	mgmdCounterVlanV3QueryOut				Counter32,
        	mgmdCounterVlanTotalQueryOut			Counter32,
		    mgmdCounterVlanRecordDropMaxGrpLimit	Counter32,
		    mgmdCounterVlanRecordDropGrpFilter		Counter32,
		    mgmdCounterVlanRecordDropMVR	   		Counter32,
		    mgmdCounterVlanRecordDropOther	   		Counter32,
		    mgmdCounterVlanDropRateLimit		Counter32,
		    mgmdCounterVlanReportDropOther	   		Counter32,
		    mgmdCounterVlanQueryDropOther    		Counter32
        }

        mgmdCounterVlanV1ReportIn OBJECT-TYPE
        SYNTAX  Counter32
        MAX-ACCESS  read-only
        STATUS  current
        DESCRIPTION
                      	"Received V1 Report counter for indicated Vlan."
        ::= { mgmdCounterVlanEntry 1 }

        mgmdCounterVlanV2ReportIn OBJECT-TYPE
        SYNTAX  Counter32
        MAX-ACCESS  read-only
        STATUS  current
        DESCRIPTION
                      	"Received V2 Report counter for indicated Vlan."
        ::= { mgmdCounterVlanEntry 2 }

        mgmdCounterVlanV3ReportIn OBJECT-TYPE
        SYNTAX  Counter32
        MAX-ACCESS  read-only
        STATUS  current
        DESCRIPTION
                      	"Received V3 Report counter for indicated Vlan."
        ::= { mgmdCounterVlanEntry 3 }

        mgmdCounterVlanLeaveIn OBJECT-TYPE
        SYNTAX  Counter32
        MAX-ACCESS  read-only
        STATUS  current
        DESCRIPTION
                      	"Received Leave counter for indicated Vlan."
        ::= { mgmdCounterVlanEntry 4 }

        mgmdCounterVlanTotalReportIn OBJECT-TYPE
        SYNTAX  Counter32
        MAX-ACCESS  read-only
        STATUS  current
        DESCRIPTION
                      	"Received total Report counter for indicated Vlan."
        ::= { mgmdCounterVlanEntry 5 }

        mgmdCounterVlanV1ReportOut OBJECT-TYPE
        SYNTAX  Counter32
        MAX-ACCESS  read-only
        STATUS  current
        DESCRIPTION
                      	"Transmitted V1 Report counter for indicated Vlan."
        ::= { mgmdCounterVlanEntry 6 }

        mgmdCounterVlanV2ReportOut OBJECT-TYPE
        SYNTAX  Counter32
        MAX-ACCESS  read-only
        STATUS  current
        DESCRIPTION
                      	"Transmitted V2 Report counter for indicated Vlan."
        ::= { mgmdCounterVlanEntry 7 }

        mgmdCounterVlanV3ReportOut OBJECT-TYPE
        SYNTAX  Counter32
        MAX-ACCESS  read-only
        STATUS  current
        DESCRIPTION
                      	"Transmitted V3 Report counter for indicated Vlan."
        ::= { mgmdCounterVlanEntry 8 }

        mgmdCounterVlanLeaveOut OBJECT-TYPE
        SYNTAX  Counter32
        MAX-ACCESS  read-only
        STATUS  current
        DESCRIPTION
                      	"Transmitted Leave counter for indicated Vlan."
        ::= { mgmdCounterVlanEntry 9 }


        mgmdCounterVlanTotalReportOut OBJECT-TYPE
        SYNTAX  Counter32
        MAX-ACCESS  read-only
        STATUS  current
        DESCRIPTION
                      	"Transmitted total Report counter for indicated Vlan."
        ::= { mgmdCounterVlanEntry 10 }

        mgmdCounterVlanV1QueryIn OBJECT-TYPE
        SYNTAX  Counter32
        MAX-ACCESS  read-only
        STATUS  current
        DESCRIPTION
                      	"Received V1 Query counter for indicated Vlan."
        ::= { mgmdCounterVlanEntry 11 }

        mgmdCounterVlanV2QueryIn OBJECT-TYPE
        SYNTAX  Counter32
        MAX-ACCESS  read-only
        STATUS  current
        DESCRIPTION
                      	"Received V2 Query counter for indicated Vlan."
        ::= { mgmdCounterVlanEntry 12 }

        mgmdCounterVlanV3QueryIn OBJECT-TYPE
        SYNTAX  Counter32
	   MAX-ACCESS 	read-only
	   STATUS	current
        DESCRIPTION
                      	"Received V3 Query counter for indicated Vlan."
        ::= { mgmdCounterVlanEntry 13 }

        mgmdCounterVlanTotalQueryIn OBJECT-TYPE
        SYNTAX  Counter32
        MAX-ACCESS  read-only
        STATUS  current
        DESCRIPTION
                      	"Received total Query counter for indicated Vlan."
        ::= { mgmdCounterVlanEntry 14 }

        mgmdCounterVlanV1QueryOut OBJECT-TYPE
        SYNTAX  Counter32
	   MAX-ACCESS 	read-only
	   STATUS	current
        DESCRIPTION
                      	"Transmitted V1 Query counter for indicated Vlan."
        ::= { mgmdCounterVlanEntry 15 }

        mgmdCounterVlanV2QueryOut OBJECT-TYPE
        SYNTAX  Counter32
	   MAX-ACCESS 	read-only
	   STATUS	current
        DESCRIPTION
                      	"Transmitted V2 Query counter for indicated Vlan."
        ::= { mgmdCounterVlanEntry 16 }

        mgmdCounterVlanV3QueryOut OBJECT-TYPE
        SYNTAX  Counter32
	   MAX-ACCESS 	read-only
	   STATUS	current
        DESCRIPTION
                      	"Transmitted V3 Query counter for indicated Vlan."
        ::= { mgmdCounterVlanEntry 17 }

        mgmdCounterVlanTotalQueryOut OBJECT-TYPE
        SYNTAX  Counter32
	   MAX-ACCESS 	read-only
	   STATUS	current
        DESCRIPTION
                      	"Transmitted total Query counter for indicated Vlan."
        ::= { mgmdCounterVlanEntry 18 }

        mgmdCounterVlanRecordDropMaxGrpLimit OBJECT-TYPE
        SYNTAX  Counter32
	   MAX-ACCESS 	read-only
	   STATUS	current
        DESCRIPTION
                      	"Record drop by max group limit counter for indicated Vlan."
        ::= { mgmdCounterVlanEntry 19 }

        mgmdCounterVlanRecordDropGrpFilter OBJECT-TYPE
        SYNTAX  Counter32
	   MAX-ACCESS 	read-only
	   STATUS	current
        DESCRIPTION
                      	"Record drop by group filter counter for indicated Vlan."
        ::= { mgmdCounterVlanEntry 20 }

        mgmdCounterVlanRecordDropMVR OBJECT-TYPE
        SYNTAX  Counter32
	   MAX-ACCESS 	read-only
	   STATUS	current
        DESCRIPTION
                      	"Record drop by MVR counter for indicated Vlan."
        ::= { mgmdCounterVlanEntry 21 }

        mgmdCounterVlanRecordDropOther OBJECT-TYPE
        SYNTAX  Counter32
	   MAX-ACCESS 	read-only
	   STATUS	current
        DESCRIPTION
                      	"Record drop by other counter for indicated Vlan."
        ::= { mgmdCounterVlanEntry 22 }

        mgmdCounterVlanDropRateLimit OBJECT-TYPE
        SYNTAX  Counter32
        MAX-ACCESS  read-only
        STATUS  current
        DESCRIPTION
                      	"Report drop by rate limit counter for indicated Vlan."
        ::= { mgmdCounterVlanEntry 23 }

        mgmdCounterVlanReportDropOther OBJECT-TYPE
        SYNTAX  Counter32
	   MAX-ACCESS 	read-only
	   STATUS	current
        DESCRIPTION
                      	"Report drop by other counter for indicated Vlan."
        ::= { mgmdCounterVlanEntry 24 }


        mgmdCounterVlanQueryDropOther OBJECT-TYPE
        SYNTAX  Counter32
	   MAX-ACCESS 	read-only
	   STATUS	current
        DESCRIPTION
                      	"Query drop by other counter for indicated Vlan."
        ::= { mgmdCounterVlanEntry 25 }

 -- mgmdCurrentGroupStatusTable

        mgmdCurrentGroupStatusTable	OBJECT-TYPE
        SYNTAX	SEQUENCE OF MGMDCurrentGroupStatusEntry
        MAX-ACCESS  not-accessible
        STATUS  current
        DESCRIPTION
                 	""
        ::= { multicastStatus 13 }

	mgmdCurrentGroupStatusEntry OBJECT-TYPE
        SYNTAX	MGMDCurrentGroupStatusEntry
        MAX-ACCESS	not-accessible
        STATUS	current
        DESCRIPTION    	"An entry in mgmdCurrentGroupStatusTable."
        INDEX          	{ mgmdStatusVlanID, mgmdStatusGroupAddressType, mgmdStatusGroupAddress }
        ::= { mgmdCurrentGroupStatusTable 1 }

        MGMDCurrentGroupStatusEntry ::=
	SEQUENCE {
        	mgmdCurrentNumberOfActivePort    INTEGER
         }

        mgmdCurrentNumberOfActivePort OBJECT-TYPE
        SYNTAX  INTEGER
        MAX-ACCESS  read-only
        STATUS  current
        DESCRIPTION
                      	"Current number Of active port."
        ::= { mgmdCurrentGroupStatusEntry 1 }

-- mgmdClientSrcIp

        mgmdClientSrcIpTable	OBJECT-TYPE
        SYNTAX	SEQUENCE OF MGMDClientSrcIpEntry
        MAX-ACCESS  not-accessible
        STATUS  current
        DESCRIPTION
                 	""
        ::= { multicastStatus 14 }

	mgmdClientSrcIpEntry OBJECT-TYPE
        SYNTAX	MGMDClientSrcIpEntry
        MAX-ACCESS	not-accessible
        STATUS	current
        DESCRIPTION    	"An entry in mgmdClientSrcIpTable."
        INDEX          	{mgmdClientSrcIpAddressType,mgmdClientSrcIpIndex, mgmdStatusVlanID, mgmdStatusPort,  mgmdStatusGroupAddress}
        ::= { mgmdClientSrcIpTable 1 }

        MGMDClientSrcIpEntry ::=
		SEQUENCE {
        	mgmdClientSrcIpIndex    	INTEGER,
        	mgmdClientSrcIpAddressType	InetAddressType,
        	mgmdClientSrcIpAddress		InetAddress
         }

        mgmdClientSrcIpIndex OBJECT-TYPE
        SYNTAX  INTEGER
        MAX-ACCESS  read-only
        STATUS  current
        DESCRIPTION
                      	""
        ::= { mgmdClientSrcIpEntry 1 }

        mgmdClientSrcIpAddressType OBJECT-TYPE
        SYNTAX  InetAddressType { ipv4(1), ipv6(2) }
	    MAX-ACCESS read-only
	    STATUS current
        DESCRIPTION
                      	""
        ::= { mgmdClientSrcIpEntry 2 }

        mgmdClientSrcIpAddress OBJECT-TYPE
        SYNTAX  InetAddress (SIZE(4|16))
	    MAX-ACCESS read-only
	    STATUS current
        DESCRIPTION
                      	""
        ::= { mgmdClientSrcIpEntry 3 }

 -- mgmdSrcListTable

	mgmdSrcListTable OBJECT-TYPE
	SYNTAX     SEQUENCE OF MGMDSrcListEntry
        MAX-ACCESS  not-accessible
        STATUS  current
   	DESCRIPTION
            "The (conceptual) table listing the Source List entries
             corresponding to each interface and multicast group pair
             on a host."

	::= { multicastStatus 15 }

	mgmdSrcListEntry OBJECT-TYPE
    	SYNTAX     MGMDSrcListEntry
    	MAX-ACCESS not-accessible
    	STATUS     current
    	DESCRIPTION
            "An entry (conceptual row) in the mgmdSrcListTable."
	INDEX      { mgmdSrcListAddressType, mgmdStatusVlanID, mgmdStatusPort, mgmdStatusGroupAddress, mgmdSrcListAddress }

	::= { mgmdSrcListTable 1 }

	MGMDSrcListEntry ::= SEQUENCE {
    		mgmdSrcListAddressType      InetAddressType,
    		mgmdSrcListAddress          InetAddress
--		mgmdSrcListExpire           TimeTicks
	}

	mgmdSrcListAddressType OBJECT-TYPE
    	SYNTAX     InetAddressType { ipv4(1), ipv6(2) }
    	MAX-ACCESS not-accessible
    	STATUS     current
	DESCRIPTION
            "The address type of the InetAddress variables in this
            table.  This value applies to the mgmdStatusGroupAddress
            and mgmdSrcListAddress entries."

	::= { mgmdSrcListEntry 1 }

	mgmdSrcListAddress OBJECT-TYPE
    	SYNTAX      InetAddress (SIZE(4|16))
    	MAX-ACCESS not-accessible
    	STATUS     current
   	DESCRIPTION
            "The IP multicast group address for which this entry
            contains information."

	::= { mgmdSrcListEntry 2 }

 -- mgmdPortCounterResetTable

	mgmdPortCounterResetTable OBJECT-TYPE
	SYNTAX     SEQUENCE OF MGMDPortCounterResetEntry
	MAX-ACCESS not-accessible
	STATUS     current
   	DESCRIPTION
            "The (conceptual) table listing all interface entries."

	::= { multicastStatus 16 }

	mgmdPortCounterResetEntry OBJECT-TYPE
    	SYNTAX     MGMDPortCounterResetEntry
        MAX-ACCESS	not-accessible
        STATUS	current
    	DESCRIPTION
            "An entry (conceptual row) in the mgmdPortCounterResetTable."
        INDEX          	{ dot1dBasePort }

	::= { mgmdPortCounterResetTable 1 }

	MGMDPortCounterResetEntry ::= SEQUENCE {
    		mgmdPortCounterReset      INTEGER
        	}

	mgmdPortCounterReset OBJECT-TYPE
    	SYNTAX     INTEGER { enable(1), disable(2) }
    	MAX-ACCESS read-write
    	STATUS     current
	DESCRIPTION
            "Clear per port mgmd counter, always return disable."

	::= { mgmdPortCounterResetEntry 1 }

	mgmdAnyPortCounterReset OBJECT-TYPE
    	SYNTAX     INTEGER { enable(1), disable(2) }
    	MAX-ACCESS read-write
    	STATUS     current
	DESCRIPTION
            "Clear all mgmd port counter, always return disable"

	::= { multicastStatus 17 }

	mgmdAnyVlanCounterReset OBJECT-TYPE
    	SYNTAX     INTEGER { enable(1), disable(2) }
    	MAX-ACCESS read-write
	    STATUS current
	DESCRIPTION
            "Clear all mgmd vlan counter, always return disable"

	::= { multicastStatus 18 }

	igmpchannelCountTable OBJECT-TYPE
		SYNTAX SEQUENCE OF IgmpchannelCountEntry
		MAX-ACCESS  not-accessible
		STATUS  current
		DESCRIPTION
					""
		::= { multicastStatus 19 }

	igmpchannelCountEntry OBJECT-TYPE
		SYNTAX IgmpchannelCountEntry
		MAX-ACCESS not-accessible
		STATUS current
		DESCRIPTION "IGMP channel counters."
		INDEX {
			dot1dBasePort,
			ontNumber,
			ontcard,
			uniPort,
			uniportIgmpchannelUniSvid,
			uniportIgmpchannelUniCvid  }
		::= { igmpchannelCountTable 1 }

	IgmpchannelCountEntry ::=
	SEQUENCE {
		igmpchannelCountInReportV1     INTEGER,
		igmpchannelCountInReportV2     INTEGER,
		igmpchannelCountInReportV3     INTEGER,
		igmpchannelCountInReportLeave  INTEGER,
		igmpchannelCountDropRateLimit  INTEGER,
		igmpchannelCountDropOthers     INTEGER
	}

	igmpchannelCountInReportV1 OBJECT-TYPE
	SYNTAX INTEGER
	MAX-ACCESS read-only
	STATUS current
	DESCRIPTION "The number of ingress IGMPv1 reports."
	::= { igmpchannelCountEntry 1 }

	igmpchannelCountInReportV2 OBJECT-TYPE
	SYNTAX INTEGER
	MAX-ACCESS read-only
	STATUS current
	DESCRIPTION "The number of ingress IGMPv2 reports."
	::= { igmpchannelCountEntry 2 }

	igmpchannelCountInReportV3 OBJECT-TYPE
	SYNTAX INTEGER
	MAX-ACCESS read-only
	STATUS current
	DESCRIPTION "The number of ingress IGMPv3 reports."
	::= { igmpchannelCountEntry 3 }

	igmpchannelCountInReportLeave OBJECT-TYPE
	SYNTAX INTEGER
	MAX-ACCESS read-only
	STATUS current
	DESCRIPTION "The number of ingress Leave reports."
	::= { igmpchannelCountEntry 4 }

	igmpchannelCountDropRateLimit OBJECT-TYPE
	SYNTAX INTEGER
	MAX-ACCESS read-only
	STATUS current
	DESCRIPTION "The number of dropped reports caused by rate limit."
	::= { igmpchannelCountEntry 5 }

	igmpchannelCountDropOthers OBJECT-TYPE
	SYNTAX INTEGER
	MAX-ACCESS read-only
	STATUS current
	DESCRIPTION "The number of dropped reports caused by other reasons."
	::= { igmpchannelCountEntry 6 }

-- igmpchannelStatusTable

	igmpchannelStatusTable OBJECT-TYPE
		SYNTAX SEQUENCE OF IgmpchannelStatusEntry
		MAX-ACCESS  not-accessible
		STATUS  current
		DESCRIPTION
					""
		::= { multicastStatus 20 }

	igmpchannelStatusEntry OBJECT-TYPE
		SYNTAX IgmpchannelStatusEntry
		MAX-ACCESS not-accessible
		STATUS current
		DESCRIPTION "IGMP channel status."
		INDEX {
			igmpchannelStatusVlanID,
			igmpchannelStatusPort,
			igmpchannelStatusGroupAddressType,
			igmpchannelStatusGroupAddress,
			igmpchannelStatusGem
		}
		::= { igmpchannelStatusTable 1 }

	IgmpchannelStatusEntry ::=
	SEQUENCE {
			igmpchannelStatusVlanID				INTEGER,
			igmpchannelStatusPort				INTEGER,
			igmpchannelStatusGroupAddressType	InetAddressType,
			igmpchannelStatusGroupAddress		InetAddress,
			igmpchannelStatusGem				INTEGER,
			igmpchannelStatusPortAid			DisplayString,
			igmpchannelStatusUniVid				INTEGER,
			igmpchannelStatusGroupFilterMode	INTEGER,
			igmpchannelStatusGroupUpTime		DisplayString
		}

        igmpchannelStatusVlanID OBJECT-TYPE
        SYNTAX  INTEGER
        MAX-ACCESS  read-only
        STATUS  current
        DESCRIPTION
                      	""
        ::= { igmpchannelStatusEntry 1 }

        igmpchannelStatusPort OBJECT-TYPE
        SYNTAX  INTEGER
        MAX-ACCESS  read-only
        STATUS  current
        DESCRIPTION
                      	""
        ::= { igmpchannelStatusEntry 2 }

        igmpchannelStatusGroupAddressType OBJECT-TYPE
        SYNTAX  InetAddressType { ipv4(1), ipv6(2) }
        MAX-ACCESS  read-only
        STATUS  current
        DESCRIPTION
              "The address type of the igmpchannelStatusGroupAddress entry."
        ::= { igmpchannelStatusEntry 3 }

        igmpchannelStatusGroupAddress OBJECT-TYPE
        SYNTAX  InetAddress (SIZE(4|16))
        MAX-ACCESS  read-only
        STATUS  current
        DESCRIPTION
                      	""
        ::= { igmpchannelStatusEntry 4 }

 		igmpchannelStatusGem OBJECT-TYPE
    	SYNTAX     INTEGER
		MAX-ACCESS read-only
		STATUS     current
		DESCRIPTION
            ""

		::= { igmpchannelStatusEntry 5 }

 		igmpchannelStatusPortAid OBJECT-TYPE
    	SYNTAX     DisplayString
		MAX-ACCESS read-only
		STATUS     current
		DESCRIPTION
            ""

		::= { igmpchannelStatusEntry 6 }

 		igmpchannelStatusUniVid OBJECT-TYPE
    	SYNTAX     INTEGER
		MAX-ACCESS read-only
		STATUS     current
		DESCRIPTION
            ""

		::= { igmpchannelStatusEntry 7 }

 		igmpchannelStatusGroupFilterMode OBJECT-TYPE
    	SYNTAX     INTEGER {include (1),exclude (2) }
		MAX-ACCESS read-only
		STATUS     current
		DESCRIPTION
            "The current cache state, applicable to MGMDv3-compatible
            nodes.  The value indicates whether the state is INCLUDE or
            EXCLUDE."

		::= { igmpchannelStatusEntry 8 }

	     igmpchannelStatusGroupUpTime OBJECT-TYPE
    	SYNTAX     DisplayString
		MAX-ACCESS read-only
		STATUS     current
		DESCRIPTION
            "The value specifies the group up time of indicated
            multicast group."

		::= { igmpchannelStatusEntry 9 }

-- igmpchannelClientSrcIp

        igmpchannelClientSrcIpTable	OBJECT-TYPE
        SYNTAX	SEQUENCE OF IgmpchannelClientSrcIpEntry
        MAX-ACCESS  not-accessible
        STATUS  current
        DESCRIPTION
                 	""
        ::= { multicastStatus 21 }

	igmpchannelClientSrcIpEntry OBJECT-TYPE
        SYNTAX	IgmpchannelClientSrcIpEntry
        MAX-ACCESS	not-accessible
        STATUS	current
        DESCRIPTION    	"An entry in igmpchannelClientSrcIpTable."
        INDEX {
			igmpchannelClientSrcIpAddressType,
			igmpchannelClientSrcIpIndex,
			igmpchannelStatusVlanID,
			igmpchannelStatusPort,
			igmpchannelStatusGroupAddress,
			igmpchannelStatusGem
		}
        ::= { igmpchannelClientSrcIpTable 1 }

        IgmpchannelClientSrcIpEntry ::=
		SEQUENCE {
        	igmpchannelClientSrcIpIndex			INTEGER,
        	igmpchannelClientSrcIpAddressType	InetAddressType,
        	igmpchannelClientSrcIpAddress		InetAddress
         }

        igmpchannelClientSrcIpIndex OBJECT-TYPE
        SYNTAX  INTEGER
        MAX-ACCESS  read-only
        STATUS  current
        DESCRIPTION
                      	""
        ::= { igmpchannelClientSrcIpEntry 1 }

        igmpchannelClientSrcIpAddressType OBJECT-TYPE
        SYNTAX  InetAddressType { ipv4(1), ipv6(2) }
	    MAX-ACCESS read-only
	    STATUS current
        DESCRIPTION
                      	""
        ::= { igmpchannelClientSrcIpEntry 2 }

        igmpchannelClientSrcIpAddress OBJECT-TYPE
        SYNTAX  InetAddress (SIZE(4|16))
	    MAX-ACCESS read-only
	    STATUS current
        DESCRIPTION
                      	""
        ::= { igmpchannelClientSrcIpEntry 3 }

--	mgmdSrcListExpire OBJECT-TYPE
--    	SYNTAX     TimeTicks
--    	MAX-ACCESS read-only
--    	STATUS     current
--    	DESCRIPTION
--            "This value indicates the relevance of the SrcList entry,
--            whereby a non-zero value indicates this is an INCLUDE state
--            value, and a zero value indicates this to be an EXCLUDE
--            state value."

--	::= { mgmdHostSrcListEntry 3 }

------------------------------------------
-- 	27.igmpFilteringProfileSetup

--		igmpFilteringMaxNumberOfProfile OBJECT-TYPE
--        SYNTAX  INTEGER
--        MAX-ACCESS  read-only
--        STATUS  current
--        DESCRIPTION
--                      	""
--        ::= { igmpFilteringProfileSetup 1 }

--        igmpFilteringProfileTable	OBJECT-TYPE
--        SYNTAX	SEQUENCE OF IgmpFilteringProfileEntry
--        MAX-ACCESS  not-accessible
--        STATUS  current
--        DESCRIPTION
--                 	""
--        ::= { igmpFilteringProfileSetup 2 }

--		igmpFilteringProfileEntry OBJECT-TYPE
--        SYNTAX	IgmpFilteringProfileEntry
--        MAX-ACCESS	not-accessible
--        STATUS	current
--        DESCRIPTION    	"An entry in igmpFilteringProfileTable."
--        INDEX          	{ igmpFilteringProfileName, igmpFilteringProfileStartAddress, igmpFilteringProfileEndAddress }
--        ::= { igmpFilteringProfileTable 1 }

--        IgmpFilteringProfileEntry ::=
--		SEQUENCE {
--        	igmpFilteringProfileName		DisplayString,
--        	igmpFilteringProfileStartAddress	IpAddress,
--        	igmpFilteringProfileEndAddress		IpAddress,
--        	igmpFilteringProfileRowStatus		RowStatus
--        }

--        igmpFilteringProfileName OBJECT-TYPE
--        SYNTAX  DisplayString
--        MAX-ACCESS  read-only
--        STATUS  current
--        DESCRIPTION
--                      	""
--        ::= { igmpFilteringProfileEntry 1 }

--        igmpFilteringProfileStartAddress OBJECT-TYPE
--        SYNTAX  IpAddress
--        MAX-ACCESS  read-only
--        STATUS  current
--        DESCRIPTION
--                      	""
--        ::= { igmpFilteringProfileEntry 2 }

--        igmpFilteringProfileEndAddress OBJECT-TYPE
--        SYNTAX  IpAddress
--        MAX-ACCESS  read-only
--        STATUS  current
--        DESCRIPTION
--                      	""
--        ::= { igmpFilteringProfileEntry 3 }

--        igmpFilteringProfileRowStatus OBJECT-TYPE
--        SYNTAX  RowStatus
--        MAX-ACCESS  read-create
--        STATUS  current
--        DESCRIPTION
--                      	""
--        ::= { igmpFilteringProfileEntry 4 }

--        mgmdFilterProfileTable	OBJECT-TYPE
--        SYNTAX	SEQUENCE OF MgmdFilterProfileEntry
--        MAX-ACCESS  not-accessible
--        STATUS  current
--        DESCRIPTION
--                 	""
--        ::= { igmpFilteringProfileSetup 3 }

--	mgmdFilterProfileEntry OBJECT-TYPE
--        SYNTAX	MgmdFilterProfileEntry
--        MAX-ACCESS	not-accessible
--        STATUS	current
--        DESCRIPTION    	"An entry in mgmdFilterProfileTable.For v4 and v6 address"
--        INDEX          	{
--        		mgmdFilterProfileName,
--        		mgmdFilterProfileAddressType,
--        		mgmdFilterProfileStartAddress,
--        		mgmdFilterProfileEndAddress }
--        ::= { mgmdFilterProfileTable 1 }

--        MgmdFilterProfileEntry ::=
--	SEQUENCE {
--        	mgmdFilterProfileName			DisplayString,
--        	mgmdFilterProfileAddressType		InetAddressType,
--        	mgmdFilterProfileStartAddress		InetAddress,
--        	mgmdFilterProfileEndAddress		InetAddress,
--        	mgmdFilterProfileRowStatus		RowStatus
--        }

--        mgmdFilterProfileName OBJECT-TYPE
--        SYNTAX  DisplayString
--        MAX-ACCESS  read-only
--        STATUS  current
--        DESCRIPTION
--                      	""
--        ::= { mgmdFilterProfileEntry 1 }

--        mgmdFilterProfileAddressType OBJECT-TYPE
--        SYNTAX  InetAddressType
--        MAX-ACCESS  read-only
--        STATUS  current
--        DESCRIPTION
--		"The type of the mgmdFilterProfileStartAddress and mgmdFilterProfileEndAddress address, as defined
--            in the InetAddress MIB."

--        ::= { mgmdFilterProfileEntry 2 }

--        mgmdFilterProfileStartAddress OBJECT-TYPE
--        SYNTAX  InetAddress
--        MAX-ACCESS  read-only
--        STATUS  current
--        DESCRIPTION
--		"The Start IP address of this profile."
--        ::= { mgmdFilterProfileEntry 3 }


--        mgmdFilterProfileEndAddress OBJECT-TYPE
--        SYNTAX  InetAddress
--        MAX-ACCESS  read-only
--        STATUS  current
--        DESCRIPTION
--		"The End IP address of this profile."
--        ::= { mgmdFilterProfileEntry 4 }

--        mgmdFilterProfileRowStatus OBJECT-TYPE
--        SYNTAX  RowStatus
--        MAX-ACCESS  read-create
--        STATUS  current
--        DESCRIPTION
--                      	""
--        ::= { mgmdFilterProfileEntry 5 }



--  28.MVRSetup

		maxNumberOfMVR OBJECT-TYPE
        SYNTAX  INTEGER
        MAX-ACCESS  read-only
        STATUS  current
        DESCRIPTION
                      	""
        ::= { mvrSetup 1 }

        mvrTable	OBJECT-TYPE
        SYNTAX	SEQUENCE OF MvrEntry
        MAX-ACCESS  not-accessible
        STATUS  current
        DESCRIPTION
                 	""
        ::= { mvrSetup 2 }

		mvrEntry OBJECT-TYPE
        SYNTAX	MvrEntry
        MAX-ACCESS	not-accessible
        STATUS	current
        DESCRIPTION    	"An entry in mvrTable."
        INDEX          	{ mvrVlanID }
        ::= { mvrTable 1 }

        MvrEntry ::=
		SEQUENCE {
        	mvrVlanID	INTEGER,
        	mvrName		DisplayString,
        	mvrMode		INTEGER,
--        	mvrRowStatus	RowStatus,
        	mvr8021pPriority	INTEGER
        }

        mvrVlanID OBJECT-TYPE
        SYNTAX  INTEGER
        MAX-ACCESS  read-only
        STATUS  current
        DESCRIPTION
                      	"1..4094"
        ::= { mvrEntry 1 }

        mvrName OBJECT-TYPE
        SYNTAX  DisplayString
        MAX-ACCESS  read-only
        STATUS  current
        DESCRIPTION
                      	""
        ::= { mvrEntry 2 }

        mvrMode OBJECT-TYPE
        SYNTAX  INTEGER {
        	dynamic(0),
        	compatible(1)
        	}
        MAX-ACCESS  read-only
        STATUS  current
        DESCRIPTION
                      	""
        ::= { mvrEntry 3 }

--      mvrRowStatus OBJECT-TYPE
--      SYNTAX  RowStatus
--      MAX-ACCESS  read-create
--      STATUS  current
--      DESCRIPTION
--                    	""
--      ::= { mvrEntry 4 }

        mvr8021pPriority OBJECT-TYPE
        SYNTAX  INTEGER
        MAX-ACCESS  read-only
        STATUS  current
        DESCRIPTION
                      	"Set the 802.1p priority of control messages within MVR (0~7)"
        ::= { mvrEntry 5 }


        mvrPortTable	OBJECT-TYPE
        SYNTAX	SEQUENCE OF MvrPortEntry
        MAX-ACCESS  not-accessible
        STATUS  current
        DESCRIPTION
                 	""
        ::= { mvrSetup 3 }

		mvrPortEntry OBJECT-TYPE
        SYNTAX	MvrPortEntry
        MAX-ACCESS	not-accessible
        STATUS	current
        DESCRIPTION    	"An entry in mvrPortTable."
        INDEX          	{ mvrVlanID, dot1dBasePort }
        ::= { mvrPortTable 1 }

        MvrPortEntry ::=
		SEQUENCE {
        	mvrPortRole	INTEGER,
        	mvrPortTagging	EnabledStatus
        }

        mvrPortRole OBJECT-TYPE
        SYNTAX  INTEGER {
        	none(1),
        	sourcePort(2),
        	receiverPort(3)
        }
        MAX-ACCESS  read-only
        STATUS  current
        DESCRIPTION
                      	""
        ::= { mvrPortEntry 1 }

        mvrPortTagging OBJECT-TYPE
        SYNTAX  EnabledStatus
        MAX-ACCESS read-only
        STATUS  current
        DESCRIPTION
                      	""
        ::= { mvrPortEntry 2 }

		maxNumberOfMvrGroup OBJECT-TYPE
        SYNTAX  INTEGER
        MAX-ACCESS  read-only
        STATUS  current
        DESCRIPTION
                      	""
        ::= { mvrSetup 4 }

        mvrGroupTable	OBJECT-TYPE
        SYNTAX	SEQUENCE OF MvrGroupEntry
        MAX-ACCESS  not-accessible
        STATUS  current
        DESCRIPTION
                 	""
        ::= { mvrSetup 5 }

		mvrGroupEntry OBJECT-TYPE
        SYNTAX	MvrGroupEntry
        MAX-ACCESS	not-accessible
        STATUS	current
        DESCRIPTION    	"An entry in mvrGroupTable."
        INDEX          	{ mvrVlanID, mvrGroupName }
        ::= { mvrGroupTable 1 }

        MvrGroupEntry ::=
		SEQUENCE {
        	mvrGroupName		DisplayString,
        	mvrGroupStartAddress	IpAddress,
            mvrGroupEndAddress	IpAddress
--        	mvrGroupRowStatus	RowStatus
        }

        mvrGroupName OBJECT-TYPE
        SYNTAX  DisplayString
        MAX-ACCESS  read-only
        STATUS  current
        DESCRIPTION
                      	""
        ::= { mvrGroupEntry 1 }

        mvrGroupStartAddress OBJECT-TYPE
        SYNTAX  IpAddress
        MAX-ACCESS  read-only
        STATUS  current
        DESCRIPTION
                      	""
        ::= { mvrGroupEntry 2 }

        mvrGroupEndAddress OBJECT-TYPE
        SYNTAX  IpAddress
        MAX-ACCESS  read-only
        STATUS  current
        DESCRIPTION
                      	""
        ::= { mvrGroupEntry 3 }

--      mvrGroupRowStatus OBJECT-TYPE
--      SYNTAX  RowStatus
--      MAX-ACCESS  read-create
--      STATUS  current
--      DESCRIPTION
--                    	""
--      ::= { mvrGroupEntry 4 }

    mvrBehavior OBJECT-TYPE
        SYNTAX  INTEGER {
         		igmpSnooping(1),
         		igmpProxy(2)
        }
        MAX-ACCESS  read-write
        STATUS  current
        DESCRIPTION
                      ""
        ::= { mvrSetup 6 }


        mvrMgmdGroupTable	OBJECT-TYPE
        SYNTAX	SEQUENCE OF MvrMgmdGroupEntry
        MAX-ACCESS  not-accessible
        STATUS  current
        DESCRIPTION
                 	""
        ::= { mvrSetup 7 }

	mvrMgmdGroupEntry OBJECT-TYPE
        SYNTAX	MvrMgmdGroupEntry
        MAX-ACCESS	not-accessible
        STATUS	current
        DESCRIPTION    	"An entry in mvrMgmdGroupTable."
        INDEX          	{ mvrVlanID, mvrMgmdGroupName }
        ::= { mvrMgmdGroupTable 1 }

        MvrMgmdGroupEntry ::=
	SEQUENCE {
        	mvrMgmdGroupName		DisplayString,
        	mvrMgmdGroupAddressType		InetAddressType,
        	mvrMgmdGroupStartAddress	InetAddress,
            mvrMgmdGroupEndAddress		InetAddress
--          mvrMgmdGroupRowStatus		RowStatus
        }

        mvrMgmdGroupName OBJECT-TYPE
        SYNTAX  DisplayString
        MAX-ACCESS  read-only
        STATUS  current
        DESCRIPTION
                      	""
        ::= { mvrMgmdGroupEntry 1 }

        mvrMgmdGroupAddressType OBJECT-TYPE
        SYNTAX  InetAddressType
        MAX-ACCESS  read-only
        STATUS  current
        DESCRIPTION
                      	""
        ::= { mvrMgmdGroupEntry 2 }


        mvrMgmdGroupStartAddress OBJECT-TYPE
        SYNTAX  InetAddress
        MAX-ACCESS  read-only
        STATUS  current
        DESCRIPTION
                      	""
        ::= { mvrMgmdGroupEntry 3 }

        mvrMgmdGroupEndAddress OBJECT-TYPE
        SYNTAX  InetAddress
        MAX-ACCESS  read-only
        STATUS  current
        DESCRIPTION
                      	""
        ::= { mvrMgmdGroupEntry 4 }

--      mvrMgmdGroupRowStatus OBJECT-TYPE
--      SYNTAX  RowStatus
--      MAX-ACCESS  read-create
--      STATUS  current
--      DESCRIPTION
--                    	""
--      ::= { mvrMgmdGroupEntry 5 }

--  29.clusterSetup
--
-- 		clusterManager
--		clusterManager     	OBJECT IDENTIFIER ::= { clusterSetup 1 }
--
--        clusterMaxNumOfManager OBJECT-TYPE
--        SYNTAX  INTEGER
--        MAX-ACCESS  read-only
--        STATUS  current
--        DESCRIPTION
--                      ""
--        ::= { clusterManager 1 }
--
-- 		clusterManagerTable
--        clusterManagerTable OBJECT-TYPE
--        SYNTAX	SEQUENCE OF ClusterManagerEntry
--        MAX-ACCESS  not-accessible
--        STATUS  current
--        DESCRIPTION
--                 	""
--        ::= { clusterManager 2 }
--
--		clusterManagerEntry OBJECT-TYPE
--        SYNTAX	ClusterManagerEntry
--        MAX-ACCESS	not-accessible
--        STATUS	current
--        DESCRIPTION    	"An entry in clusterManagerTable."
--        INDEX          	{ clusterManagerVid }
--        ::= { clusterManagerTable 1 }
--
--        ClusterManagerEntry ::=
--           SEQUENCE {
--        	clusterManagerVid	INTEGER,
--        	clusterManagerName	DisplayString,
--        	clusterManagerRowStatus	RowStatus
--           }
--
--        clusterManagerVid OBJECT-TYPE
--        SYNTAX  INTEGER
--        MAX-ACCESS  read-only
--        STATUS  current
--        DESCRIPTION
--                      	""
--        ::= { clusterManagerEntry 1 }
--
--        clusterManagerName OBJECT-TYPE
--        SYNTAX  DisplayString
--        MAX-ACCESS  read-write
--        STATUS  current
--        DESCRIPTION
--                      	""
--        ::= { clusterManagerEntry 2 }
--
--        clusterManagerRowStatus OBJECT-TYPE
--        SYNTAX  RowStatus
--        MAX-ACCESS  read-create
--        STATUS  current
--        DESCRIPTION
--                      	""
--        ::= { clusterManagerEntry 3 }
--
---- 		--clusterMembers
--		clusterMembers     	OBJECT IDENTIFIER ::= { clusterSetup 2 }
--
--        clusterMaxNumOfMember OBJECT-TYPE
--        SYNTAX  INTEGER
--        MAX-ACCESS  read-only
--        STATUS  current
--        DESCRIPTION
--                      ""
--        ::= { clusterMembers 1 }
--
---- 		--clusterMemberTable
--        clusterMemberTable OBJECT-TYPE
--        SYNTAX	SEQUENCE OF ClusterMemberEntry
--        MAX-ACCESS  not-accessible
--        STATUS  current
--        DESCRIPTION
--                 	""
--        ::= { clusterMembers 2 }
--
--		clusterMemberEntry OBJECT-TYPE
--        SYNTAX	ClusterMemberEntry
--        MAX-ACCESS	not-accessible
--        STATUS	current
--        DESCRIPTION    	"An entry in clusterMemberTable."
--        INDEX          	{ clusterMemberMac }
--        ::= { clusterMemberTable 1 }
--
--        ClusterMemberEntry ::=
--           SEQUENCE {
--        	clusterMemberMac	MacAddress,
--        	clusterMemberName	DisplayString,
--        	clusterMemberModel	DisplayString,
--        	clusterMemberPassword	DisplayString,
--        	clusterMemberRowStatus	RowStatus
--           }
--
--        clusterMemberMac OBJECT-TYPE
--        SYNTAX  MacAddress
--        MAX-ACCESS  not-accessible
--        STATUS  current
--        DESCRIPTION
--                      	""
--        ::= { clusterMemberEntry 1 }
--
--        clusterMemberName OBJECT-TYPE
--        SYNTAX  DisplayString
--        MAX-ACCESS  read-only
--        STATUS  current
--        DESCRIPTION
--                      	""
--        ::= { clusterMemberEntry 2 }
--
--        clusterMemberModel OBJECT-TYPE
--        SYNTAX  DisplayString
--        MAX-ACCESS  read-only
--        STATUS  current
--        DESCRIPTION
--                      	""
--        ::= { clusterMemberEntry 3 }
--
--        clusterMemberPassword OBJECT-TYPE
--        SYNTAX  DisplayString
--        MAX-ACCESS  read-write
--        STATUS  current
--        DESCRIPTION
--                      	""
--        ::= { clusterMemberEntry 4 }
--
--        clusterMemberRowStatus OBJECT-TYPE
--        SYNTAX  RowStatus
--        MAX-ACCESS  read-create
--        STATUS  current
--        DESCRIPTION
--                      	""
--        ::= { clusterMemberEntry 5 }
--
---- 		--clusterCandidates
--		clusterCandidates     	OBJECT IDENTIFIER ::= { clusterSetup 3 }
--
-- 		clusterCandidateTable
--        clusterCandidateTable OBJECT-TYPE
--        SYNTAX	SEQUENCE OF ClusterCandidateEntry
--        MAX-ACCESS  not-accessible
--        STATUS  current
--        DESCRIPTION
--                 	""
--        ::= { clusterCandidates 1 }
--
--		clusterCandidateEntry OBJECT-TYPE
--        SYNTAX	ClusterCandidateEntry
--        MAX-ACCESS	not-accessible
--        STATUS	current
--        DESCRIPTION    	"An entry in clusterCandidateTable."
--        INDEX          	{ clusterCandidateMac }
--        ::= { clusterCandidateTable 1 }
--
--        ClusterCandidateEntry ::=
--           SEQUENCE {
--        	clusterCandidateMac	MacAddress,
--        	clusterCandidateName	DisplayString,
--        	clusterCandidateModel	DisplayString
--           }
--
--        clusterCandidateMac OBJECT-TYPE
--        SYNTAX  MacAddress
--        MAX-ACCESS  read-only
--        STATUS  current
--        DESCRIPTION
--                      	""
--        ::= { clusterCandidateEntry 1 }
--
--        clusterCandidateName OBJECT-TYPE
--        SYNTAX  DisplayString
--        MAX-ACCESS  read-only
--        STATUS  current
--        DESCRIPTION
--                      	""
--        ::= { clusterCandidateEntry 2 }
--
--        clusterCandidateModel OBJECT-TYPE
--        SYNTAX  DisplayString
--        MAX-ACCESS  read-only
--        STATUS  current
--        DESCRIPTION
--                      	""
--        ::= { clusterCandidateEntry 3 }
--
---- 		--clusterStatus
--		clusterStatus     	OBJECT IDENTIFIER ::= { clusterSetup 4 }
--
--        clusterStatusRole OBJECT-TYPE
--        SYNTAX  INTEGER {
--        	none(0),
--        	manager(1),
--        	member(2)
--        }
--        MAX-ACCESS  read-only
--        STATUS  current
--        DESCRIPTION
--                      	""
--        ::= { clusterStatus 1 }
--
--        clusterStatusManager OBJECT-TYPE
--        SYNTAX  DisplayString
--        MAX-ACCESS  read-only
--        STATUS  current
--        DESCRIPTION
--                      	""
--        ::= { clusterStatus 2 }
--
--        clsuterStatusMaxNumOfMember OBJECT-TYPE
--        SYNTAX  INTEGER
--        MAX-ACCESS  read-only
--        STATUS  current
--        DESCRIPTION
--                      	""
--        ::= { clusterStatus 3 }
--
-- 		clusterStatusMemberTable
--        clusterStatusMemberTable OBJECT-TYPE
--        SYNTAX	SEQUENCE OF ClusterStatusMemberEntry
--        MAX-ACCESS  not-accessible
--        STATUS  current
--        DESCRIPTION
--                 	""
--        ::= { clusterStatus 4 }
--
--		clusterStatusMemberEntry OBJECT-TYPE
--        SYNTAX	ClusterStatusMemberEntry
--        MAX-ACCESS	not-accessible
--        STATUS	current
--        DESCRIPTION    	"An entry in clusterStatusMemberTable."
--        INDEX          	{ clusterStatusMemberMac }
--        ::= { clusterStatusMemberTable 1 }
--
--        ClusterStatusMemberEntry ::=
--           SEQUENCE {
--        	clusterStatusMemberMac		MacAddress,
--        	clusterStatusMemberName		DisplayString,
--        	clusterStatusMemberModel	DisplayString,
--        	clusterStatusMemberStatus	INTEGER
--           }
--
--        clusterStatusMemberMac OBJECT-TYPE
--        SYNTAX  MacAddress
--        MAX-ACCESS  read-only
--        STATUS  current
--        DESCRIPTION
--                      	""
--        ::= { clusterStatusMemberEntry 1 }
--
--        clusterStatusMemberName OBJECT-TYPE
--        SYNTAX  DisplayString
--        MAX-ACCESS  read-only
--        STATUS  current
--        DESCRIPTION
--                      	""
--        ::= { clusterStatusMemberEntry 2 }
--
--        clusterStatusMemberModel OBJECT-TYPE
--        SYNTAX  DisplayString
--        MAX-ACCESS  read-only
--        STATUS  current
--        DESCRIPTION
--                      	""
--        ::= { clusterStatusMemberEntry 3 }
--
--        clusterStatusMemberStatus OBJECT-TYPE
--        SYNTAX  INTEGER {
--        	error(0),
--        	online(1),
--        	offline(2)
--        }
--        MAX-ACCESS  read-only
--        STATUS  current
--        DESCRIPTION
--                      	""
--        ::= { clusterStatusMemberEntry 4 }
--

----	--30.fault MIB



-- **************************************************************************
-- Local Textual Conventions
-- **************************************************************************

UtcTimeStamp ::= TEXTUAL-CONVENTION
    STATUS current
    DESCRIPTION
           "Universal Time Coordinated as a 32-bit value that designates
            the number of seconds since Jan 1, 1970 12:00AM."
    SYNTAX  Unsigned32

EventIdNumber ::= TEXTUAL-CONVENTION
   STATUS current
   DESCRIPTION
          "This textual convention describes the index that uniquely
           identifies a fault event type in the entire system. Every fault
           event type, e.g. link down, has a unique EventIdNumber."
   SYNTAX  Integer32

EventSeverity ::= TEXTUAL-CONVENTION
   STATUS current
   DESCRIPTION
          "This textual convention describes the severity of a fault event.
           The decreasing order of severity is shown in the textual
           convention."
   SYNTAX  INTEGER{
             critical (1),
             major (2),
             minor (3),
             informational (4)
           }

EventServiceAffective ::= TEXTUAL-CONVENTION
   STATUS current
   DESCRIPTION
          "This textual convention indicates whether an event is immediately
           service affecting or not."
   SYNTAX  INTEGER{
   	     noServiceAffected (1),
	     serviceAffected (2)
           }


InstanceType ::= TEXTUAL-CONVENTION
    STATUS current
    DESCRIPTION
           "This textual convention describes the type of an instanceId
            associated with each event and by that means specifies how
            the instanceId variable should be intepreted.

            Various instanceId types are specified below to enable fault
            monitoring for different kind of devices from fixed
            configuration pizza boxes to multi chassis nodes. All
            instanceId types may not need to be used in every device
            type.

            Note also that instanceId semantics are element type dependent
            (e.g. different kind of interface naming conventions may be used)
            and thus instanceId usage may vary from element to element.

    =========================================================================
    Type            Description                                 Example form
                                                                of InstanceId
    =========================================================================
    unknown    (1)  unknown type                               - Irrelevant-
    -------------------------------------------------------------------------
    node       (2)  Associated with events originating from          1
                    the node. Used for general events that     (Node number)
                    can not be associated with any specific
                    block. InstanceId value 1 is used for
                    single node equipment.
    -------------------------------------------------------------------------
    shelf      (3)  Associated with events originating from          1
                    the shelf. In the case of fixed       	(shelf number)
                    configuration devices this type is used
                    for events that are associated with the
                    physical enclosure, e.g. faults related
                    to fan etc. InstanceId value 1 is used
                    for single self equipment.
    -------------------------------------------------------------------------
    line       (4)  Associated with events originating from
                    physical interfaces or associated
                    components such as line cards.
                    InstanceId usage examples for faults
                    originating from:
                    - Physical port: Simply port number, e.g. .......1
    -------------------------------------------------------------------------
    switch     (5)  Associated with events originating from          1
                    from a switch chip or a switch card.      (switch number)
                    For single switch equipment InstanceId
                    value 1 is used, for multi swich nodes
                    InstanceId semantics if for further
                    study.
    -------------------------------------------------------------------------
    lsp        (6)  Associated with events originating from          1
                    a particular lsp.                           (lsp index)
                    NOTE: In this case the InstanceName
                    contains the lsp name and InstanceId
                    contains lsp index.
    -------------------------------------------------------------------------
    l2Interface(7)  Associated with events originating from        - TBD -
                    a particular layer 2 interface. Used for
                    layer 2 related events such as L2 control
                    protocol faults. InstanceId semantics is
                    for further study.
    -------------------------------------------------------------------------
    l3Interface(8)  Associated with events originating from        - TBD -
                    a particular layer 3 interface. Used for
                    layer 3 related events such as L3 control
                    protocol faults. InstanceId semantics is
                    for further study.
    -------------------------------------------------------------------------
    rowIndex  (9)   Associated with events reporting about a
                    'logical' or conceptual table that consists
                    of rows.  The Instance Id is the index/key
                    for a row in the table.  The format of the
                    Instance Id will simply be a series of decimal
                    numbers seperated by a '.':
    -------------------------------------------------------------------------
    aid  	(10)	Associated with events reporting about an instance with
    				aid format.
    				InstanceId is ge-5-1; ont-5-1-100; uniport-5-1-100-1-2...etc.
    ========================================================================="

    SYNTAX  INTEGER {
              unknown (1),
              node (2),
              shelf (3),
              line (4),
              switch (5),
              lsp (6),
              l2Interface(7),
              l3Interface(8),
              rowIndex(9),
              aid(10)
            }


-- *****************************************************************************
-- Top level structure of this MIB.
-- *****************************************************************************

eventObjects        OBJECT IDENTIFIER ::= { faultMIB  1 }


-- *****************************************************************************
-- Event Table
--
-- Event table reports all currently active fault events. Only normal type of
-- faults (i.e. faults that are not automatically and immediately cleared) are
-- present in the event table. Delta faults (i.e. faults that are automatically
-- cleared) are reported only by using trap messages.
-- *****************************************************************************

eventTable OBJECT-TYPE
    SYNTAX      SEQUENCE OF EventEntry
    MAX-ACCESS 	 	not-accessible
    STATUS      current
    DESCRIPTION
            "A list of currently active fault events. All faults
             of normal type regardless of their severity level
             are recorded in the event table. When a normal
             type fault is cleared it is deleted from the event
             table."
    ::= { eventObjects 1 }

eventEntry OBJECT-TYPE
    SYNTAX      EventEntry
    MAX-ACCESS  	not-accessible
    STATUS      current
    DESCRIPTION
            "An entry containing information about an
             event in the event table."
    INDEX   { eventSeqNum }
    ::= { eventTable 1 }

EventEntry ::=
    SEQUENCE {
      eventSeqNum           Integer32,
      eventEventId          EventIdNumber,
      eventName             DisplayString,
      eventInstanceType     InstanceType,
      eventInstanceId       DisplayString,
      eventInstanceName     DisplayString,
      eventSeverity         EventSeverity,
      eventSetTime          UtcTimeStamp,
      eventDescription      DisplayString,
      eventServAffective    EventServiceAffective,
      eventInstanceIdNumber Integer32
   }

eventSeqNum OBJECT-TYPE
    SYNTAX      Integer32
    MAX-ACCESS  read-only
    STATUS      current
    DESCRIPTION
            "This variable represents the sequence number of an event.
             Sequence number is incremented monotonically starting
             from 0 until it reaches its maximum and wraps around back
             to 0.

             Sequence number is incremented when
             - the state of a normal type fault is set on (the same sequence
             number is present in the events table as well as in the trap
             that is sent to notify about the fault on event)
             - delta event occurs (sequence number present in trap message)
             - the state of a normal type fault is set off (sequence number
             present in trap that is sent to notify for clearing)."
    ::= { eventEntry 1 }

eventEventId OBJECT-TYPE
    SYNTAX      EventIdNumber
    MAX-ACCESS  read-only
    STATUS      current
    DESCRIPTION
            "This variable represents the event ID which uniquely
             identifies the event in the entire system."
    ::= { eventEntry 2 }

eventName OBJECT-TYPE
    SYNTAX      DisplayString (SIZE (0..40))
    MAX-ACCESS  read-only
    STATUS      current
    DESCRIPTION
            "This variable represents the name of the event, for
             example 'Ethernet Link Down'"
    ::= { eventEntry 3 }

eventInstanceType OBJECT-TYPE
    SYNTAX      InstanceType
    MAX-ACCESS  read-only
    STATUS      current
    DESCRIPTION
            "This variable represents the type of InstanceId of a
             particular event in the event table. In brief
             the instanceType refers to the type of sub-component
             generating this event in the system, for example
             switch (5). For more details see the textual
             conventions section.

             AFFECTS:   eventInstanceId,
                        eventInstanceName"
    ::= { eventEntry 4 }

eventInstanceId OBJECT-TYPE
    SYNTAX  DisplayString
    MAX-ACCESS  read-only
    STATUS      current
    DESCRIPTION
            "This variable represents the InstanceId of a particular
             event in the event current table. In brief the instanceId
             refers to the sub-component generating this event in the
             system, for example '1' for port 1. For more details see
             the textual conventions section.

             DEPENDS ON:  eventInstanceType"
    ::= { eventEntry 5 }

eventInstanceName OBJECT-TYPE
    SYNTAX      DisplayString
    MAX-ACCESS  read-only
    STATUS      current
    DESCRIPTION
            "This variable is mainly used to store additional information
             about the sub-component that is generating an event. For
             example this field may specify what cooling fan is faulty.

             DEPENDS ON:  eventInstanceType"
    ::= { eventEntry 6 }

eventSeverity OBJECT-TYPE
    SYNTAX      EventSeverity
    MAX-ACCESS  read-only
    STATUS      current
    DESCRIPTION
            "This variable dictates the urgency of action when a event
             occurs. There are four severity levels - Critical, Major,
             Minor, and Informational.  Critical events are those, which
             require immediate operator intervention to prevent/reduce
             system down time. Major events require quick attention and
             Minor events possibly require some attention. Informational
             events indicate the occurrence of events that may need to be
             investigated."
    ::= { eventEntry 7 }

eventSetTime OBJECT-TYPE
    SYNTAX      UtcTimeStamp
    MAX-ACCESS  read-only
    STATUS      current
    DESCRIPTION
            "This table contains only normal events and this variable
             represents the time when the event become active, i.e. the
             number of seconds since Jan 1, 1970 12:00AM."
    ::= { eventEntry 8 }


eventDescription OBJECT-TYPE
    SYNTAX      DisplayString (SIZE (0..255))
    MAX-ACCESS  read-only
    STATUS      current
    DESCRIPTION
            "This variable contains a description of the event and reasons
             behind the event. This is a free format alpha-numeric string
             that is set by the entity generating this event. This variable
             may be empty if there is no usefull information to report.
             The maximum length of this string is 255 characters."
    ::= { eventEntry 9 }

eventServAffective OBJECT-TYPE
    SYNTAX      EventServiceAffective
    MAX-ACCESS  	read-only
    STATUS      current
    DESCRIPTION
            "This variable indicates whether the event is service affective or not"
    ::= { eventEntry 10 }

eventInstanceIdNumber OBJECT-TYPE
   	SYNTAX  	Integer32
   	MAX-ACCESS  	read-only
   	STATUS      current
    DESCRIPTION
            "This variable represents the InstanceId of a particular
             event in the event current table. In brief the instanceId
             refers to the sub-component generating this event in the
             system, for example '1' for port 1. For more details see
             the textual conventions section.

             DEPENDS ON:  eventInstanceType"
   	::= { eventEntry 11 }


-- 31.fault Trap MIB

trapInfoObjects             OBJECT IDENTIFIER ::= { faultTrapsMIB 1}
trapNotifications           OBJECT IDENTIFIER ::= { faultTrapsMIB 2}


-- **************************************************************************
-- Local Textual Conventions
-- **************************************************************************

EventPersistence ::= TEXTUAL-CONVENTION
   STATUS current
   DESCRIPTION
          "This textual convention indicates whether the event is delta
           (automatically and immediately cleared) or normal (not
           automatically cleared)."
   SYNTAX  INTEGER{
   	     normal (1),
	     delta (2)
         }


-- **************************************************************************
-- Trap information object definitions
-- **************************************************************************

trapRefSeqNum OBJECT-TYPE
    SYNTAX      Integer32
    MAX-ACCESS  	read-only
    STATUS      current
    DESCRIPTION
            "Indicates the former sequence number of a cleared event
             in the event table. Not intended to read but only used in
             trap notifications."
    ::= { trapInfoObjects 1 }

trapPersistence OBJECT-TYPE
    SYNTAX      EventPersistence
    MAX-ACCESS  	read-only
    STATUS      current
    DESCRIPTION
            "Indicates whether the event is delta (automatically and
             immediately cleared) or normal (not automatically cleared).
             Not intended to read but only used in trap notifications."
    ::= { trapInfoObjects 2 }

trapSenderNodeId OBJECT-TYPE
    SYNTAX      Integer32
    MAX-ACCESS  	read-only
    STATUS      current
    DESCRIPTION
            "Represents the node ID of the sending network element. If not
             supported should be set to 0. Not intended to read but only
             used in trap notifications."
    ::= { trapInfoObjects 3 }

trapSenderStatus OBJECT-TYPE
   	SYNTAX      Integer32
   	MAX-ACCESS  	read-only
    STATUS      current
   	DESCRIPTION
            "Represents the trap status. 0 means cleared, 1 means happened."
  	::= { trapInfoObjects 4 }


-- ***************************************************************************
-- Trap definitions
-- ***************************************************************************

eventOnTrap NOTIFICATION-TYPE
         OBJECTS {
                  eventSeqNum,
                  eventEventId,
                  eventName,
                  eventSetTime,
                  eventSeverity,
                  eventInstanceType,
                  eventInstanceId,
                  eventInstanceName,
                  eventServAffective,
                  eventDescription,
                  trapPersistence,
                  trapSenderNodeId,
                  sysObjectID}
         STATUS current
         DESCRIPTION
           "This trap is used to inform network management system that a delta
           fault event (events that are automatically cleared) has occured
           or a normal fault event (not automatically cleared) state has
           been set on.

           Objects are used as follows:
           - eventSeqNum is the sequence number of the event. For normal
           type of events must equal to the sequence number of the event
           in the events table.
           - eventEventId specifies what fault event has occured.
           - eventName specifies the name of the fault event.
           - eventSetTime indicates when fault event has occured
           (delta events) or when fault has been set on (normal events).
           - eventSeverity reports the severity level of the event.
           - eventInstanceType indicates what kind of object is faulty.
           - eventInstanceId specifies what instance is faulty.
           - eventInstanceName may contain textual description for
           the faulty object.
           - eventServAffective specifies whether the event is
           immediately service affcetive.
           - eventDescription reports possible additional information about the event.
           - trapPersistence tells whether this event is a delta or normal event.
           - trapSenderNodeId specifies the node ID of the sending network element if
           configuring it is supported for the network element, otherwise 0.
           - sysObjectID specifies what kind of equipment reports the fault event.

           For more information see the eventTable specification"
         ::= { trapNotifications 1 }

eventClearedTrap NOTIFICATION-TYPE
         OBJECTS {
                  eventSeqNum,
                  eventEventId,
                  eventSetTime,
                  eventInstanceType,
                  eventInstanceId,
                  trapRefSeqNum,
                  trapSenderNodeId,
                  sysObjectID}
         STATUS current
         DESCRIPTION
           "This trap is used to inform network management system that a normal
           type fault event has been cleared (state set off).

           Objects are used as follows:
           - eventSeqNum is the sequence number of the this clearing event. Note that
           the sequence number of the cleared event is reported in the trapRefSeqNum
           object.
           - eventEventId specifies what event has been cleared.
           - eventSetTime indicates when fault event has been cleared.
           - eventInstanceType indicates what kind of object has been
           faulty.
           - eventInstanceId specifies what instance has been faulty.
           - trapRefSeqNum specifies the sequence number of the cleared event (i.e.
           the sequence number was assigned for the event in the events table).
           - trapSenderNodeId specifies the node ID of the sending network element if
           configuring it is supported for the network element, otherwise 0.
           - sysObjectID specifies what kind of equipment reports the clearing event.

           For more information see the eventTable specification"
         ::= { trapNotifications 2 }

--  32.protocol-based VLAN

	    protoBasedVlanTable  OBJECT-TYPE
	    SYNTAX	SEQUENCE OF ProtoBasedVlanEntry
	    MAX-ACCESS  not-accessible
	    STATUS  current
	    DESCRIPTION
	             	""
	    ::= { protoBasedVlanSetup 1 }

		protoBasedVlanEntry  OBJECT-TYPE
        SYNTAX	ProtoBasedVlanEntry
        MAX-ACCESS	not-accessible
        STATUS	current
        DESCRIPTION    	"An entry in protoBasedVlanTable."
        INDEX          	{ protoBasedVlanPort, protoBasedVlanPacketType, protoBasedVlanEtherType }
        ::= { protoBasedVlanTable 1 }

        ProtoBasedVlanEntry ::=
           SEQUENCE {
            protoBasedVlanPort			INTEGER,
        	protoBasedVlanPacketType	INTEGER,
        	protoBasedVlanEtherType		INTEGER,
        	protoBasedVlanName			DisplayString,
        	protoBasedVlanVid			INTEGER,
        	protoBasedVlanPriority		INTEGER,
        	protoBasedVlanState			RowStatus
           }

        protoBasedVlanPort OBJECT-TYPE
        SYNTAX  INTEGER
        MAX-ACCESS  read-only
        STATUS  current
        DESCRIPTION
                      	""
        ::= { protoBasedVlanEntry 1 }

        protoBasedVlanPacketType OBJECT-TYPE
        SYNTAX  INTEGER {
        	etherII(1)
--        	etherII(1),
--        	snap(2),
--        	llc(3)
        }
        MAX-ACCESS  read-only
        STATUS  current
        DESCRIPTION
                      	""
        ::= { protoBasedVlanEntry 2 }

        protoBasedVlanEtherType OBJECT-TYPE
        SYNTAX  INTEGER
        MAX-ACCESS  read-only
        STATUS  current
        DESCRIPTION
                      	""
        ::= { protoBasedVlanEntry 3 }

        protoBasedVlanName OBJECT-TYPE
        SYNTAX  DisplayString (SIZE (0..32))
        MAX-ACCESS  read-write
        STATUS  current
        DESCRIPTION
                      	""
        ::= { protoBasedVlanEntry 4 }

        protoBasedVlanVid OBJECT-TYPE
        SYNTAX  INTEGER (1..4094)
        MAX-ACCESS  read-write
        STATUS  current
        DESCRIPTION
                      	""
        ::= { protoBasedVlanEntry 5 }

        protoBasedVlanPriority OBJECT-TYPE
        SYNTAX  INTEGER (0..7)
        MAX-ACCESS  read-write
        STATUS  current
        DESCRIPTION
                      	""
        ::= { protoBasedVlanEntry 6 }

        protoBasedVlanState OBJECT-TYPE
        SYNTAX  RowStatus
        MAX-ACCESS  read-create
        STATUS  current
        DESCRIPTION
                      	""
        ::= { protoBasedVlanEntry 7 }

--  33.sysLogSetup

		sysLogState OBJECT-TYPE
        SYNTAX  EnabledStatus
        MAX-ACCESS  read-write
        STATUS  current
        DESCRIPTION
                      	"sysLog enabled/disabled for the switch."
        ::= { sysLogSetup 1 }

--  	sysLogTypeTable
       	sysLogTypeTable	OBJECT-TYPE
        SYNTAX	SEQUENCE OF SysLogTypeEntry
        MAX-ACCESS  not-accessible
        STATUS  current
        DESCRIPTION
                 	""
        ::= { sysLogSetup 2 }

		sysLogTypeEntry OBJECT-TYPE
        SYNTAX	SysLogTypeEntry
        MAX-ACCESS	not-accessible
        STATUS	current
        DESCRIPTION    	"An entry in sysLogTypeTable."
        INDEX          	{ sysLogTypeIndex }
        ::= { sysLogTypeTable 1 }

        SysLogTypeEntry ::=
           SEQUENCE {
         	sysLogTypeIndex		INTEGER,
        	sysLogTypeName		DisplayString,
        	sysLogTypeState		EnabledStatus,
        	sysLogTypeFacility	INTEGER,
        	sysLogTypeLevel	INTEGER
           }

        sysLogTypeIndex OBJECT-TYPE
        SYNTAX  INTEGER
        MAX-ACCESS  not-accessible
        STATUS  current
        DESCRIPTION
                      	""
        ::= { sysLogTypeEntry 1 }

        sysLogTypeName OBJECT-TYPE
        SYNTAX  DisplayString
        MAX-ACCESS  read-only
        STATUS  current
        DESCRIPTION
                      	""
        ::= { sysLogTypeEntry 2 }

        sysLogTypeState OBJECT-TYPE
        SYNTAX  EnabledStatus
        MAX-ACCESS  read-write
        STATUS  current
        DESCRIPTION
                      	""
        ::= { sysLogTypeEntry 3 }

   		sysLogTypeFacility OBJECT-TYPE
        SYNTAX  INTEGER {
        	localUser0(0),
        	localUser1(1),
        	localUser2(2),
        	localUser3(3),
        	localUser4(4),
        	localUser5(5),
        	localUser6(6),
        	localUser7(7)
        }
        MAX-ACCESS  read-write
        STATUS  current
        DESCRIPTION
                      	""
        ::= { sysLogTypeEntry 4 }

   		sysLogTypeLevel OBJECT-TYPE
        SYNTAX  INTEGER {
        	level0(0),
        	level0to1(1),
        	level0to2(2),
        	level0to3(3),
        	level0to4(4),
        	level0to5(5),
        	level0to6(6),
        	level0to7(7)
        }
        MAX-ACCESS  read-write
        STATUS  current
        DESCRIPTION
                      	""
        ::= { sysLogTypeEntry 5 }

--  	sysLogServerTable
       	sysLogServerTable	OBJECT-TYPE
        SYNTAX	SEQUENCE OF SysLogServerEntry
        MAX-ACCESS  not-accessible
        STATUS  current
        DESCRIPTION
                 	""
        ::= { sysLogSetup 3 }

		sysLogServerEntry OBJECT-TYPE
        SYNTAX	SysLogServerEntry
        MAX-ACCESS	not-accessible
        STATUS	current
        DESCRIPTION    	"An entry in sysLogServerTable."
        INDEX          	{ sysLogServerAddress }
        ::= { sysLogServerTable 1 }

        SysLogServerEntry ::=
           SEQUENCE {
         	sysLogServerAddress		IpAddress,
        	sysLogServerLogLevel	INTEGER,
        	sysLogServerRowStatus	RowStatus
           }

        sysLogServerAddress OBJECT-TYPE
        SYNTAX  IpAddress
        MAX-ACCESS  not-accessible
        STATUS  current
        DESCRIPTION
                      	""
        ::= { sysLogServerEntry 1 }

        sysLogServerLogLevel OBJECT-TYPE
        SYNTAX  INTEGER {
        	level0(0),
        	level0to1(1),
        	level0to2(2),
        	level0to3(3),
        	level0to4(4),
        	level0to5(5),
        	level0to6(6),
        	level0to7(7)
        }
        MAX-ACCESS  read-write
        STATUS  current
        DESCRIPTION
                      	""
        ::= { sysLogServerEntry 2 }

        sysLogServerRowStatus OBJECT-TYPE
        SYNTAX  RowStatus
        MAX-ACCESS  read-create
        STATUS  current
        DESCRIPTION
                      	""
        ::= { sysLogServerEntry 3 }

--  	sysLogUploadSetup
       	sysLogUploadSetup OBJECT IDENTIFIER ::= { sysLogSetup 4 }

        sysLogUploadState OBJECT-TYPE
        SYNTAX  EnabledStatus
        MAX-ACCESS  read-write
        STATUS  current
        DESCRIPTION
                      "sysLogUpload service enabled/disabled."
        ::= { sysLogUploadSetup 1 }

        sysLogUploadTime OBJECT-TYPE
        SYNTAX  DisplayString
        MAX-ACCESS  read-write
        STATUS  current
        DESCRIPTION
                      "The time of sysLogUpload everyday in Hour:Min"
        ::= { sysLogUploadSetup 2 }

       	sysLogUploadServerTable	OBJECT-TYPE
        SYNTAX	SEQUENCE OF SysLogUploadServerEntry
        MAX-ACCESS  not-accessible
        STATUS  current
        DESCRIPTION
                 	""
        ::= { sysLogUploadSetup 3 }

		sysLogUploadServerEntry OBJECT-TYPE
        SYNTAX	SysLogUploadServerEntry
        MAX-ACCESS	not-accessible
        STATUS	current
        DESCRIPTION    	"An entry in sysLogUploadServerTable."
        INDEX          	{ sysLogUploadServerAddress }
        ::= { sysLogUploadServerTable 1 }

        SysLogUploadServerEntry ::=
           SEQUENCE {
         	sysLogUploadServerAddress	IpAddress,
        	sysLogUploadServerUsername	DisplayString,
        	sysLogUploadServerPassword  DisplayString,
        	sysLogUploadServerFilepath  DisplayString,
        	sysLogUploadServerRowStatus	RowStatus
           }

        sysLogUploadServerAddress OBJECT-TYPE
        SYNTAX  IpAddress
        MAX-ACCESS  not-accessible
        STATUS  current
        DESCRIPTION
                      	"IP address of sysLogUpload ftp server"
        ::= { sysLogUploadServerEntry 1 }

        sysLogUploadServerUsername OBJECT-TYPE
        SYNTAX  DisplayString
        MAX-ACCESS  read-write
        STATUS  current
        DESCRIPTION
                      	"The username of sysLogUpload ftp server"
        ::= { sysLogUploadServerEntry 2 }

        sysLogUploadServerPassword OBJECT-TYPE
        SYNTAX  DisplayString
        MAX-ACCESS  read-write
        STATUS  current
        DESCRIPTION
                      	"The password of sysLogUpload ftp server"
        ::= { sysLogUploadServerEntry 3 }

        sysLogUploadServerFilepath OBJECT-TYPE
        SYNTAX  DisplayString
        MAX-ACCESS  read-write
        STATUS  current
        DESCRIPTION
                      	"The path of sysLogUpload ftp server"
        ::= { sysLogUploadServerEntry 4 }

        sysLogUploadServerRowStatus OBJECT-TYPE
        SYNTAX  RowStatus
        MAX-ACCESS  read-create
        STATUS  current
        DESCRIPTION
                      	"The RowStatus of sysLogUpload ftp server"
        ::= { sysLogUploadServerEntry 5 }


--  35.l3Routing
--	routing protocol global settings
    layer3Setup		OBJECT IDENTIFIER ::= { l3Routing 1 }

    routerRipDistance OBJECT-TYPE
    SYNTAX  INTEGER
    MAX-ACCESS  read-write
    STATUS  current
    DESCRIPTION
        "The administrative distance of RIP routes"
    ::= { layer3Setup 1 }

    ospfSettings		OBJECT IDENTIFIER ::= { layer3Setup 6 }

    ospfRouterId OBJECT-TYPE
    SYNTAX  IpAddress
    MAX-ACCESS  read-write
    STATUS  current
    DESCRIPTION
                    "OSPF router id.
                    Range: 0.0.0.0 ~ 255.255.255.255"
    ::= { ospfSettings 1 }

    ospfRouterState OBJECT-TYPE
    SYNTAX  INTEGER{
            enable(1),
            disable(2)
    }
    MAX-ACCESS  read-write
    STATUS  current
    DESCRIPTION
                    "OSPF router State.
                     Write method only accept disable(2)"
    ::= { ospfSettings 2 }

    ospfDistance OBJECT-TYPE
    SYNTAX  INTEGER
    MAX-ACCESS  read-write
    STATUS  current
    DESCRIPTION
                    "OSPF distance, range: 1 ~ 255
                    Default: 15"
    ::= { ospfSettings 3 }

    ospfRedistributeStatic OBJECT-TYPE
    SYNTAX  INTEGER{
            enable(1),
            disable(2)
    }
    MAX-ACCESS  read-write
    STATUS  current
    DESCRIPTION
                    "Enable redistribute static route"
    ::= { ospfSettings 4 }

    ospfRedistributeStaticMetricType OBJECT-TYPE
    SYNTAX  INTEGER{
            type1(1),
            type2(2)
    }
    MAX-ACCESS  read-write
    STATUS  current
    DESCRIPTION
                    "Set redistribute static route metric type
                    Default: 1
                    1(1): External Type 1, add up the cost toward the destination
                    2(2): External Type 2, with default metric of 20 and will never change/increment through every hops"
    ::= { ospfSettings 5 }

    ospfRedistributeStaticMetric OBJECT-TYPE
    SYNTAX  INTEGER(0..16777215)
    MAX-ACCESS  read-write
    STATUS  current
    DESCRIPTION
                    "Set redistribute static route metric
                    Default: 15"
    ::= { ospfSettings 6 }

    ospfRedistributeRip OBJECT-TYPE
    SYNTAX  INTEGER{
            enable(1),
            disable(2)
    }
    MAX-ACCESS  read-write
    STATUS  current
    DESCRIPTION
                    "Enable redistribute RIP"
    ::= { ospfSettings 7 }

    ospfRedistributeRipMetricType OBJECT-TYPE
    SYNTAX  INTEGER{
            type1(1),
            type2(2)
    }
    MAX-ACCESS  read-write
    STATUS  current
    DESCRIPTION
                    "Set redistribute RIP metric type
                    Default: 1
                    1(1): External Type 1, add up the cost toward the destination
                    2(2): External Type 2, with default metric of 20 and will never change/increment through every hops"
    ::= { ospfSettings 8 }

    ospfRedistributeRipMetric OBJECT-TYPE
    SYNTAX  INTEGER(0..16777215)
    MAX-ACCESS  read-write
    STATUS  current
    DESCRIPTION
                    "Set redistribute RIP metric
                    Default: 15"
    ::= { ospfSettings 9 }

        --	ospfNetworkTable
    ospfNetworkTable OBJECT-TYPE
    SYNTAX  SEQUENCE OF OspfNetworkEntry
    MAX-ACCESS  not-accessible
    STATUS  current
    DESCRIPTION
                ""
    ::= { layer3Setup 7 }

    ospfNetworkEntry OBJECT-TYPE
    SYNTAX  OspfNetworkEntry
    MAX-ACCESS  not-accessible
    STATUS  current
    DESCRIPTION     "An entry in ospfNetworkTable."
    INDEX           { ospfNetworkAddress, ospfNetworkMask, ospfNetworkAreaId }
    ::= { ospfNetworkTable 1 }

    OspfNetworkEntry ::=
    SEQUENCE {
        ospfNetworkAddress				IpAddress,
        ospfNetworkMask					INTEGER,
        ospfNetworkAreaId				IpAddress,
        ospfNetworkStatus			INTEGER,
        ospfNetworkPassive			INTEGER
    }

    ospfNetworkAddress OBJECT-TYPE
    SYNTAX  IpAddress
    MAX-ACCESS  read-only
    STATUS  current
    DESCRIPTION
                    "OSPF network IP address.
                    Range: 0.0.0.1 ~ 223.255.255.255"
    ::= { ospfNetworkEntry 1 }

    ospfNetworkMask OBJECT-TYPE
    SYNTAX  INTEGER (1..32)
    MAX-ACCESS  read-only
    STATUS  current
    DESCRIPTION
                    "OSPF network mask.
                    Range: 1 ~ 32"
    ::= { ospfNetworkEntry 2 }

    ospfNetworkAreaId OBJECT-TYPE
    SYNTAX  IpAddress
    MAX-ACCESS  read-write
    STATUS  current
    DESCRIPTION
                    "OSPF network area ID.
                    Range: 0.0.0.0 ~ 255.255.255.255"
    ::= { ospfNetworkEntry 3 }

    ospfNetworkStatus OBJECT-TYPE
    SYNTAX  INTEGER{
            inactive(0),
            active(1)
    }
    MAX-ACCESS  read-write
    STATUS  current
    DESCRIPTION
                    "Status of OSPF network."
    ::= { ospfNetworkEntry 4 }
    
    ospfNetworkPassive OBJECT-TYPE
    SYNTAX  INTEGER{
            false(0),
            true(1)
    }
    MAX-ACCESS  read-write
    STATUS  current
    DESCRIPTION
                    "Status of Passive-Iface setting."
    ::= { ospfNetworkEntry 5 }

    --	ospfAreaTable
    ospfAreaSetupTable OBJECT-TYPE
    SYNTAX  SEQUENCE OF OspfAreaSetupEntry
    MAX-ACCESS  not-accessible
    STATUS  current
    DESCRIPTION
                ""
    ::= { layer3Setup 8 }

    ospfAreaSetupEntry OBJECT-TYPE
    SYNTAX  OspfAreaSetupEntry
    MAX-ACCESS  not-accessible
    STATUS  current
    DESCRIPTION     "An entry in ospfAreaTable."
    INDEX           { ospfAreaId }
    ::= { ospfAreaSetupTable 1 }

    OspfAreaSetupEntry ::=
    SEQUENCE {
        ospfAreaId					IpAddress,
        ospfAreaName				DisplayString,
        ospfAreaDefaultCost		INTEGER,
        ospfAreaAuthProtocol		INTEGER,
        ospfAreaStub			INTEGER,
        ospfAreaNoSummary			INTEGER,
        ospfArearRowStatus			RowStatus
    }

    ospfAreaId OBJECT-TYPE
    SYNTAX  IpAddress
    MAX-ACCESS  read-only
    STATUS  current
    DESCRIPTION
                    "OSPF area ID."
    ::= { ospfAreaSetupEntry 1 }

    ospfAreaName OBJECT-TYPE
    SYNTAX  DisplayString (SIZE (0..32))
    MAX-ACCESS  read-write
    STATUS  current
    DESCRIPTION
                    "OSPF area name."
    ::= { ospfAreaSetupEntry 2 }

    ospfAreaDefaultCost OBJECT-TYPE
    SYNTAX  INTEGER (0..16777215)
    MAX-ACCESS  read-write
    STATUS  current
    DESCRIPTION
                    "OSPF area default cost,
                    can be set only when current area is stub or NSSA area.
                    Default: 15"
    ::= { ospfAreaSetupEntry 3 }

    ospfAreaAuthProtocol OBJECT-TYPE
    SYNTAX  INTEGER{
            none(0),
            simple(1),
            md5(2)
    }
    MAX-ACCESS  read-write
    STATUS  current
    DESCRIPTION
                    "OSPF area authentication type."
    ::= { ospfAreaSetupEntry 4 }

	ospfAreaStub  OBJECT-TYPE
    SYNTAX  INTEGER{
            enable(1),
            disable(2)
    }
    MAX-ACCESS  read-write
    STATUS  current
    DESCRIPTION
                    "OSPF area stub."
    ::= { ospfAreaSetupEntry 5 }
    
	ospfAreaNoSummary  OBJECT-TYPE
    SYNTAX  INTEGER{
            enable(1),
            disable(2)
    }
    MAX-ACCESS  read-write
    STATUS  current
    DESCRIPTION
                    "OSPF area no-summary."
    ::= { ospfAreaSetupEntry 6 }

    ospfArearRowStatus OBJECT-TYPE
    SYNTAX  RowStatus
    MAX-ACCESS  read-create
    STATUS  current
    DESCRIPTION
                    "Row status of OSPF area"
    ::= { ospfAreaSetupEntry 7 }
    
    --	ospfSummaryAddrTable
    ospfSummaryAddrTable OBJECT-TYPE
    SYNTAX  SEQUENCE OF OspfSummaryAddrEntry
    MAX-ACCESS  not-accessible
    STATUS  current
    DESCRIPTION
                ""
    ::= { layer3Setup 9 }

    ospfSummaryAddrEntry OBJECT-TYPE
    SYNTAX  OspfSummaryAddrEntry
    MAX-ACCESS  not-accessible
    STATUS  current
    DESCRIPTION     "An entry in ospfSummaryAddrTable."
    INDEX           { ospfSummaryAddress, ospfSummaryAddrMask }
    ::= { ospfSummaryAddrTable 1 }

    OspfSummaryAddrEntry ::=
    SEQUENCE {
        ospfSummaryAddress				IpAddress,
        ospfSummaryAddrMask					INTEGER,
        ospfSummaryAddrRowStatus				RowStatus
    }

    ospfSummaryAddress OBJECT-TYPE
    SYNTAX  IpAddress
    MAX-ACCESS  read-only
    STATUS  current
    DESCRIPTION
                    "OSPF Summary IP address.
                    Range: 0.0.0.1 ~ 223.255.255.255"
    ::= { ospfSummaryAddrEntry 1 }

    ospfSummaryAddrMask OBJECT-TYPE
    SYNTAX  INTEGER (1..32)
    MAX-ACCESS  read-only
    STATUS  current
    DESCRIPTION
                    "OSPF SummaryAddr mask.
                    Range: 1 ~ 32"
    ::= { ospfSummaryAddrEntry 2 }

    ospfSummaryAddrRowStatus OBJECT-TYPE
    SYNTAX  RowStatus
    MAX-ACCESS  read-create
    STATUS  current
    DESCRIPTION
                    "Row status of summary address."
    ::= { ospfSummaryAddrEntry 3 }

    routerDomainSetup OBJECT IDENTIFIER ::= { l3Routing 2 }

--	routing protocol per VLAN settings
--	routerDomainIpTable
    routerDomainIpTable OBJECT-TYPE
    SYNTAX  SEQUENCE OF RouterDomainIpEntry
    MAX-ACCESS  not-accessible
    STATUS  current
    DESCRIPTION
                ""
    ::= { routerDomainSetup 1 }

    routerDomainIpEntry OBJECT-TYPE
    SYNTAX  RouterDomainIpEntry
    MAX-ACCESS  not-accessible
    STATUS  current
    DESCRIPTION     "An entry in routerDomainIpTable."
    INDEX           { ospfNetworkAddress, ospfNetworkMask }
    ::= { routerDomainIpTable 1 }

    RouterDomainIpEntry ::=
    SEQUENCE {
        routerDomainIpOspfCost               INTEGER,
        routerDomainIpOspfPriority           INTEGER,
        routerDomainIpOspfRetransmitInterval INTEGER,
        routerDomainIpOspfTransmitDelay      INTEGER,
        routerDomainIpOspfDeadInterval       INTEGER,
        routerDomainIpOspfHelloInterval      INTEGER,
        routerDomainIpOspfAuth               INTEGER,
        routerDomainIpOspfAuthSimpleKey      DisplayString,
        routerDomainIpOspfMd5KeyId           INTEGER,
        routerDomainIpOspfMd5Key             DisplayString
    }

    routerDomainIpOspfCost OBJECT-TYPE
    SYNTAX  INTEGER (1..65535)
    MAX-ACCESS  read-write
    STATUS  current
    DESCRIPTION
                    "OSPF interface cost.
                    Range: 1 ~ 65535
                    Default: 15"
    ::= { routerDomainIpEntry 1 }

    routerDomainIpOspfPriority OBJECT-TYPE
    SYNTAX  INTEGER (0..255)
    MAX-ACCESS  read-write
    STATUS  current
    DESCRIPTION
                    "OSPF interface priority.
                    Range: 0 ~ 255
                    Default: 1"
    ::= { routerDomainIpEntry 2 }

    routerDomainIpOspfRetransmitInterval OBJECT-TYPE
    SYNTAX  INTEGER (1..65535)
    MAX-ACCESS  read-write
    STATUS  current
    DESCRIPTION
                    "OSPF interface retransmit interval.
                    Range: 1 ~ 65535
                    Default: 5"
    ::= { routerDomainIpEntry 3 }

    routerDomainIpOspfTransmitDelay OBJECT-TYPE
    SYNTAX  INTEGER (1..65535)
    MAX-ACCESS  read-write
    STATUS  current
    DESCRIPTION
                    "OSPF interface transmit delay.
                    Range: 1 ~ 65535
                    Default: 1"
    ::= { routerDomainIpEntry 4 }

    routerDomainIpOspfDeadInterval OBJECT-TYPE
    SYNTAX  INTEGER(1..65535)
    MAX-ACCESS  read-write
    STATUS  current
    DESCRIPTION
                    "OSPF interface dead interval.
                    Range: 1 ~ 65535
                    Default: 40"
    ::= { routerDomainIpEntry 5 }

    routerDomainIpOspfHelloInterval OBJECT-TYPE
    SYNTAX  INTEGER (1..65535)
    MAX-ACCESS  read-write
    STATUS  current
    DESCRIPTION
                    "OSPF interface hello interval.
                    Range: 1 ~ 65535
                    Default: 10"
    ::= { routerDomainIpEntry 6 }

    routerDomainIpOspfAuth OBJECT-TYPE
    SYNTAX  INTEGER {
        same_as_area(0),
        none(1),
        simple(2),
        md5(3)
    }
    MAX-ACCESS  read-write
    STATUS  current
    DESCRIPTION
                    "OSPF interface authentication type."
    ::= { routerDomainIpEntry 7 }

    routerDomainIpOspfAuthSimpleKey OBJECT-TYPE
    SYNTAX  DisplayString
    MAX-ACCESS  read-write
    STATUS  current
    DESCRIPTION
                    "OSPF simple key, 8 printable characters.
                    Simple key can only be set when authentication method is set as 'simple(1)'
                    Set null string to remove simple key setting"
    ::= { routerDomainIpEntry 8 }

    routerDomainIpOspfMd5KeyId OBJECT-TYPE
    SYNTAX  INTEGER (1..255)
    MAX-ACCESS  read-write
    STATUS  current
    DESCRIPTION
                    "OSPF interface message-digest key ID.
                    Range: 1 ~ 255
                    0 indicates key ID is not set."
    ::= { routerDomainIpEntry 9 }

    routerDomainIpOspfMd5Key OBJECT-TYPE
    SYNTAX  DisplayString
    MAX-ACCESS  read-write
    STATUS  current
    DESCRIPTION
                    "OSPF interface message-digest key, 16 printable characters.
                    MD5 key can only be set when authentication method is set as 'md5(2)',
                    key id and key must can be set only via variable binding option.
                    Set null string to remove message-digest key setting"
    ::= { routerDomainIpEntry 10 }

--  39.ipStatus

        ipStatusTable	OBJECT-TYPE
        SYNTAX	SEQUENCE OF IpStatusEntry
        MAX-ACCESS  not-accessible
        STATUS  current
        DESCRIPTION
                 	""
        ::= { ipStatus 1 }

		ipStatusEntry OBJECT-TYPE
        SYNTAX	IpStatusEntry
        MAX-ACCESS	not-accessible
        STATUS	current
        DESCRIPTION    	""
        INDEX          	{ ipStatusIPAddress, ipStatusVid}
        ::= { ipStatusTable 1 }

        IpStatusEntry ::=
		SEQUENCE {
        	ipStatusIPAddress	IpAddress,
        	ipStatusVid		INTEGER,
        	ipStatusPort		DisplayString,
        	ipStatusType		INTEGER
         }

        ipStatusIPAddress OBJECT-TYPE
        SYNTAX  IpAddress
        MAX-ACCESS  read-only
        STATUS  current
        DESCRIPTION
                      	""
        ::= { ipStatusEntry 1 }

        ipStatusVid OBJECT-TYPE
        SYNTAX  INTEGER
        MAX-ACCESS  read-only
        STATUS  current
        DESCRIPTION
                      	""
        ::= { ipStatusEntry 2 }

        ipStatusPort OBJECT-TYPE
        SYNTAX  DisplayString
        MAX-ACCESS  read-only
        STATUS  current
        DESCRIPTION
                      	""
        ::= { ipStatusEntry 3 }

        ipStatusType OBJECT-TYPE
        SYNTAX  INTEGER{
			static(1),
			dynamic(2)
        }
        MAX-ACCESS  read-only
        STATUS  current
        DESCRIPTION
                      	""
        ::= { ipStatusEntry 4 }

----  --41.ospf ext. table
--
-- 		ospfInterfaceTable
--        ospfInterfaceTable	OBJECT-TYPE
--        SYNTAX	SEQUENCE OF OspfInterfaceEntry
--        MAX-ACCESS  not-accessible
--        STATUS  current
--        DESCRIPTION
--                 	""
--        ::= { ospfExt 1 }
--
--		ospfInterfaceEntry OBJECT-TYPE
--        SYNTAX	OspfInterfaceEntry
--        MAX-ACCESS	not-accessible
--        STATUS	current
--        DESCRIPTION    	""
--		INDEX          	{ ospfIfIpAddress, ospfAddressLessIf }
--        ::= { ospfInterfaceTable 1 }
--
--        OspfInterfaceEntry ::=
--		SEQUENCE {
--        	ospfIfKeyId	INTEGER,
--        	ospfIfMaskbits	INTEGER,
--        	ospfIfDesignatedRouterID	IpAddress,
--        	ospfIfBackupDesignatedRouterID	IpAddress,
--            ospfIfNbrCount	INTEGER,
--            ospfIfAdjacentNbrCount	INTEGER,
--            ospfIfHelloDueTime	DisplayString
--        }
--        ospfIfKeyId OBJECT-TYPE
--        SYNTAX  INTEGER
--        MAX-ACCESS  read-write
--        STATUS  current
--        DESCRIPTION
--                      	""
--        ::= { ospfInterfaceEntry 1 }
--
--        ospfIfMaskbits OBJECT-TYPE
--        SYNTAX  INTEGER
--        MAX-ACCESS  read-only
--        STATUS  current
--        DESCRIPTION
--                      	""
--        ::= { ospfInterfaceEntry 2 }
--
--        ospfIfDesignatedRouterID OBJECT-TYPE
--        SYNTAX  IpAddress
--        MAX-ACCESS  read-only
--        STATUS  current
--        DESCRIPTION
--                      	""
--        ::= { ospfInterfaceEntry 3 }
--
--        ospfIfBackupDesignatedRouterID OBJECT-TYPE
--        SYNTAX  IpAddress
--        MAX-ACCESS  read-only
--        STATUS  current
--        DESCRIPTION
--                      	""
--        ::= { ospfInterfaceEntry 4 }
--
--        ospfIfNbrCount OBJECT-TYPE
--        SYNTAX  INTEGER
--        MAX-ACCESS  read-only
--        STATUS  current
--        DESCRIPTION
--                      	""
--        ::= { ospfInterfaceEntry 5 }
--
--        ospfIfAdjacentNbrCount OBJECT-TYPE
--        SYNTAX  INTEGER
--        MAX-ACCESS  read-only
--        STATUS  current
--        DESCRIPTION
--                      	""
--        ::= { ospfInterfaceEntry 6 }
--
--        ospfIfHelloDueTime OBJECT-TYPE
--        SYNTAX  DisplayString
--        MAX-ACCESS  read-only
--        STATUS  current
--        DESCRIPTION
--                      	""
--        ::= { ospfInterfaceEntry 7 }
--
--  	ospfAreaExtTable
--        ospfAreaExtTable	OBJECT-TYPE
--        SYNTAX	SEQUENCE OF OspfAreaExtEntry
--        MAX-ACCESS  not-accessible
--        STATUS  current
--        DESCRIPTION
--                 	""
--        ::= { ospfExt 2 }
--
--		ospfAreaExtEntry OBJECT-TYPE
--        SYNTAX	OspfAreaExtEntry
--        MAX-ACCESS	not-accessible
--        STATUS	current
--        DESCRIPTION    	""
--		INDEX          	{ ospfAreaId }
--        ::= { ospfAreaExtTable 1 }
--
--        OspfAreaExtEntry ::=
--		SEQUENCE {
--        	ospfAreaExtName	DisplayString
--        }
--        ospfAreaExtName OBJECT-TYPE
--        SYNTAX  DisplayString
--        MAX-ACCESS  read-write
--        STATUS  current
--        DESCRIPTION
--                      	""
--        ::= { ospfAreaExtEntry 1 }
--
-- 		ospfRedistributeRouteTable
--
--        ospfRedistributeRouteTable	OBJECT-TYPE
--        SYNTAX	SEQUENCE OF OspfRedistributeRouteEntry
--        MAX-ACCESS  not-accessible
--        STATUS  current
--        DESCRIPTION
--                 	""
--        ::= { ospfExt 3 }
--
--		ospfRedistributeRouteEntry OBJECT-TYPE
--        SYNTAX	OspfRedistributeRouteEntry
--        MAX-ACCESS	not-accessible
--        STATUS	current
--        DESCRIPTION    	""
--		INDEX          	{ ospfRedistributeRouteProtocol }
--        ::= { ospfRedistributeRouteTable 1 }
--
--        OspfRedistributeRouteEntry ::=
--		SEQUENCE {
--        	ospfRedistributeRouteProtocol	INTEGER,
--        	ospfRedistributeRouteState	EnabledStatus,
--        	ospfRedistributeRouteType	INTEGER,
--        	ospfRedistributeRouteMetric	INTEGER
--        }
--        ospfRedistributeRouteProtocol OBJECT-TYPE
--        SYNTAX  INTEGER{
--		rip(1),
--		static(2)
--        }
--        MAX-ACCESS  read-only
--        STATUS  current
--        DESCRIPTION
--                      	""
--        ::= { ospfRedistributeRouteEntry 1 }
--
--        ospfRedistributeRouteState OBJECT-TYPE
--        SYNTAX  EnabledStatus
--        MAX-ACCESS  read-write
--        STATUS  current
--        DESCRIPTION
--                      	""
--        ::= { ospfRedistributeRouteEntry 2 }
--
--        ospfRedistributeRouteType OBJECT-TYPE
--        SYNTAX  INTEGER
--        MAX-ACCESS  read-write
--        STATUS  current
--        DESCRIPTION
--                      	""
--        ::= { ospfRedistributeRouteEntry 3 }
--
--        ospfRedistributeRouteMetric OBJECT-TYPE
--        SYNTAX  INTEGER
--        MAX-ACCESS  read-write
--        STATUS  current
--        DESCRIPTION
--                      	""
--        ::= { ospfRedistributeRouteEntry 4 }
--
-- 		ospfNbrExtTable
--
--        ospfNbrExtTable	OBJECT-TYPE
--        SYNTAX	SEQUENCE OF OspfNbrExtEntry
--        MAX-ACCESS  not-accessible
--        STATUS  current
--        DESCRIPTION
--                 	""
--        ::= { ospfExt 4 }
--
--		ospfNbrExtEntry OBJECT-TYPE
--        SYNTAX	OspfNbrExtEntry
--        MAX-ACCESS	not-accessible
--        STATUS	current
--        DESCRIPTION    	""
--		INDEX          	{ ospfNbrIpAddr, ospfNbrAddressLessIndex }
--        ::= { ospfNbrExtTable 1 }
--
--        OspfNbrExtEntry ::=
--		SEQUENCE {
--        	ospfNbrExtRole	INTEGER,
--        	ospfNbrExtDeadtime	DisplayString,
--        	ospfNbrExtInterface	IpAddress,
--        	ospfNbrExtRXmtL	INTEGER,
--        	ospfNbrExtRqstL	INTEGER,
--        	ospfNbrExtDBsmL	INTEGER
--        }
--        ospfNbrExtRole OBJECT-TYPE
--        SYNTAX  INTEGER{
--		dr(1),
--		backup(2),
--		drOther(3)
--        }
--        MAX-ACCESS  read-only
--        STATUS  current
--        DESCRIPTION
--                      	""
--        ::= { ospfNbrExtEntry 1 }
--
--        ospfNbrExtDeadtime OBJECT-TYPE
--        SYNTAX  DisplayString
--        MAX-ACCESS  read-only
--        STATUS  current
--        DESCRIPTION
--                      	""
--        ::= { ospfNbrExtEntry 2 }
--
--        ospfNbrExtInterface OBJECT-TYPE
--        SYNTAX  IpAddress
--        MAX-ACCESS  read-only
--        STATUS  current
--        DESCRIPTION
--                      	""
--        ::= { ospfNbrExtEntry 3 }
--
--        ospfNbrExtRXmtL OBJECT-TYPE
--        SYNTAX  INTEGER
--        MAX-ACCESS  read-only
--        STATUS  current
--        DESCRIPTION
--                      	""
--        ::= { ospfNbrExtEntry 4 }
--
--        ospfNbrExtRqstL OBJECT-TYPE
--        SYNTAX  INTEGER
--        MAX-ACCESS  read-only
--        STATUS  current
--        DESCRIPTION
--                      	""
--        ::= { ospfNbrExtEntry 5 }
--
--        ospfNbrExtDBsmL OBJECT-TYPE
--        SYNTAX  INTEGER
--        MAX-ACCESS  read-only
--        STATUS  current
--        DESCRIPTION
--                      	""
--        ::= { ospfNbrExtEntry 6 }
--
-- 		ospfLsdbExtTable
--
--        ospfLsdbExtTable	OBJECT-TYPE
--        SYNTAX	SEQUENCE OF OspfLsdbExtEntry
--        MAX-ACCESS  not-accessible
--        STATUS  current
--        DESCRIPTION
--                 	""
--        ::= { ospfExt 5 }
--
--		ospfLsdbExtEntry OBJECT-TYPE
--        SYNTAX	OspfLsdbExtEntry
--        MAX-ACCESS	not-accessible
--        STATUS	current
--        DESCRIPTION    	""
--		INDEX          	{ ospfLsdbAreaId, ospfLsdbType, ospfLsdbLsid, ospfLsdbRouterId }
--        ::= { ospfLsdbExtTable 1 }
--
--        OspfLsdbExtEntry ::=
--		SEQUENCE {
--        	ospfLsdbExtLinkCount	INTEGER,
--        	ospfLsdbExtRouteAddress	IpAddress,
--        	ospfLsdbExtRouteMaskbits	INTEGER
--        }
--        ospfLsdbExtLinkCount OBJECT-TYPE
--        SYNTAX  INTEGER
--        MAX-ACCESS  read-only
--        STATUS  current
--        DESCRIPTION
--                      	""
--        ::= { ospfLsdbExtEntry 1 }
--
--        ospfLsdbExtRouteAddress OBJECT-TYPE
--        SYNTAX  IpAddress
--        MAX-ACCESS  read-only
--        STATUS  current
--        DESCRIPTION
--                      	""
--        ::= { ospfLsdbExtEntry 2 }
--
--        ospfLsdbExtRouteMaskbits OBJECT-TYPE
--        SYNTAX  INTEGER
--        MAX-ACCESS  read-only
--        STATUS  current
--        DESCRIPTION
--                      	""
--        ::= { ospfLsdbExtEntry 3 }
--
-- 		ospfVirtualLinkTable
--
--        ospfVirtualLinkTable	OBJECT-TYPE
--        SYNTAX	SEQUENCE OF OspfVirtualLinkEntry
--        MAX-ACCESS  not-accessible
--        STATUS  current
--        DESCRIPTION
--                 	""
--        ::= { ospfExt 6 }
--
--		ospfVirtualLinkEntry OBJECT-TYPE
--        SYNTAX	OspfVirtualLinkEntry
--        MAX-ACCESS	not-accessible
--        STATUS	current
--        DESCRIPTION    	""
--		INDEX          	{ ospfVirtIfAreaId, ospfVirtIfNeighbor }
--        ::= { ospfVirtualLinkTable 1 }
--
--        OspfVirtualLinkEntry ::=
--		SEQUENCE {
--        	ospfVirtualLinkName	DisplayString,
--        	ospfVirtualLinkKeyId	INTEGER
--        }
--        ospfVirtualLinkName OBJECT-TYPE
--        SYNTAX  DisplayString
--        MAX-ACCESS  read-write
--        STATUS  current
--        DESCRIPTION
--                      	""
--        ::= { ospfVirtualLinkEntry 1 }
--
--        ospfVirtualLinkKeyId OBJECT-TYPE
--        SYNTAX  INTEGER
--        MAX-ACCESS  read-write
--        STATUS  current
--        DESCRIPTION
--                      	""
--        ::= { ospfVirtualLinkEntry 2 }
--
-- 		ospfSummaryAddrTable
--
--	    ospfSummaryAddrTable  OBJECT-TYPE
--	    SYNTAX	SEQUENCE OF OspfSummaryAddrEntry
--	    MAX-ACCESS  not-accessible
--	    STATUS  current
--	    DESCRIPTION
--	             	""
--	    ::= { ospfExt 7 }
--
--		ospfSummaryAddrEntry  OBJECT-TYPE
--        SYNTAX	OspfSummaryAddrEntry
--        MAX-ACCESS	not-accessible
--        STATUS	current
--        DESCRIPTION    	"An entry in ospfSummaryAddrTable."
--        INDEX          	{ospfSummaryAddress , ospfSummaryAddrMaskBit}
--        ::= { ospfSummaryAddrTable 1 }
--
--        OspfSummaryAddrEntry ::=
--           SEQUENCE {
--            ospfSummaryAddress			IpAddress,
--            ospfSummaryAddrMaskBit		INTEGER,
--            ospfSummaryAddrRowStatus	RowStatus
--           }
--
--        ospfSummaryAddress OBJECT-TYPE
--        SYNTAX  IpAddress
--        MAX-ACCESS  read-only
--        STATUS  current
--        DESCRIPTION
--                      	"ip address for ospf summary address entry"
--        ::= { ospfSummaryAddrEntry 1 }
--
--        ospfSummaryAddrMaskBit OBJECT-TYPE
--        SYNTAX  INTEGER (1..32)
--        MAX-ACCESS  read-only
--        STATUS  current
--        DESCRIPTION
--                      	"mask-bits for ospf summary address entry"
--        ::= { ospfSummaryAddrEntry 2 }
--
--        ospfSummaryAddrRowStatus OBJECT-TYPE
--        SYNTAX  RowStatus
--        MAX-ACCESS  read-create
--        STATUS  current
--        DESCRIPTION
--                      	""
--        ::= { ospfSummaryAddrEntry 3 }
--
-- 		ospfGeneralExtGroup
--    ospfGeneralExtGroup OBJECT IDENTIFIER ::= { ospfExt 8 }
--
--    ospfDistance OBJECT-TYPE
--        SYNTAX   INTEGER
--        MAX-ACCESS   read-write
--        STATUS   current
--        DESCRIPTION
--           "The administrative distance of OSPF routes"
--
--      ::= { ospfGeneralExtGroup 1 }
--

----  --42.MRSTP

--    	mrstpSetup  OBJECT IDENTIFIER ::= { mrstp 1 }

--		mrstpBridgeTable  OBJECT-TYPE
--		SYNTAX	SEQUENCE OF MrstpBridgeEntry
--		MAX-ACCESS  not-accessible
--		STATUS  current
--		DESCRIPTION
--		    	""
--	    ::= { mrstpSetup 1 }

--		mrstpBridgeEntry  OBJECT-TYPE
--        SYNTAX	MrstpBridgeEntry
--        MAX-ACCESS	not-accessible
--        STATUS	current
--        DESCRIPTION    	"An entry in mrstpBridgeTable."
--        INDEX          	{ mrstpBridgeIndex }
--        ::= { mrstpBridgeTable 1 }

--        MrstpBridgeEntry ::=
--			SEQUENCE {
--	           	mrstpBridgeIndex				INTEGER,
--	           	mrstpState						INTEGER,
--	 			mrstpProtocolSpecification		INTEGER,
--	           	mrstpPriority					INTEGER,
--	        	mrstpTimeSinceTopologyChange	TimeTicks,
--	        	mrstpTopChanges					Counter,
--	        	mrstpDesignatedRoot				BridgeId,
--	        	mrstpRootCost					INTEGER,
--	        	mrstpRootPort					INTEGER,
--	        	mrstpMaxAge						Timeout,
--	        	mrstpHelloTime					Timeout,
--	        	mrstpHoldTime					INTEGER,
--	        	mrstpForwardDelay				Timeout,
--	        	mrstpBridgeMaxAge				Timeout,
--	        	mrstpBridgeHelloTime			Timeout,
--	        	mrstpBridgeForwardDelay			Timeout
--			}

----          -- the dot1dStp group

----          -- Implementation of the dot1dStp group is optional.  It is
----          -- implemented by those bridges that support the Spanning Tree
----          -- Protocol.

--          mrstpBridgeIndex OBJECT-TYPE
--              SYNTAX  INTEGER
--              MAX-ACCESS  read-only
--              STATUS  current
--              DESCRIPTION
--                      "The tree index of the MRSTP."
--              ::= { mrstpBridgeEntry 1 }

--		  mrstpState OBJECT-TYPE
--        	SYNTAX  EnabledStatus
--        	MAX-ACCESS  read-write
--        	STATUS  current
--        	DESCRIPTION
--                      "Enabled/disabled on the mrstp bridge."
--        	::= { mrstpBridgeEntry 2 }

--          mrstpProtocolSpecification OBJECT-TYPE
--              SYNTAX  INTEGER {
--                          unknown(1),
--                          decLb100(2),
--                          ieee8021d(3)
--                      }
--              MAX-ACCESS  read-only
--              STATUS  current
--              DESCRIPTION
--                      "An indication of what version of the Spanning
--                      Tree Protocol is being run.  The value
--                      'decLb100(2)' indicates the DEC LANbridge 100
--                      Spanning Tree protocol.  IEEE 802.1d
--                      implementations will return 'ieee8021d(3)'.  If
--                      future versions of the IEEE Spanning Tree Protocol
--                      are released that are incompatible with the
--                      current version a new value will be defined."
--              ::= { mrstpBridgeEntry 3 }

--          mrstpPriority OBJECT-TYPE
--              SYNTAX  INTEGER (0..65535)
--              MAX-ACCESS  read-write
--              STATUS  current
--              DESCRIPTION
--                      "The value of the write-able portion of the Bridge
--                      ID, i.e., the first two octets of the (8 octet
--                      long) Bridge ID.  The other (last) 6 octets of the
--                      Bridge ID are given by the value of
--                      dot1dBaseBridgeAddress."
--              REFERENCE
--                      "IEEE 802.1D-1990: Section 4.5.3.7"
--              ::= { mrstpBridgeEntry 4 }

--          mrstpTimeSinceTopologyChange OBJECT-TYPE
--              SYNTAX  TimeTicks
--              MAX-ACCESS  read-only
--              STATUS  current
--              DESCRIPTION
--                      "The time (in hundredths of a second) since the
--                      last time a topology change was detected by the
--                      bridge entity."
--              REFERENCE
--                      "IEEE 802.1D-1990: Section 6.8.1.1.3"
--              ::= { mrstpBridgeEntry 5 }

--          mrstpTopChanges OBJECT-TYPE
--              SYNTAX  Counter
--              MAX-ACCESS  read-only
--              STATUS  current
--              DESCRIPTION
--                      "The total number of topology changes detected by
--                      this bridge since the management entity was last
--                      reset or initialized."
--              REFERENCE
--                      "IEEE 802.1D-1990: Section 6.8.1.1.3"
--              ::= { mrstpBridgeEntry 6 }

--          mrstpDesignatedRoot OBJECT-TYPE
--              SYNTAX  BridgeId
--              MAX-ACCESS  read-only
--              STATUS  current
--              DESCRIPTION
--                      "The bridge identifier of the root of the spanning
--                      tree as determined by the Spanning Tree Protocol
--                      as executed by this node.  This value is used as
--                      the Root Identifier parameter in all Configuration
--                      Bridge PDUs originated by this node."
--              REFERENCE
--                      "IEEE 802.1D-1990: Section 4.5.3.1"
--              ::= { mrstpBridgeEntry 7 }

--          mrstpRootCost OBJECT-TYPE
--              SYNTAX  INTEGER
--              MAX-ACCESS  read-only
--              STATUS  current
--              DESCRIPTION
--                      "The cost of the path to the root as seen from
--                      this bridge."
--              REFERENCE
--                      "IEEE 802.1D-1990: Section 4.5.3.2"
--              ::= { mrstpBridgeEntry 8 }

--          mrstpRootPort OBJECT-TYPE
--              SYNTAX  INTEGER
--              MAX-ACCESS  read-only
--              STATUS  current
--              DESCRIPTION
--                      "The port number of the port which offers the
--                      lowest cost path from this bridge to the root
--                      bridge."
--              REFERENCE
--                      "IEEE 802.1D-1990: Section 4.5.3.3"
--              ::= { mrstpBridgeEntry 9 }

--          mrstpMaxAge OBJECT-TYPE
--              SYNTAX  Timeout
--              MAX-ACCESS  read-only
--              STATUS  current
--              DESCRIPTION
--                      "The maximum age of Spanning Tree Protocol
--                      information learned from the network on any port
--                      before it is discarded, in units of hundredths of
--                      a second.  This is the actual value that this
--                      bridge is currently using."
--              REFERENCE
--                      "IEEE 802.1D-1990: Section 4.5.3.4"
--              ::= { mrstpBridgeEntry 10 }

--          mrstpHelloTime OBJECT-TYPE
--              SYNTAX  Timeout
--              MAX-ACCESS  read-only
--              STATUS  current
--              DESCRIPTION
--                      "The amount of time between the transmission of
--                      Configuration bridge PDUs by this node on any port
--                      when it is the root of the spanning tree or trying
--                      to become so, in units of hundredths of a second.
--                      This is the actual value that this bridge is
--                      currently using."
--              REFERENCE
--                      "IEEE 802.1D-1990: Section 4.5.3.5"
--              ::= { mrstpBridgeEntry 11 }

--          mrstpHoldTime OBJECT-TYPE
--              SYNTAX  INTEGER
--              MAX-ACCESS  read-only
--              STATUS  current
--              DESCRIPTION
--                      "This time value determines the interval length
--                      during which no more than two Configuration bridge
--                      PDUs shall be transmitted by this node, in units
--                      of hundredths of a second."
--              REFERENCE
--                      "IEEE 802.1D-1990: Section 4.5.3.14"
--              ::= { mrstpBridgeEntry 12 }

--          mrstpForwardDelay OBJECT-TYPE
--              SYNTAX  Timeout
--              MAX-ACCESS  read-only
--              STATUS  current
--              DESCRIPTION
--                      "This time value, measured in units of hundredths
--                      of a second, controls how fast a port changes its
--                      spanning state when moving towards the Forwarding
--                      state.  The value determines how long the port
--                      stays in each of the Listening and Learning
--                      states, which precede the Forwarding state.  This
--                      value is also used, when a topology change has
--                      been detected and is underway, to age all dynamic
--                      entries in the Forwarding Database.  [Note that
--                      this value is the one that this bridge is
--                      currently using, in contrast to
--                      mrstpBridgeForwardDelay which is the value that
--                      this bridge and all others would start using
--                      if/when this bridge were to become the root.]"
--              REFERENCE
--                      "IEEE 802.1D-1990: Section 4.5.3.6"
--              ::= { mrstpBridgeEntry 13 }

--          mrstpBridgeMaxAge OBJECT-TYPE
--              SYNTAX  Timeout (600..4000)
--              MAX-ACCESS  read-write
--              STATUS  current
--              DESCRIPTION
--                      "The value that all bridges use for MaxAge when
--                      this bridge is acting as the root.  Note that
--                      802.1D-1990 specifies that the range for this
--                      parameter is related to the value of
--                      mrstpBridgeHelloTime. The granularity of this
--                      timer is specified by 802.1D-1990 to be 1 second.
--                      An agent may return a badValue error if a set is
--                      attempted to a value which is not a whole number
--                      of seconds."
--              REFERENCE
--                      "IEEE 802.1D-1990: Section 4.5.3.8"
--              ::= { mrstpBridgeEntry 14 }

--          mrstpBridgeHelloTime OBJECT-TYPE
--              SYNTAX  Timeout (100..1000)
--              MAX-ACCESS  read-write
--              STATUS  current
--              DESCRIPTION
--                      "The value that all bridges use for HelloTime when
--                      this bridge is acting as the root.  The
--                      granularity of this timer is specified by 802.1D-
--                      1990 to be 1 second.  An agent may return a
--                      badValue error if a set is attempted to a value
--                      which is not a whole number of seconds."
--              REFERENCE
--                      "IEEE 802.1D-1990: Section 4.5.3.9"
--              ::= { mrstpBridgeEntry 15 }

--          mrstpBridgeForwardDelay OBJECT-TYPE
--              SYNTAX  Timeout (400..3000)
--              MAX-ACCESS  read-write
--              STATUS  current
--              DESCRIPTION
--                      "The value that all bridges use for ForwardDelay
--                      when this bridge is acting as the root.  Note that
--                      802.1D-1990 specifies that the range for this
--                      parameter is related to the value of
--                      mrstpBridgeMaxAge.  The granularity of this
--                      timer is specified by 802.1D-1990 to be 1 second.
--                      An agent may return a badValue error if a set is
--                      attempted to a value which is not a whole number
--                      of seconds."
--              REFERENCE
--                      "IEEE 802.1D-1990: Section 4.5.3.10"
--              ::= { mrstpBridgeEntry 16 }

----          -- The Spanning Tree Port Table

--          mrstpPortTable OBJECT-TYPE
--              SYNTAX  SEQUENCE OF MrstpPortEntry
--              MAX-ACCESS  not-accessible
--              STATUS  current
--              DESCRIPTION
--                      "A table that contains port-specific information
--                      for the Spanning Tree Protocol."
--              ::= { mrstpSetup 2 }

--          mrstpPortEntry OBJECT-TYPE
--              SYNTAX  MrstpPortEntry
--              MAX-ACCESS  not-accessible
--              STATUS  current
--              DESCRIPTION
--                      "A list of information maintained by every port
--                      about the Spanning Tree Protocol state for that
--                      port."
--              INDEX   { mrstpPort }
--              ::= { mrstpPortTable 1 }

--          MrstpPortEntry ::=
--              SEQUENCE {
--                  mrstpPort
--                      INTEGER,
--                  mrstpPortPriority
--                      INTEGER,
--                  mrstpPortState
--                      INTEGER,
--                  mrstpPortEnable
--                      INTEGER,
--                  mrstpPortPathCost
--                      INTEGER,
--                  mrstpPortDesignatedRoot
--                      BridgeId,
--                  mrstpPortDesignatedCost
--                      INTEGER,
--                  mrstpPortDesignatedBridge
--                      BridgeId,
--                  mrstpPortDesignatedPort
--                      OCTET STRING,
--                  mrstpPortForwardTransitions
--                      Counter,
--                  mrstpPortOnBridgeIndex
--                      INTEGER,
--                  mrstpPortAdminEdgePort
--            		  INTEGER,
--        		  mrstpPortOperEdgePort
--            		  INTEGER
--              }

--          mrstpPort OBJECT-TYPE
--              SYNTAX  INTEGER (1..65535)
--              MAX-ACCESS  read-only
--              STATUS  current
--              DESCRIPTION
--                      "The port number of the port for which this entry
--                      contains Spanning Tree Protocol management
--                      information."
--              REFERENCE
--                      "IEEE 802.1D-1990: Section 6.8.2.1.2"
--              ::= { mrstpPortEntry 1 }

--          mrstpPortPriority OBJECT-TYPE
--              SYNTAX  INTEGER (0..255)
--              MAX-ACCESS  read-write
--              STATUS  current
--              DESCRIPTION
--                      "The value of the priority field which is
--                      contained in the first (in network byte order)
--                      octet of the (2 octet long) Port ID.  The other
--                      octet of the Port ID is given by the value of
--                      mrstpPort."
--              REFERENCE
--                      "IEEE 802.1D-1990: Section 4.5.5.1"
--              ::= { mrstpPortEntry 2 }

--          mrstpPortState OBJECT-TYPE
--              SYNTAX  INTEGER {
--                          disabled(1),
--                          blocking(2),
--                          listening(3),
--                          learning(4),
--                          forwarding(5),
--                          broken(6)
--                      }
--              MAX-ACCESS  read-only
--              STATUS  current
--              DESCRIPTION
--                      "The port's current state as defined by
--                      application of the Spanning Tree Protocol.  This
--                      state controls what action a port takes on
--                      reception of a frame.  If the bridge has detected
--                      a port that is malfunctioning it will place that
--                      port into the broken(6) state.  For ports which
--                      are disabled (see mrstpPortEnable), this object
--                      will have a value of disabled(1)."
--              REFERENCE
--                      "IEEE 802.1D-1990: Section 4.5.5.2"
--              ::= { mrstpPortEntry 3 }

--          mrstpPortEnable OBJECT-TYPE
--              SYNTAX  INTEGER {
--                          enabled(1),
--                          disabled(2)
--                      }
--              MAX-ACCESS  read-write
--              STATUS  current
--              DESCRIPTION
--                      "The enabled/disabled status of the port."
--              REFERENCE
--                      "IEEE 802.1D-1990: Section 4.5.5.2"
--              ::= { mrstpPortEntry 4 }

--          mrstpPortPathCost OBJECT-TYPE
--              SYNTAX  INTEGER (1..65535)
--              MAX-ACCESS  read-write
--              STATUS  current
--              DESCRIPTION
--                      "The contribution of this port to the path cost of
--                      paths towards the spanning tree root which include
--                      this port.  802.1D-1990 recommends that the
--                      default value of this parameter be in inverse
--                      proportion to the speed of the attached LAN."
--              REFERENCE
--                      "IEEE 802.1D-1990: Section 4.5.5.3"
--              ::= { mrstpPortEntry 5 }

--          mrstpPortDesignatedRoot OBJECT-TYPE
--              SYNTAX  BridgeId
--              MAX-ACCESS  read-only
--              STATUS  current
--              DESCRIPTION
--                      "The unique Bridge Identifier of the Bridge
--                      recorded as the Root in the Configuration BPDUs
--                      transmitted by the Designated Bridge for the
--                      segment to which the port is attached."
--              REFERENCE
--                      "IEEE 802.1D-1990: Section 4.5.5.4"
--              ::= { mrstpPortEntry 6 }

--          mrstpPortDesignatedCost OBJECT-TYPE
--              SYNTAX  INTEGER
--              MAX-ACCESS  read-only
--              STATUS  current
--              DESCRIPTION
--                      "The path cost of the Designated Port of the
--                      segment connected to this port.  This value is
--                      compared to the Root Path Cost field in received
--                      bridge PDUs."
--              REFERENCE
--                      "IEEE 802.1D-1990: Section 4.5.5.5"
--              ::= { mrstpPortEntry 7 }

--          mrstpPortDesignatedBridge OBJECT-TYPE
--              SYNTAX  BridgeId
--              MAX-ACCESS  read-only
--              STATUS  current
--              DESCRIPTION
--                      "The Bridge Identifier of the bridge which this
--                      port considers to be the Designated Bridge for
--                      this port's segment."
--              REFERENCE
--                      "IEEE 802.1D-1990: Section 4.5.5.6"
--              ::= { mrstpPortEntry 8 }

--          mrstpPortDesignatedPort OBJECT-TYPE
--              SYNTAX  OCTET STRING (SIZE (2))
--              MAX-ACCESS  read-only
--              STATUS  current
--              DESCRIPTION
--                      "The Port Identifier of the port on the Designated
--                      Bridge for this port's segment."
--              REFERENCE
--                      "IEEE 802.1D-1990: Section 4.5.5.7"
--              ::= { mrstpPortEntry 9 }

--          mrstpPortForwardTransitions OBJECT-TYPE
--              SYNTAX  Counter
--              MAX-ACCESS  read-only
--              STATUS  current
--              DESCRIPTION
--                      "The number of times this port has transitioned
--                      from the Learning state to the Forwarding state."
--              ::= { mrstpPortEntry 10 }

--          mrstpPortOnBridgeIndex OBJECT-TYPE
--              SYNTAX  INTEGER
--              MAX-ACCESS  read-write
--              STATUS  current
--              DESCRIPTION
--                      "Indetify the bridge index that this port joined to in MRSTP."
--              ::= { mrstpPortEntry 11 }

--          mrstpPortAdminEdgePort OBJECT-TYPE
--              SYNTAX  INTEGER {
--                          true(1),
--                          false(2)
--                      }
--              MAX-ACCESS  read-write
--              STATUS  current
--              DESCRIPTION
--                      "	The administrative value of the Edge Port parameter.  A
--         				value of true(1) indicates that this port should be
--         				assumed as an edge-port, and a value of false(2) indicates
--         				that this port should be assumed as a non-edge-port. "
--              REFERENCE
--                      "IEEE 802.1t clause 14.8.2, 18.3.3"
--              ::= { mrstpPortEntry 12 }

--          mrstpPortOperEdgePort OBJECT-TYPE
--              SYNTAX  INTEGER {
--                          true(1),
--                          false(2)
--                      }
--              MAX-ACCESS  read-only
--              STATUS  current
--              DESCRIPTION
--  					  "	The operational value of the Edge Port parameter.  The
--			        	object is initialized to the value of the corresponding
--				        instance of dot1dStpPortAdminEdgePort.  When the
--				        corresponding instance of dot1dStpPortAdminEdgePort is
--				        set, this object will be changed as well.  This object
--				        will also be changed to false on reception of a BPDU."
--              REFERENCE
--                      "IEEE 802.1t clause 14.8.2, 18.3.4"
--              ::= { mrstpPortEntry 13 }


----  --MRSTP Trap
--		  mrstpNotifications     	OBJECT IDENTIFIER ::= { mrstp 2 }
--
--	 	  newRoot NOTIFICATION-TYPE
--      	  OBJECTS {
--       	   mrstpBridgeIndex
--      	  }
--      	  STATUS  current
--      	  DESCRIPTION
--       	     ""
--      	  ::= { mrstpNotifications 1 }
--
--    	  topologyChange NOTIFICATION-TYPE
--     	  OBJECTS {
--        	 mrstpBridgeIndex
--      	  }
--      	  STATUS  current
--      	  DESCRIPTION
--       	   ""
--     	  ::= { mrstpNotifications 2 }

-- ******************************************************************
-- *
-- 100. dhcp snooping
-- *
-- ******************************************************************

--
--  dhcp snooping vlan table
--

        dhcpSnpVlanTable	OBJECT-TYPE
        SYNTAX	SEQUENCE OF DhcpSnpVlanEntry
        MAX-ACCESS  not-accessible
        STATUS  current
        DESCRIPTION
                    "A. dhcpSnpVlanEntryOption82Enable
                           append [ponport vlan] into circuit-id of dhcp option-82
                           append [client's mac] into remote-id of dhcp option-82
                     B. dhcpSnpVlanEntryInfo
                           append [system_name] behind [ponport vlan] into circuit-id of dhcp option-82
                           If (A) & (B) are enabled at the same time, the circuit-id format would be [ponport vlan system_name]
                     C. dhcpSnpVlanEntryOption82FormatEnable
                           append specific format into circuit-id and remote-id, shown as below
                        => circuit-id : [SYS_ID /PONPORT:NNISVID.SNISVID ONTID/SN]
                        => remote-id  : Unnecessary
                     D. dhcpL2AgentOpt82CircuitIdInfo or dhcpL2AgentOpt82RemoteIdInfo
                     Note :
                        For pon ports, OLT uses below rules as dhcp option-82 configurations.
                            (D) > (C) > (A) = (B)
                    "
        ::= { dhcpSnp 1 }

		dhcpSnpVlanEntry OBJECT-TYPE
        SYNTAX	DhcpSnpVlanEntry
        MAX-ACCESS	not-accessible
        STATUS	current
        DESCRIPTION    	"An entry in dhcpSnpVlanTable."
        INDEX          	{ dhcpSnpVlanEntryVid }
        ::= { dhcpSnpVlanTable 1 }

        DhcpSnpVlanEntry ::=
		SEQUENCE {
        	dhcpSnpVlanEntryVid				INTEGER,
        	dhcpSnpVlanEntryEnable			EnabledStatus,
        	dhcpSnpVlanEntryOption82Enable	EnabledStatus,
        	dhcpSnpVlanEntryInfo			EnabledStatus,
        	dhcpSnpVlanEntryOption82FormatEnable	EnabledStatus
        }

        dhcpSnpVlanEntryVid OBJECT-TYPE
        SYNTAX  INTEGER (1..4094)
        MAX-ACCESS  read-only
        STATUS  current
        DESCRIPTION
                      	"The vlan id of specified dhcp snooping entry."
        ::= { dhcpSnpVlanEntry 1 }

        dhcpSnpVlanEntryEnable OBJECT-TYPE
        SYNTAX  EnabledStatus
        MAX-ACCESS  read-write
        STATUS  current
        DESCRIPTION
                      	"Enable/Disable dhcp snooping on specified vlan."
        ::= { dhcpSnpVlanEntry 2 }

        dhcpSnpVlanEntryOption82Enable OBJECT-TYPE
        SYNTAX  EnabledStatus
        MAX-ACCESS  read-write
        STATUS  current
        DESCRIPTION
                      	"Enable/Disable dhcp snooping option 82 on specified vlan."
        ::= { dhcpSnpVlanEntry 3 }

        dhcpSnpVlanEntryInfo OBJECT-TYPE
        SYNTAX  EnabledStatus
        MAX-ACCESS  read-write
        STATUS  current
        DESCRIPTION
                      	"Enable/Disable dhcp snooping information on specified vlan."
        ::= { dhcpSnpVlanEntry 4 }

        dhcpSnpVlanEntryOption82FormatEnable OBJECT-TYPE
        SYNTAX  EnabledStatus
        MAX-ACCESS  read-write
        STATUS  current
        DESCRIPTION
                      	"Enable/Disable dhcp snooping option 82 with specific format on specified vlan."
        ::= { dhcpSnpVlanEntry 5 }

--
--  dhcp snooping interface table
--

        dhcpSnpPortTable	OBJECT-TYPE
        SYNTAX	SEQUENCE OF DhcpSnpPortEntry
        MAX-ACCESS  not-accessible
        STATUS  current
        DESCRIPTION
                 	""
        ::= { dhcpSnp 2 }

		dhcpSnpPortEntry OBJECT-TYPE
        SYNTAX	DhcpSnpPortEntry
        MAX-ACCESS	not-accessible
        STATUS	current
        DESCRIPTION    	"An entry in dhcpSnpPortTable."
        INDEX          	{ dhcpSnpPortEntryPort }
        ::= { dhcpSnpPortTable 1 }

        DhcpSnpPortEntry ::=
		SEQUENCE {
        	dhcpSnpPortEntryPort		INTEGER,
        	dhcpSnpPortEntryTrust		EnabledStatus,
        	dhcpSnpPortEntryRate		INTEGER
        }

        dhcpSnpPortEntryPort OBJECT-TYPE
        SYNTAX  INTEGER
        MAX-ACCESS  read-only
        STATUS  current
        DESCRIPTION
                      	"The port index of specified dhcp snooping entry."
        ::= { dhcpSnpPortEntry 1 }

        dhcpSnpPortEntryTrust OBJECT-TYPE
        SYNTAX  EnabledStatus
        MAX-ACCESS  read-write
        STATUS  current
        DESCRIPTION
                      	"Enable/Disable this port from being a trusted port for dhcp snooping."
        ::= { dhcpSnpPortEntry 2 }

        dhcpSnpPortEntryRate OBJECT-TYPE
        SYNTAX  INTEGER (0..2048)
        MAX-ACCESS  read-write
        STATUS  current
        DESCRIPTION
                      	"Set the maximum rate in packets per second (pps) that dhcp packets are
                      	 allowed to arrive at a trusted dhcp snooping port. 0 means unlimited."
        ::= { dhcpSnpPortEntry 3 }
--
--  	dhcp snooping binding table
--

        dhcpSnpBindTable	OBJECT-TYPE
        SYNTAX	SEQUENCE OF DhcpSnpBindEntry
        MAX-ACCESS  not-accessible
        STATUS  current
        DESCRIPTION
                 	""
        ::= { dhcpSnp 3 }

		dhcpSnpBindEntry OBJECT-TYPE
        SYNTAX	DhcpSnpBindEntry
        MAX-ACCESS	not-accessible
        STATUS	current
        DESCRIPTION    	"An entry in dhcpSnpBindTable."
        INDEX          	{ dhcpSnpBindEntryMac, dhcpSnpBindEntryVid }
        ::= { dhcpSnpBindTable 1 }

        DhcpSnpBindEntry ::=
		SEQUENCE {
        	dhcpSnpBindEntryMac		MacAddress,
        	dhcpSnpBindEntryVid		INTEGER,
        	dhcpSnpBindEntryIP		IpAddress,
        	dhcpSnpBindEntryLease		INTEGER,
        	dhcpSnpBindEntryType		INTEGER,
        	dhcpSnpBindEntryPort		DisplayString
        }

        dhcpSnpBindEntryMac OBJECT-TYPE
        SYNTAX  MacAddress
        MAX-ACCESS  read-only
        STATUS  current
        DESCRIPTION
                      	"The source MAC address in the binding."
        ::= { dhcpSnpBindEntry 1 }

        dhcpSnpBindEntryVid OBJECT-TYPE
        SYNTAX  INTEGER
        MAX-ACCESS  read-only
        STATUS  current
        DESCRIPTION
                      	"The source vlan id in the binding."
        ::= { dhcpSnpBindEntry 2 }

        dhcpSnpBindEntryIP OBJECT-TYPE
        SYNTAX  IpAddress
        MAX-ACCESS  read-only
        STATUS  current
        DESCRIPTION
                      	"The IP address assigned to the MAC address in the binding."
        ::= { dhcpSnpBindEntry 3 }

        dhcpSnpBindEntryLease OBJECT-TYPE
        SYNTAX  INTEGER
        MAX-ACCESS  read-only
        STATUS  current
        DESCRIPTION
                      	"Display how many days, hours, minutes, and seconds the binding is valid. For example,
                      	 2d3h4m5s means the binding is still valid for 2 days, 3 hours, 4 minutes, and 5 seconds.
                      	 This field displays infinity if the binding is always valid (for example, a static binding)."
        ::= { dhcpSnpBindEntry 4 }

        dhcpSnpBindEntryType OBJECT-TYPE
        SYNTAX  INTEGER { dynamic(2) }
        MAX-ACCESS  read-only
        STATUS  current
        DESCRIPTION
                      	"Display how the Switch learned the binding.
                       	 Static: This binding was learned from information provided manually by an administrator."
        ::= { dhcpSnpBindEntry 5 }

        dhcpSnpBindEntryPort OBJECT-TYPE
        SYNTAX  DisplayString
        MAX-ACCESS  read-only
        STATUS  current
        DESCRIPTION
                      	"Display the port number in the binding. If this field is blank, the binding applies to all ports."
        ::= { dhcpSnpBindEntry 6 }

--
--  dhcp snooping
--

	dhcpSnpEnable OBJECT-TYPE
	SYNTAX  EnabledStatus
	MAX-ACCESS  read-write
	STATUS  current
	DESCRIPTION
	              "Enable/Disable dhcp snooping."
	::= { dhcpSnp 4 }

--
--  dhcp snooping database
--


	dhcpSnpDb     	OBJECT IDENTIFIER ::= { dhcpSnp 5 }

	dhcpSnpDbAbort OBJECT-TYPE
	SYNTAX  INTEGER (10..65535)
	MAX-ACCESS  read-write
	STATUS  current
	DESCRIPTION
	              "Specify how long (10-65535 seconds) the Switch tries to complete a
	               specific update in the dhcp snooping database before it gives up."
	::= { dhcpSnpDb 1 }

	dhcpSnpDbWriteDelay OBJECT-TYPE
	SYNTAX  INTEGER (10..65535)
	MAX-ACCESS  read-write
	STATUS  current
	DESCRIPTION
	              "Specify how long (10-65535 seconds) the Switch waits to update the dhcp
	               snooping database the first time the current bindings change after an update."
	::= { dhcpSnpDb 2 }

	dhcpSnpDbUrl OBJECT-TYPE
	SYNTAX  DisplayString (SIZE (0..255))
	MAX-ACCESS  read-write
	STATUS  current
	DESCRIPTION
	              "Specify the location of the dhcp snooping database."
	::= { dhcpSnpDb 3 }

	dhcpSnpDbUrlRenew OBJECT-TYPE
	SYNTAX  DisplayString (SIZE (0..255))
	MAX-ACCESS  read-write
	STATUS  current
	DESCRIPTION
	              "Loads dynamic bindings from the specified dhcp snooping database."
	::= { dhcpSnpDb 4 }

	dhcpSnpDbStat     	OBJECT IDENTIFIER ::= { dhcpSnpDb 5 }

	dhcpSnpDbStatClear OBJECT-TYPE
	SYNTAX  EnabledStatus
	MAX-ACCESS  read-write
	STATUS  current
	DESCRIPTION
	              "Delete all statistics records of dhcp requests going through the Switch."
	::= { dhcpSnpDbStat 1 }

	dhcpSnpDbStatAgentRunning OBJECT-TYPE
	SYNTAX  INTEGER { none(0), read(1), write(2) }
	MAX-ACCESS  read-only
	STATUS  current
	DESCRIPTION
	              "Agent running state."
	::= { dhcpSnpDbStat 2 }

	dhcpSnpDbStatDelayExpiry OBJECT-TYPE
	SYNTAX  INTEGER
	MAX-ACCESS  read-only
	STATUS  current
	DESCRIPTION
	              "Delay timer expiry."
	::= { dhcpSnpDbStat 3 }

	dhcpSnpDbStatAbortExpiry OBJECT-TYPE
	SYNTAX  INTEGER
	MAX-ACCESS  read-only
	STATUS  current
	DESCRIPTION
	              "Abort timer expiry."
	::= { dhcpSnpDbStat 4 }

	dhcpSnpDbStatLastSuccTime OBJECT-TYPE
	SYNTAX  DisplayString
	MAX-ACCESS  read-only
	STATUS  current
	DESCRIPTION
	              "Last succeded time."
	::= { dhcpSnpDbStat 5 }

	dhcpSnpDbStatLastFailTime OBJECT-TYPE
	SYNTAX  DisplayString
	MAX-ACCESS  read-only
	STATUS  current
	DESCRIPTION
	              "Last failed time."
	::= { dhcpSnpDbStat 6 }

	dhcpSnpDbStatLastFailReason OBJECT-TYPE
	SYNTAX  DisplayString
	MAX-ACCESS  read-only
	STATUS  current
	DESCRIPTION
	              "Last failed reason."
	::= { dhcpSnpDbStat 7 }

	dhcpSnpDbStatTotalAttempt OBJECT-TYPE
	SYNTAX  INTEGER
	MAX-ACCESS  read-only
	STATUS  current
	DESCRIPTION
	              "Total attempt counter."
	::= { dhcpSnpDbStat 8 }

	dhcpSnpDbStatStartupFail OBJECT-TYPE
	SYNTAX  INTEGER
	MAX-ACCESS  read-only
	STATUS  current
	DESCRIPTION
	              "Startup failures counter."
	::= { dhcpSnpDbStat 9 }

	dhcpSnpDbStatSuccTrans OBJECT-TYPE
	SYNTAX  INTEGER
	MAX-ACCESS  read-only
	STATUS  current
	DESCRIPTION
	              "Successful transfers counter."
	::= { dhcpSnpDbStat 10 }

	dhcpSnpDbStatFailTrans OBJECT-TYPE
	SYNTAX  INTEGER
	MAX-ACCESS  read-only
	STATUS  current
	DESCRIPTION
	              "Failed transfers counter."
	::= { dhcpSnpDbStat 11 }

	dhcpSnpDbStatSuccRead OBJECT-TYPE
	SYNTAX  INTEGER
	MAX-ACCESS  read-only
	STATUS  current
	DESCRIPTION
	              "Successful reads counter."
	::= { dhcpSnpDbStat 12 }

	dhcpSnpDbStatFailRead OBJECT-TYPE
	SYNTAX  INTEGER
	MAX-ACCESS  read-only
	STATUS  current
	DESCRIPTION
	              "Failed reads counter."
	::= { dhcpSnpDbStat 13 }

	dhcpSnpDbStatSuccWrite OBJECT-TYPE
	SYNTAX  INTEGER
	MAX-ACCESS  read-only
	STATUS  current
	DESCRIPTION
	              "Successful writes counter."
	::= { dhcpSnpDbStat 14 }

	dhcpSnpDbStatFailWrite OBJECT-TYPE
	SYNTAX  INTEGER
	MAX-ACCESS  read-only
	STATUS  current
	DESCRIPTION
	              "Failed writes counter."
	::= { dhcpSnpDbStat 15 }

	dhcpSnpDbStatFirstSuccAccess OBJECT-TYPE
	SYNTAX  INTEGER { none(0), read(1), write(2) }
	MAX-ACCESS  read-only
	STATUS  current
	DESCRIPTION
	              "First success access."
	::= { dhcpSnpDbStat 16 }

	dhcpSnpDbStatLastIgnoreBindCol OBJECT-TYPE
	SYNTAX  INTEGER
	MAX-ACCESS  read-only
	STATUS  current
	DESCRIPTION
	              "Last ignored: binding collision."
	::= { dhcpSnpDbStat 17 }

	dhcpSnpDbStatLastIgnoreExpireLease OBJECT-TYPE
	SYNTAX  INTEGER
	MAX-ACCESS  read-only
	STATUS  current
	DESCRIPTION
	              "Last ignored: expired leases."
	::= { dhcpSnpDbStat 18 }

	dhcpSnpDbStatLastIgnoreInvalidIntf OBJECT-TYPE
	SYNTAX  INTEGER
	MAX-ACCESS  read-only
	STATUS  current
	DESCRIPTION
	              "Last ignored: invalid interface."
	::= { dhcpSnpDbStat 19 }

	dhcpSnpDbStatLastIgnoreUnsuppVlan OBJECT-TYPE
	SYNTAX  INTEGER
	MAX-ACCESS  read-only
	STATUS  current
	DESCRIPTION
	              "Last ignored: unsupported vlans."
	::= { dhcpSnpDbStat 20 }

	dhcpSnpDbStatLastIgnoreParse OBJECT-TYPE
	SYNTAX  INTEGER
	MAX-ACCESS  read-only
	STATUS  current
	DESCRIPTION
	              "Last ignored: parsing error."
	::= { dhcpSnpDbStat 21 }

	dhcpSnpDbStatTotalIgnoreBindCol OBJECT-TYPE
	SYNTAX  INTEGER
	MAX-ACCESS  read-only
	STATUS  current
	DESCRIPTION
	              "Total ignored: binding collision."
	::= { dhcpSnpDbStat 22 }

	dhcpSnpDbStatTotalIgnoreExpireLease OBJECT-TYPE
	SYNTAX  INTEGER
	MAX-ACCESS  read-only
	STATUS  current
	DESCRIPTION
	              "Total ignored: expired leases."
	::= { dhcpSnpDbStat 23 }

	dhcpSnpDbStatTotalIgnoreInvalidIntf OBJECT-TYPE
	SYNTAX  INTEGER
	MAX-ACCESS  read-only
	STATUS  current
	DESCRIPTION
	              "Total ignored: invalid interface."
	::= { dhcpSnpDbStat 24 }

	dhcpSnpDbStatTotalIgnoreUnsuppVlan OBJECT-TYPE
	SYNTAX  INTEGER
	MAX-ACCESS  read-only
	STATUS  current
	DESCRIPTION
	              "Total ignored: unsupported vlans."
	::= { dhcpSnpDbStat 25 }

	dhcpSnpDbStatTotalIgnoreParse OBJECT-TYPE
	SYNTAX  INTEGER
	MAX-ACCESS  read-only
	STATUS  current
	DESCRIPTION
	              "Total ignored: parsing error."
	::= { dhcpSnpDbStat 26 }

	dhcpSnpDbStatFirstSuccessAccess OBJECT-TYPE
	SYNTAX INTEGER{
        		none(0),
        		read(1),
        		write(2)
    }
	MAX-ACCESS  read-only
	STATUS  current
	DESCRIPTION
	              "First success access."
	::= { dhcpSnpDbStat 27 }

--
--  dhcp snooping dhcp vlan
--

	dhcpSnpDhcpVlan     	OBJECT IDENTIFIER ::= { dhcpSnp 6 }

	dhcpSnpDhcpVlanVid OBJECT-TYPE
	SYNTAX  INTEGER (0..4094)
	MAX-ACCESS  read-write
	STATUS  current
	DESCRIPTION
	              "Specify the vlan id you want to enable dhcp snooping on. 0: Disable dhcp vlan."
	::= { dhcpSnpDhcpVlan 1 }

-- ******************************************************************
-- *
-- 101. ip source guard
-- *
-- ******************************************************************

	    ipsgTable  OBJECT-TYPE
	    SYNTAX	SEQUENCE OF IpsgEntry
	    MAX-ACCESS  not-accessible
	    STATUS  current
	    DESCRIPTION
	             	""
	    ::= { ipsg 1 }

		ipsgEntry  OBJECT-TYPE
        SYNTAX	IpsgEntry
        MAX-ACCESS	not-accessible
        STATUS	current
        DESCRIPTION    	""
        INDEX          	{ ipsgEntryMac, ipsgEntryVid }
        ::= { ipsgTable 1 }

        IpsgEntry ::=
           SEQUENCE {
            ipsgEntryMac		MacAddress,
        	ipsgEntryVid		INTEGER,
        	ipsgEntryIp			IpAddress,
        	ipsgEntryLease		INTEGER,
        	ipsgEntryType		INTEGER,
        	ipsgEntryPort		OCTET STRING,
        	ipsgEntryState		RowStatus
           }

        ipsgEntryMac OBJECT-TYPE
        SYNTAX  MacAddress
        MAX-ACCESS  read-only
        STATUS  current
        DESCRIPTION
                      	""
        ::= { ipsgEntry 1 }

        ipsgEntryVid OBJECT-TYPE
        SYNTAX  INTEGER (1.. 4094)
        MAX-ACCESS  read-only
        STATUS  current
        DESCRIPTION
                      	""
        ::= { ipsgEntry 2 }

        ipsgEntryIp OBJECT-TYPE
        SYNTAX  IpAddress
        MAX-ACCESS  read-write
        STATUS  current
        DESCRIPTION
                      	""
        ::= { ipsgEntry 3 }

        ipsgEntryLease OBJECT-TYPE
        SYNTAX  INTEGER
        MAX-ACCESS  read-only
        STATUS  current
        DESCRIPTION
                      	"second"
        ::= { ipsgEntry 4 }

        ipsgEntryType OBJECT-TYPE
        SYNTAX  INTEGER { static(1), dhcp(2) }
        MAX-ACCESS  read-only
        STATUS  current
        DESCRIPTION
                      	""
        ::= { ipsgEntry 5 }

        ipsgEntryPort OBJECT-TYPE
        SYNTAX  OCTET STRING
        MAX-ACCESS  read-write
        STATUS  current
        DESCRIPTION
                      	"0 means any port"
        ::= { ipsgEntry 6 }

        ipsgEntryState OBJECT-TYPE
        SYNTAX  RowStatus
        MAX-ACCESS  read-create
        STATUS  current
        DESCRIPTION
                      	""
        ::= { ipsgEntry 7 }

-- ******************************************************************
-- *
-- 102. arpInspect
-- *
-- ******************************************************************

		arpInspectSetup  OBJECT IDENTIFIER ::= { arpInspect 1 }

        arpInspectState OBJECT-TYPE
        SYNTAX  EnabledStatus
        MAX-ACCESS  read-write
        STATUS  current
        DESCRIPTION
                      "Enable/Disable arp inspection."
        ::= { arpInspectSetup 1 }

        arpInspectFilterAgingTime OBJECT-TYPE
        SYNTAX  INTEGER (0..2147483647)
        MAX-ACCESS  read-write
        STATUS  current
        DESCRIPTION
                      "Specify how long (0-2147483647 seconds) MAC address filters remain
                       in the Switch after the Switch identifies an unauthorized ARP packet.
                       The Switch automatically deletes the MAC address filter afterwards."
        ::= { arpInspectSetup 2 }

		arpInspectLog  OBJECT IDENTIFIER ::= { arpInspectSetup 3 }

        arpInspectLogEntries OBJECT-TYPE
        SYNTAX  INTEGER	(0..1024)
        MAX-ACCESS  read-write
        STATUS  current
        DESCRIPTION
                      "Specify the maximum number (0-1024) of log messages that can be
                       generated by ARP packets and not sent to the syslog server."
        ::= { arpInspectLog 1 }

        arpInspectLogRate OBJECT-TYPE
        SYNTAX  INTEGER (0..1024)
        MAX-ACCESS  read-write
        STATUS  current
        DESCRIPTION
                      "Specify the number (0-1024) of syslog messages that can be sent to
                       the syslog server in one batch."
        ::= { arpInspectLog 2 }

        arpInspectLogInterval OBJECT-TYPE
        SYNTAX  INTEGER (0..86400)
        MAX-ACCESS  read-write
        STATUS  current
        DESCRIPTION
                      "Specify how often (0-86400 seconds) the Switch sends a batch of
                       syslog messages to the syslog server."
        ::= { arpInspectLog 3 }

		arpInspectVlanTable OBJECT-TYPE
        SYNTAX	SEQUENCE OF ArpInspectVlanEntry
        MAX-ACCESS  not-accessible
        STATUS  current
        DESCRIPTION
                 	""
        ::= { arpInspectSetup 4 }

		arpInspectVlanEntry OBJECT-TYPE
        SYNTAX	ArpInspectVlanEntry
        MAX-ACCESS	not-accessible
        STATUS	current
        DESCRIPTION    	"An entry in arpInspectVlanTable."
        INDEX          	{ arpInspectVlanVid }
        ::= { arpInspectVlanTable 1 }

        ArpInspectVlanEntry ::=
           SEQUENCE {
        	arpInspectVlanVid	INTEGER,
        	arpInspectVlanLog	INTEGER,
			arpInspectVlanStatus	INTEGER
           }

        arpInspectVlanVid OBJECT-TYPE
        SYNTAX  INTEGER (1..4094)
        MAX-ACCESS  read-only
        STATUS  current
        DESCRIPTION
                      	"The VLAN ID."
        ::= { arpInspectVlanEntry 1 }

        arpInspectVlanLog OBJECT-TYPE
        SYNTAX  INTEGER {
        		all (1),
        		none (2),
        		permit (3),
        		deny (4)
        }

        MAX-ACCESS  read-write
        STATUS  current
        DESCRIPTION
                      	"Enable logging of ARP inspection events on the specified VLAN(s).
                      	 Optionally specifies which types of events to log."
        ::= { arpInspectVlanEntry 2 }

        arpInspectVlanStatus OBJECT-TYPE
        SYNTAX  INTEGER {
        		enabled(1),
        		disabled(2)
        }
        MAX-ACCESS  read-write
        STATUS  current
        DESCRIPTION
                      	"Enable/Disable ARP inspection on the specified VLAN(s)."
        ::= { arpInspectVlanEntry 3 }

		arpInspectPortTable OBJECT-TYPE
        SYNTAX	SEQUENCE OF ArpInspectPortEntry
        MAX-ACCESS  not-accessible
        STATUS  current
        DESCRIPTION
                 	""
        ::= { arpInspectSetup 5 }

		arpInspectPortEntry OBJECT-TYPE
        SYNTAX	ArpInspectPortEntry
        MAX-ACCESS	not-accessible
        STATUS	current
        DESCRIPTION    	"An entry in arpInspectPortTable."
        INDEX          	{ arpInspectPortIndex }
        ::= { arpInspectPortTable 1 }

        ArpInspectPortEntry ::=
           SEQUENCE {
        	arpInspectPortIndex	INTEGER,
        	arpInspectPortTrust	INTEGER,
			arpInspectPortRate	INTEGER,
			arpInspectPortInterval	INTEGER
           }

        arpInspectPortIndex OBJECT-TYPE
        SYNTAX  INTEGER
        MAX-ACCESS  read-only
        STATUS  current
        DESCRIPTION
                      	"The port index."
        ::= { arpInspectPortEntry 1 }

        arpInspectPortTrust OBJECT-TYPE
        SYNTAX  INTEGER {
        		trusted(1),
        		untrusted(2)
        }
        MAX-ACCESS  read-write
        STATUS  current
        DESCRIPTION
                      	"Enable/Disable the port to be a trusted port for arp inspection.
                      	 The Switch does not discard ARP packets on trusted ports for any reason."
        ::= { arpInspectPortEntry 2 }

        arpInspectPortRate OBJECT-TYPE
        SYNTAX  INTEGER	(0..2048)
        MAX-ACCESS  read-write
        STATUS  current
        DESCRIPTION
                      	"Set the maximum number for DHCP packets that the switch receives from
                      	 each port each second. The switch discards any additional DHCP packets."
        ::= { arpInspectPortEntry 3 }

        arpInspectPortInterval OBJECT-TYPE
        SYNTAX  INTEGER	(1..15)
        MAX-ACCESS  read-write
        STATUS  current
        DESCRIPTION
                      	"Set the length of time over which the rate of ARP packets is monitored for each port."
        ::= { arpInspectPortEntry 4 }

		arpInspectStatus  OBJECT IDENTIFIER ::= { arpInspect 2 }

        arpInspectFilterClear OBJECT-TYPE
        SYNTAX  EnabledStatus
        MAX-ACCESS  read-write
        STATUS  current
        DESCRIPTION
                      "Clear all arp inspection database."
        ::= { arpInspectStatus 1 }

        arpInspectLogClear OBJECT-TYPE
        SYNTAX  EnabledStatus
        MAX-ACCESS  read-write
        STATUS  current
        DESCRIPTION
                      "Clear arp inspection logs."
        ::= { arpInspectStatus 2 }

		arpInspectFilterTable OBJECT-TYPE
        SYNTAX	SEQUENCE OF ArpInspectFilterEntry
        MAX-ACCESS  not-accessible
        STATUS  current
        DESCRIPTION
                 	""
        ::= { arpInspectStatus 3 }

		arpInspectFilterEntry OBJECT-TYPE
        SYNTAX	ArpInspectFilterEntry
        MAX-ACCESS	not-accessible
        STATUS	current
        DESCRIPTION    	"An entry in arpInspectFilterTable."
        INDEX          	{ arpInspectFilterMac, arpInspectFilterVid }
        ::= { arpInspectFilterTable 1 }

        ArpInspectFilterEntry ::=
           SEQUENCE {
        	arpInspectFilterMac	MacAddress,
        	arpInspectFilterVid	INTEGER,
			arpInspectFilterPort	INTEGER,
			arpInspectFilterExpiry	INTEGER,
			arpInspectFilterReason	INTEGER,
			arpInspectFilterRowStatus RowStatus
           }

        arpInspectFilterMac OBJECT-TYPE
        SYNTAX  MacAddress
        MAX-ACCESS  read-only
        STATUS  current
        DESCRIPTION
                      	"The MAC address."
        ::= { arpInspectFilterEntry 1 }

        arpInspectFilterVid OBJECT-TYPE
        SYNTAX  INTEGER (1..4094)
        MAX-ACCESS  read-only
        STATUS  current
        DESCRIPTION
                      	"The VLAN ID."
        ::= { arpInspectFilterEntry 2 }

        arpInspectFilterPort OBJECT-TYPE
        SYNTAX  INTEGER
        MAX-ACCESS  read-only
        STATUS  current
        DESCRIPTION
                      	"The port index."
        ::= { arpInspectFilterEntry 3 }

        arpInspectFilterExpiry OBJECT-TYPE
        SYNTAX  INTEGER
        MAX-ACCESS  read-only
        STATUS  current
        DESCRIPTION
                      	"The expiry time represents how long (in seconds)
                      	 the MAC address filter remains in the Switch."
        ::= { arpInspectFilterEntry 4 }

        arpInspectFilterReason OBJECT-TYPE
        SYNTAX  INTEGER {
        		macVid(1),
        		port(2),
        		ip(3)
        }
        MAX-ACCESS  read-only
        STATUS  current
        DESCRIPTION
                      	"The reason why the ARP packet was discarded."
        ::= { arpInspectFilterEntry 5 }

       arpInspectFilterRowStatus OBJECT-TYPE
        SYNTAX  RowStatus
        MAX-ACCESS  read-create
        STATUS  current
        DESCRIPTION
                      	"The status of arp inspect filter entry."
        ::= { arpInspectFilterEntry 6 }

		arpInspectLogTable OBJECT-TYPE
        SYNTAX	SEQUENCE OF ArpInspectLogEntry
        MAX-ACCESS  not-accessible
        STATUS  current
        DESCRIPTION
                 	""
        ::= { arpInspectStatus 4 }

		arpInspectLogEntry OBJECT-TYPE
        SYNTAX	ArpInspectLogEntry
        MAX-ACCESS	not-accessible
        STATUS	current
        DESCRIPTION    	"An entry in arpInspectLogTable."
        INDEX          	{ arpInspectLogMac, arpInspectLogVid, arpInspectLogPort, arpInspectLogIp, arpInspectLogReason }
        ::= { arpInspectLogTable 1 }

        ArpInspectLogEntry ::=
           SEQUENCE {
        	arpInspectLogMac	MacAddress,
        	arpInspectLogVid	INTEGER,
			arpInspectLogPort	INTEGER,
			arpInspectLogIp	IpAddress,
			arpInspectLogNumPkt	INTEGER,
			arpInspectLogReason	INTEGER,
			arpInspectLogTime	DateAndTime
           }

        arpInspectLogMac OBJECT-TYPE
        SYNTAX  MacAddress
        MAX-ACCESS  read-only
        STATUS  current
        DESCRIPTION
                      	"The MAC address."
        ::= { arpInspectLogEntry 1 }

        arpInspectLogVid OBJECT-TYPE
        SYNTAX  INTEGER (1..4094)
        MAX-ACCESS  read-only
        STATUS  current
        DESCRIPTION
                      	"The VLAN ID."
        ::= { arpInspectLogEntry 2 }

        arpInspectLogPort OBJECT-TYPE
        SYNTAX  INTEGER
        MAX-ACCESS  read-only
        STATUS  current
        DESCRIPTION
                      	"The port index."
        ::= { arpInspectLogEntry 3 }

        arpInspectLogIp OBJECT-TYPE
        SYNTAX  IpAddress
        MAX-ACCESS  read-only
        STATUS  current
        DESCRIPTION
                      	"The IP address."
        ::= { arpInspectLogEntry 4 }

        arpInspectLogNumPkt OBJECT-TYPE
        SYNTAX  INTEGER
        MAX-ACCESS  read-only
        STATUS  current
        DESCRIPTION
                      	"The number of ARP packets that were consolidated into this log message.
                      	 The Switch consolidates identical log messages generated by ARP packets
                      	 in the log consolidation interval into one log message."
        ::= { arpInspectLogEntry 5 }

        arpInspectLogReason OBJECT-TYPE
        SYNTAX  INTEGER {
        		deny (1),
        		denyStatic (2),
        		denyDHCP (3),
        		permitStatic (4),
        		permitDHCP (5)
        }
        MAX-ACCESS  read-only
        STATUS  current
        DESCRIPTION
                      	"The reason why the log message was generated."
        ::= { arpInspectLogEntry 6 }

        arpInspectLogTime OBJECT-TYPE
        SYNTAX  DateAndTime
        MAX-ACCESS  read-only
        STATUS  current
        DESCRIPTION
                      	"Record time when the log message was generated."
        ::= { arpInspectLogEntry 7 }

		arpInspectStatisticsTable OBJECT-TYPE
        SYNTAX	SEQUENCE OF ArpInspectStatisticsEntry
        MAX-ACCESS  not-accessible
        STATUS  current
        DESCRIPTION
                 	""
        ::= { arpInspectStatus 5 }

		arpInspectStatisticsEntry OBJECT-TYPE
        SYNTAX	ArpInspectStatisticsEntry
        MAX-ACCESS	not-accessible
        STATUS	current
        DESCRIPTION    	"An entry in arpInspectStatisticsTable."
        INDEX          	{ arpInspectStatisticsVid }
        ::= { arpInspectStatisticsTable 1 }

        ArpInspectStatisticsEntry ::=
           SEQUENCE {
        	arpInspectStatisticsVid	INTEGER,
			arpInspectStatisticsReceived	Counter32,
			arpInspectStatisticsRequest	Counter32,
			arpInspectStatisticsReply	Counter32,
			arpInspectStatisticsForward	Counter32,
			arpInspectStatisticsDrop	Counter32,
			arpInspectStatisticsClear	EnabledStatus
           }

        arpInspectStatisticsVid OBJECT-TYPE
        SYNTAX  INTEGER
        MAX-ACCESS  read-only
        STATUS  current
        DESCRIPTION
                      	"The VLAN ID."
        ::= { arpInspectStatisticsEntry 1 }

        arpInspectStatisticsReceived OBJECT-TYPE
        SYNTAX  Counter32
        MAX-ACCESS  read-only
        STATUS  current
        DESCRIPTION
                      	"Receive counter."
        ::= { arpInspectStatisticsEntry 2 }

        arpInspectStatisticsRequest OBJECT-TYPE
        SYNTAX  Counter32
        MAX-ACCESS  read-only
        STATUS  current
        DESCRIPTION
                      	"Request counter."
        ::= { arpInspectStatisticsEntry 3 }

        arpInspectStatisticsReply OBJECT-TYPE
        SYNTAX  Counter32
        MAX-ACCESS  read-only
        STATUS  current
        DESCRIPTION
                      	"Reply counter."
        ::= { arpInspectStatisticsEntry 4 }

        arpInspectStatisticsForward OBJECT-TYPE
        SYNTAX  Counter32
        MAX-ACCESS  read-only
        STATUS  current
        DESCRIPTION
                      	"Forward counter."
        ::= { arpInspectStatisticsEntry 5 }

        arpInspectStatisticsDrop OBJECT-TYPE
        SYNTAX  Counter32
        MAX-ACCESS  read-only
        STATUS  current
        DESCRIPTION
                      	"Drop counter."
        ::= { arpInspectStatisticsEntry 6 }

        arpInspectStatisticsClear OBJECT-TYPE
        SYNTAX  EnabledStatus
        MAX-ACCESS  read-write
        STATUS  current
        DESCRIPTION
                      	"Clear all ARP inspection statistics on the Switch.x`x`"
        ::= { arpInspectStatisticsEntry 7 }


-- ******************************************************************
-- *
-- 103. trTCMSetup
-- *
-- ******************************************************************

        trTCMState OBJECT-TYPE
        SYNTAX  EnabledStatus
        MAX-ACCESS  read-write
        STATUS  current
        DESCRIPTION
                      	"Two-rate three color marker enabled/disabled for the switch."
        ::= { trTCMSetup 1 }

        trTCMMode OBJECT-TYPE
        SYNTAX  INTEGER {
        	colorAware(0),
        	colorBlind(1)
        	}
        MAX-ACCESS  read-write
        STATUS  current
        DESCRIPTION
                      	""
        ::= { trTCMSetup 2 }

-- 		trTCMPortTable
        trTCMPortTable OBJECT-TYPE
        SYNTAX	SEQUENCE OF TrTCMPortEntry
        MAX-ACCESS  not-accessible
        STATUS  current
        DESCRIPTION
                 	""
        ::= { trTCMSetup 3 }

		trTCMPortEntry OBJECT-TYPE
        SYNTAX	TrTCMPortEntry
        MAX-ACCESS	not-accessible
        STATUS	current
        DESCRIPTION    	"An entry in trTCMPortTable."
        INDEX          	{ dot1dBasePort }
        ::= { trTCMPortTable 1 }

        TrTCMPortEntry ::=
		SEQUENCE {
	       	trTCMPortState	EnabledStatus,
			trTCMPortCIR	INTEGER,
			trTCMPortPIR	INTEGER,
			trTCMPortDscpGreen	INTEGER,
			trTCMPortDscpYellow	INTEGER,
			trTCMPortDscpRed	INTEGER
		}

        trTCMPortState OBJECT-TYPE
        SYNTAX  EnabledStatus
        MAX-ACCESS  read-write
        STATUS  current
        DESCRIPTION
                      	"Two-rate three color marker enabled/disabled on the port."
        ::= { trTCMPortEntry 1 }

        trTCMPortCIR OBJECT-TYPE
        SYNTAX  INTEGER
        MAX-ACCESS  read-write
        STATUS  current
        DESCRIPTION
                      	"Allowed CIR in pkts/s."
        ::= { trTCMPortEntry 2 }

        trTCMPortPIR OBJECT-TYPE
        SYNTAX  INTEGER
        MAX-ACCESS  read-write
        STATUS  current
        DESCRIPTION
                      	"Allowed PIR in pkts/s."
        ::= { trTCMPortEntry 3 }

        trTCMPortDscpGreen OBJECT-TYPE
        SYNTAX  INTEGER
        MAX-ACCESS  read-write
        STATUS  current
        DESCRIPTION
                      	"0-63"
        ::= { trTCMPortEntry 4 }

        trTCMPortDscpYellow OBJECT-TYPE
        SYNTAX  INTEGER
        MAX-ACCESS  read-write
        STATUS  current
        DESCRIPTION
                      	"0-63"
        ::= { trTCMPortEntry 5 }

        trTCMPortDscpRed OBJECT-TYPE
        SYNTAX  INTEGER
        MAX-ACCESS  read-write
        STATUS  current
        DESCRIPTION
                      	"0-63"
        ::= { trTCMPortEntry 6 }


-- ******************************************************************
-- *
-- 104. loopGuardSetup
-- *
-- ******************************************************************

        loopGuardState OBJECT-TYPE
        SYNTAX  EnabledStatus
        MAX-ACCESS  read-write
        STATUS  current
        DESCRIPTION
                      	""
        ::= { loopGuardSetup 1 }


-- 		loopGuardPortTable

		loopGuardPortTable OBJECT-TYPE
		SYNTAX	SEQUENCE OF LoopGuardPortEntry
        MAX-ACCESS  not-accessible
        STATUS  current
        DESCRIPTION
                 	""
        ::= { loopGuardSetup 2 }

		loopGuardPortEntry OBJECT-TYPE
        SYNTAX	LoopGuardPortEntry
        MAX-ACCESS	not-accessible
        STATUS	current
        DESCRIPTION    	"An entry in loopGuardPortTable."
        INDEX          	{ dot1dBasePort }
        ::= { loopGuardPortTable 1 }

		LoopGuardPortEntry ::=
		SEQUENCE {
			loopGuardPortState	EnabledStatus,
			loopGuardPortVlan	INTEGER
		}

        loopGuardPortState OBJECT-TYPE
        SYNTAX  EnabledStatus
        MAX-ACCESS  read-write
        STATUS  current
        DESCRIPTION
                      	""
        ::= { loopGuardPortEntry 1 }

        loopGuardPortVlan OBJECT-TYPE
        SYNTAX  INTEGER (0..4094)
        MAX-ACCESS  read-write
        STATUS  current
        DESCRIPTION
                      	"vid for loopguard, 0 means untag"
        ::= { loopGuardPortEntry 2 }

    loopGuardDetectionTime OBJECT-TYPE
    SYNTAX  INTEGER
    MAX-ACCESS  read-write
    STATUS  current
    DESCRIPTION
        "Configure loopguard detection time. (1 ~ 120 seconds)"
    ::= { loopGuardSetup 3 }

  -- 	loopGuardPortStatusTable
		loopGuardPortStatusTable OBJECT-TYPE
		SYNTAX	SEQUENCE OF LoopGuardPortStatusEntry
        MAX-ACCESS  not-accessible
        STATUS  current
        DESCRIPTION
                 	""
        ::= { loopGuardSetup 4 }

		loopGuardPortStatusEntry OBJECT-TYPE
        SYNTAX	LoopGuardPortStatusEntry
        MAX-ACCESS	not-accessible
        STATUS	current
        DESCRIPTION    	"An entry in loopGuardPortStatusTable."
        INDEX          	{ dot1dBasePort }
        ::= { loopGuardPortStatusTable 1 }

		LoopGuardPortStatusEntry ::=
		SEQUENCE {
			loopGuardPortTxPkts		Counter32,
			loopGuardPortRxPkts		Counter32,
			loopGuardPortBadPkts	Counter32,
			loopGuardShutdownTime	DisplayString,
		}

        loopGuardPortTxPkts OBJECT-TYPE
        SYNTAX  Counter32
        MAX-ACCESS  read-only
        STATUS  current
        DESCRIPTION
                      	"port loopguard total Tx packets."
        ::= { loopGuardPortStatusEntry 1 }

        loopGuardPortRxPkts OBJECT-TYPE
        SYNTAX  Counter32
        MAX-ACCESS  read-only
        STATUS  current
        DESCRIPTION
                      	"port loopguard total Rx packets."
        ::= { loopGuardPortStatusEntry 2 }

        loopGuardPortBadPkts OBJECT-TYPE
        SYNTAX  Counter32
        MAX-ACCESS  read-only
        STATUS  current
        DESCRIPTION
                      	"port loopguard total bad packets."
        ::= { loopGuardPortStatusEntry 3 }

        loopGuardShutdownTime OBJECT-TYPE
        SYNTAX  DisplayString
        MAX-ACCESS  read-only
        STATUS  current
        DESCRIPTION
                      	"port loopguard shutdown time."
        ::= { loopGuardPortStatusEntry 4 }

-- ******************************************************************
-- *
-- 105. subnetBasedVlanSetup
-- *
-- ******************************************************************

        subnetBasedVlanState OBJECT-TYPE
        SYNTAX  EnabledStatus
        MAX-ACCESS  read-write
        STATUS  current
        DESCRIPTION
        	"subnet-based vlan feature enabled/disabled for the switch."
        ::= { subnetBasedVlanSetup 1 }

        dhcpVlanOverrideState OBJECT-TYPE
        SYNTAX  EnabledStatus
        MAX-ACCESS  read-write
        STATUS  current
        DESCRIPTION
        	"dhcp vlan override enabled/disabled when subnet-based vlan is enabled."
        ::= { subnetBasedVlanSetup 2 }


	    subnetBasedVlanTable  OBJECT-TYPE
	    SYNTAX	SEQUENCE OF SubnetBasedVlanEntry
	    MAX-ACCESS  not-accessible
	    STATUS  current
	    DESCRIPTION
	             	""
	    ::= { subnetBasedVlanSetup 3 }

		subnetBasedVlanEntry  OBJECT-TYPE
        SYNTAX	SubnetBasedVlanEntry
        MAX-ACCESS	not-accessible
        STATUS	current
        DESCRIPTION    	"An entry in subnetBasedVlanTable."
        INDEX          	{subnetBasedVlanSrcIp , subnetBasedVlanSrcMaskBit}
        ::= { subnetBasedVlanTable 1 }

        SubnetBasedVlanEntry ::=
           SEQUENCE {
            subnetBasedVlanSrcIp			IpAddress,
            subnetBasedVlanSrcMaskBit		INTEGER,
            subnetBasedVlanName				DisplayString,
            subnetBasedVlanVid				INTEGER,
            subnetBasedVlanPriority			INTEGER,
            subnetBasedVlanEntryState		RowStatus
           }

        subnetBasedVlanSrcIp OBJECT-TYPE
        SYNTAX  IpAddress
        MAX-ACCESS  read-only
        STATUS  current
        DESCRIPTION
                      	"source ip for subnet-based vlan entry"
        ::= { subnetBasedVlanEntry 1 }


        subnetBasedVlanSrcMaskBit OBJECT-TYPE
        SYNTAX  INTEGER (1..32)
        MAX-ACCESS  read-only
        STATUS  current
        DESCRIPTION
                      	"source ip mask-bits for subnet-based vlan entry"
        ::= { subnetBasedVlanEntry 2 }

        subnetBasedVlanName OBJECT-TYPE
        SYNTAX  DisplayString (SIZE (0..32))
        MAX-ACCESS  read-write
        STATUS  current
        DESCRIPTION
                      	"name for subnet-based vlan entry"
        ::= { subnetBasedVlanEntry 3 }

        subnetBasedVlanVid OBJECT-TYPE
        SYNTAX  INTEGER (1..4094)
        MAX-ACCESS  read-write
        STATUS  current
        DESCRIPTION
                      	"vid for subnet-based vlan entry"
        ::= { subnetBasedVlanEntry 4 }


        subnetBasedVlanPriority OBJECT-TYPE
        SYNTAX  INTEGER (0..7)
        MAX-ACCESS  read-write
        STATUS  current
        DESCRIPTION
                      	"priority for subnet-based vlan entry"
        ::= { subnetBasedVlanEntry 5 }

        subnetBasedVlanEntryState OBJECT-TYPE
        SYNTAX  RowStatus
        MAX-ACCESS  read-create
        STATUS  current
        DESCRIPTION
                      	""
        ::= { subnetBasedVlanEntry 6 }


-- ******************************************************************
-- *
-- 106. MAC Authentication
-- *
-- ******************************************************************

-- macAuthenticationSetup

        macAuthenticationState OBJECT-TYPE
        SYNTAX  EnabledStatus
        MAX-ACCESS  read-write
        STATUS  current
        DESCRIPTION
                       ""
        ::= { macAuthenticationSetup 1 }

        macAuthenticationNamePrefix OBJECT-TYPE
        SYNTAX  DisplayString
        MAX-ACCESS  read-write
        STATUS  current
        DESCRIPTION
                       ""
        ::= { macAuthenticationSetup 2 }

        macAuthenticationPassword OBJECT-TYPE
        SYNTAX  DisplayString
        MAX-ACCESS  read-write
        STATUS  current
        DESCRIPTION
                       ""
        ::= { macAuthenticationSetup 3 }

        macAuthenticationTimeout OBJECT-TYPE
        SYNTAX  INTEGER
        MAX-ACCESS  read-write
        STATUS  current
        DESCRIPTION
                       ""
        ::= { macAuthenticationSetup 4 }

-- macAuthenticationPortTable

		macAuthenticationPortTable OBJECT-TYPE
        SYNTAX SEQUENCE OF MacAuthenticationPortEntry
        MAX-ACCESS  not-accessible
        STATUS  current
        DESCRIPTION
                  ""
        ::= { macAuthenticationSetup 5 }

 		macAuthenticationPortEntry OBJECT-TYPE
        SYNTAX MacAuthenticationPortEntry
        MAX-ACCESS not-accessible
        STATUS current
        DESCRIPTION     "An entry in macAuthenticationPortTable."
        INDEX           { dot1dBasePort }
        ::= { macAuthenticationPortTable 1 }

		MacAuthenticationPortEntry ::=
		SEQUENCE {
			macAuthenticationPortState EnabledStatus
		}

        macAuthenticationPortState OBJECT-TYPE
        SYNTAX  EnabledStatus
        MAX-ACCESS  read-write
        STATUS  current
        DESCRIPTION
                       ""
        ::= { macAuthenticationPortEntry 1 }

-- ******************************************************************
-- *
-- 107. MSTP
-- *
-- ******************************************************************
--****************************************************************
-- TEXTUAL-CONVENTIONs
--****************************************************************
		MstiOrCistInstanceIndex ::= TEXTUAL-CONVENTION
      		STATUS       current
    		DESCRIPTION
	            "This textual convention is an extension of the
	            MstiInstanceIndex convention.  This extension permits the
	            additional value of zero, which means Common and Internal
	            Spanning Tree (CIST)."
            SYNTAX      Integer32 (0..16)

-- mstpGen group reflects configurations/statuses
-- the Bridge as a unit
	    mstpGen			OBJECT IDENTIFIER ::= { mstp 1}

        mstpGenState		OBJECT-TYPE
        SYNTAX    EnabledStatus
        MAX-ACCESS    read-write
        STATUS    current
        DESCRIPTION
        "Enabled/disabled on the mrstp bridge."
        ::= { mstpGen 1 }

        mstpGenCfgIdName    OBJECT-TYPE
        SYNTAX    DisplayString
        MAX-ACCESS    read-write
        STATUS    current
        DESCRIPTION
        "The configuration name that identifies the MST
         region and is used as one of the inputs in the
         computation of the MST Configuration Identifier."
        REFERENCE
            "12.12.3.4.2.b)"
        ::= { mstpGen 2 }

        mstpGenCfgIdRevLevel OBJECT-TYPE
        SYNTAX    Integer32
        MAX-ACCESS    read-write
        STATUS    current
        DESCRIPTION
        "This object identifies the MST revision that
         identifies the MST region and is used as one
         of the inputs in the computation of the MST
         configuration Identifier."
        REFERENCE
            "12.12.3.4.2.c)"
        ::= { mstpGen 3 }


	  		mstpGenCfgIdCfgDigest  OBJECT-TYPE
            SYNTAX    OCTET STRING(SIZE(16))
            MAX-ACCESS    read-only
            STATUS    current
            DESCRIPTION
              "Configuration Digest."
            REFERENCE
               "12.12.3.3.3.a.4"
            ::= { mstpGen 4 }

	    	mstpGenHelloTime  OBJECT-TYPE
	        SYNTAX    Timeout (1..10)
            MAX-ACCESS    read-write
            STATUS    current
            DESCRIPTION
            ""
            ::= { mstpGen 5 }

        	mstpGenMaxAge    OBJECT-TYPE
            SYNTAX  Timeout (6..40)
            MAX-ACCESS  read-write
            STATUS  current
            DESCRIPTION
            ""
            ::= { mstpGen 6 }

        	mstpGenForwardDelay   OBJECT-TYPE
            SYNTAX  Timeout (4..30)
            MAX-ACCESS  read-write
            STATUS  current
            DESCRIPTION
            ""
            ::= {mstpGen 7}

        	mstpGenMaxHops  OBJECT-TYPE
            SYNTAX      Integer32 (1..255)
            MAX-ACCESS  read-write
            STATUS      current
            DESCRIPTION
               "13.22.f)"
            ::= { mstpGen 8 }

			mstpGenCistRootPathCost  OBJECT-TYPE
            SYNTAX      Integer32
            MAX-ACCESS  read-only
            STATUS      current
            DESCRIPTION
	    "."
            ::= { mstpGen 9 }

			mstpGenCistRootBrid  OBJECT-TYPE
            SYNTAX      OCTET STRING(SIZE(8))
            MAX-ACCESS  read-only
            STATUS      current
            DESCRIPTION
            "."
            ::= { mstpGen 10 }
-- MSTP MAP TABLE
        	mstMapTable        OBJECT-TYPE
            SYNTAX      SEQUENCE OF MstMapEntry
            MAX-ACCESS  not-accessible
            STATUS      current
            DESCRIPTION
               "This table contains one entry for each instance of MSTP."
            ::= { mstp 20 }

        	mstMapEntry        OBJECT-TYPE
            SYNTAX      MstMapEntry
            MAX-ACCESS  not-accessible
            STATUS      current
            DESCRIPTION
               "A conceptual row containing the status of the MSTP instance."
            INDEX  { mstMapIndex }
            ::= { mstMapTable 1 }

        	MstMapEntry ::= SEQUENCE {
                   mstMapIndex             MstiOrCistInstanceIndex,
                   mstMapVlans1k           OCTET STRING,
                   mstMapVlans2k           OCTET STRING,
                   mstMapVlans3k           OCTET STRING,
                   mstMapVlans4k           OCTET STRING,
                   mstMapRowStatus         RowStatus
        	}

        	mstMapIndex    OBJECT-TYPE
            SYNTAX      MstiOrCistInstanceIndex
            MAX-ACCESS  not-accessible
            STATUS      current
            DESCRIPTION
            "Uniquely identifies an instance. The entry of this table with index 0
            presents always, represents CIST. When SET operation "
            ::= { mstMapEntry 1 }

        	mstMapVlans1k      OBJECT-TYPE
            SYNTAX      OCTET STRING (SIZE (0..128))
            MAX-ACCESS  read-write
            STATUS      current
            DESCRIPTION
           "A string of octets containing one bit per VLAN. The
            first octet corresponds to VLANs with VlanIndex values
            1 through 8; the second octet to VLANs 9 through
            16 etc.  The most significant bit of each octet
            corresponds to the lowest VlanIndex value in that octet.

            For each VLAN that is mapped to this MSTP instance,
            the bit corresponding to that VLAN is set to '1'.
            Empty (zero) most significant octes are not mandatory."
            ::= { mstMapEntry 2 }

        	mstMapVlans2k      OBJECT-TYPE
            SYNTAX  OCTET STRING (SIZE (0..128))
            MAX-ACCESS  read-write
            STATUS  current
            DESCRIPTION
            "A string of octets containing one bit per VLAN for
             VLANS with VlanIndex values 1024 through 2047. The
             first octet corresponds to VLANs with VlanIndex values
             1024 through 1031; the second octet to VLANs 1032
             through 1039 etc.  The most significant bit of each
             octet corresponds to the lowest VlanIndex value in that
             octet.

             For each VLAN that is mapped to this MSTP instance,
             the bit corresponding to that VLAN is set to '1'.

             Empty (zero) most significant octes are not mandatory."
             ::= { mstMapEntry 3 }

        	mstMapVlans3k      OBJECT-TYPE
            SYNTAX      OCTET STRING (SIZE (0..128))
            MAX-ACCESS  read-write
            STATUS      current
            DESCRIPTION
            "A string of octets containing one bit per VLAN for
             VLANS with VlanIndex values 2048 through 3071. The
             first octet corresponds to VLANs with VlanIndex values
             of 2048 through 2055; the second octet to VLANs 2056
             through 2063 etc.  The most significant bit of each
             octet corresponds to the lowest VlanIndex value in that
             octet.

             For each VLAN that is mapped to this MSTP instance,
             the bit corresponding to that VLAN is set to '1'.

             Empty (zero) most significant octes are not mandatory."
             ::= { mstMapEntry 4 }

        	mstMapVlans4k      OBJECT-TYPE
            SYNTAX      OCTET STRING (SIZE (0..128))
            MAX-ACCESS  read-write
            STATUS      current
            DESCRIPTION
            "A string of octets containing one bit per VLAN for
             VLANS with VlanIndex values 3072 through 4095. The
             first octet corresponds to VLANs with VlanIndex values
             3072 through 3079; the second octet to VLANs 3080
             through 3087 etc.  The most significant bit of each
             octet corresponds to the lowest VlanIndex value in that
             octet.

             For each VLAN that is mapped to this MSTP instance,
             the bit corresponding to that VLAN is set to '1'.

             Empty (zero) most significant octes are not mandatory."
             ::= { mstMapEntry 5 }

        	mstMapRowStatus    OBJECT-TYPE
            SYNTAX  RowStatus
            MAX-ACCESS  read-create
            STATUS  current
            DESCRIPTION
            ""
        	::= {  mstMapEntry 6 }

-- MSTP Vlan Table, map vlan to msti
        	mstVlanTable       OBJECT-TYPE
            SYNTAX      SEQUENCE OF MstVlanEntry
            MAX-ACCESS  not-accessible
            STATUS      current
            DESCRIPTION
            "This table contains one entry for each VlanId."
            ::= { mstp 30 }

        	mstVlanEntry  OBJECT-TYPE
            SYNTAX      MstVlanEntry
            MAX-ACCESS      not-accessible
            STATUS      current
            DESCRIPTION
                "Information regarding the instance to which each Vlan is mapped."
            INDEX  { mstVlanIndex }
            ::= { mstVlanTable 1 }

        	MstVlanEntry ::= SEQUENCE {
              mstVlanIndex         INTEGER,
              mstVlanMstIndex      MstiOrCistInstanceIndex
        	}


        	mstVlanIndex     OBJECT-TYPE
            SYNTAX        INTEGER(1..4094)
            MAX-ACCESS        not-accessible
            STATUS        current
            DESCRIPTION
                "The VlanId for which this entry contains the instance mapped."
            ::= { mstVlanEntry 1 }

        	mstVlanMstIndex    OBJECT-TYPE
             SYNTAX      MstiOrCistInstanceIndex
             MAX-ACCESS  read-only
             STATUS      current
             DESCRIPTION
                 "An integer with values ranging from 0 to 64 that identify a
                      the CIST/MSTI instance to which this VLAN is mapped"
             ::= { mstVlanEntry 2 }
-- 		MSTP Port Table, information for all instance of a port
        	mstpPortTable      OBJECT-TYPE
            SYNTAX      SEQUENCE OF MstpPortEntry
            MAX-ACCESS  not-accessible
            STATUS      current
            DESCRIPTION
                "A table that contains generic information about
                every port that is associated with this bridge."
            ::= { mstp 40 }

       	 	mstpPortEntry      OBJECT-TYPE
            SYNTAX  MstpPortEntry
            MAX-ACCESS  not-accessible
            STATUS  current
            DESCRIPTION
            "A list of information for each port of the
            bridge."
            INDEX  { mstpPortIndex }
            ::= { mstpPortTable 1 }

        	MstpPortEntry ::= SEQUENCE {
             mstpPortIndex                    INTEGER,
             mstpPortOperEdgePort             TruthValue,
             mstpPortOperPointToPointMAC      TruthValue,
			 mstpPortAdminEdgePort            TruthValue
        	}

        	mstpPortIndex	OBJECT-TYPE
            SYNTAX    INTEGER (1..65535)
            MAX-ACCESS  not-accessible
            STATUS      current
            DESCRIPTION
            "A unique value, greater than zero, for each Port.
            The value for each interface sub-layer
            must remain constant at least from one re-initialization
            of the entity's network management system to the next re-
            initialization."
            ::= { mstpPortEntry 1 }

       		mstpPortOperEdgePort    OBJECT-TYPE
            SYNTAX    TruthValue
            MAX-ACCESS    read-only
            STATUS    current
            DESCRIPTION
            ""
            REFERENCE   ""
            ::= { mstpPortEntry 2 }

        	mstpPortOperPointToPointMAC    OBJECT-TYPE
            SYNTAX    TruthValue
            MAX-ACCESS    read-only
            STATUS    current
            DESCRIPTION
            ""
            REFERENCE    ""
            ::= {mstpPortEntry 3}

			mstpPortAdminEdgePort OBJECT-TYPE
            SYNTAX  INTEGER {
                      true(1),
                      false(2)
                   }
            MAX-ACCESS  read-write
            STATUS  current
            DESCRIPTION
                   "The administrative value of the Edge Port parameter.  A
					value of true(1) indicates that this port should be
         			assumed as an edge-port, and a value of false(2) indicates
         			that this port should be assumed as a non-edge-port. "
            REFERENCE
                    ""
            ::= { mstpPortEntry 4 }

-- 		MSTP Xst Table, Cist/Mst status/setting
        	mstpXstTable  OBJECT-TYPE
              SYNTAX      SEQUENCE OF MstpXstEntry
              MAX-ACCESS  not-accessible
              STATUS      current
              DESCRIPTION
                "."
              ::= { mstp 50 }

        	mstpXstEntry OBJECT-TYPE
              SYNTAX      MstpXstEntry
              MAX-ACCESS  not-accessible
              STATUS      current
              DESCRIPTION
                "."
              INDEX { mstpXstId }
              ::= { mstpXstTable 1 }

       		MstpXstEntry ::= SEQUENCE {
	           mstpXstId                      MstiOrCistInstanceIndex,
	           mstpXstBridgePriority          Integer32,
	           mstpXstBridgeId                BridgeId,
	           mstpXstInternalRootCost        Integer32,
	           mstpXstRootPort                INTEGER,
	           mstpXstTimeSinceTopologyChange TimeTicks,
	           mstpXstTopologyChangesCount    Counter32
       		}

       	mstpXstId   OBJECT-TYPE
           SYNTAX      MstiOrCistInstanceIndex
           MAX-ACCESS      read-only
           STATUS      current
           DESCRIPTION
             "0 means CIST."
           ::= { mstpXstEntry 1 }

       	mstpXstBridgePriority   OBJECT-TYPE
           SYNTAX      Integer32 (0..61440)
           MAX-ACCESS  read-write
           STATUS      current
           DESCRIPTION
              "Bridge priority, in steps of 4096."
           DEFVAL       { 32768 }
           ::= { mstpXstEntry 2 }

       mstpXstBridgeId   OBJECT-TYPE
           SYNTAX      BridgeId
           MAX-ACCESS      read-only
           STATUS      current
           DESCRIPTION
             "."
           ::= { mstpXstEntry 3 }


       mstpXstInternalRootCost     OBJECT-TYPE
           SYNTAX      Integer32
           MAX-ACCESS      read-only
           STATUS      current
           DESCRIPTION
             "."
           ::= { mstpXstEntry 4 }

       mstpXstRootPort      OBJECT-TYPE
           SYNTAX      INTEGER
           MAX-ACCESS      read-only
           STATUS      current
           DESCRIPTION
           "."
           ::= { mstpXstEntry 5 }

       mstpXstTimeSinceTopologyChange  OBJECT-TYPE
           SYNTAX      TimeTicks
           MAX-ACCESS      read-only
           STATUS      current
           DESCRIPTION
             "."
           ::= { mstpXstEntry 6 }

       mstpXstTopologyChangesCount     OBJECT-TYPE
           SYNTAX      Counter32
           MAX-ACCESS      read-only
           STATUS      current
           DESCRIPTION
             "."
           ::= { mstpXstEntry 7 }
-- MSTP Xst Port Table, Cist/Mst Port status/setting
       mstpXstPortTable    OBJECT-TYPE
           SYNTAX  SEQUENCE OF MstpXstPortEntry
           MAX-ACCESS  not-accessible
           STATUS  current
           DESCRIPTION
             "."
           ::= { mstp 60 }

       mstpXstPortEntry    OBJECT-TYPE
           SYNTAX  MstpXstPortEntry
           MAX-ACCESS  not-accessible
           STATUS  current
           DESCRIPTION
             "."
           REFERENCE
             "."
           INDEX  { mstpXstPortXstId, mstpXstPortIndex }
           ::= { mstpXstPortTable 1 }


        MstpXstPortEntry ::=
        SEQUENCE {
         	mstpXstPortXstId                 MstiOrCistInstanceIndex,
          	mstpXstPortIndex                 INTEGER,
          	mstpXstPortEnable                EnabledStatus,
          	mstpXstPortPriority              Integer32,
          	mstpXstPortPathCost              INTEGER,
          	mstpXstPortState				 INTEGER,
          	mstpXstPortDesignatedRoot        BridgeId,
          	mstpXstPortDesignatedCost        Integer32,
          	mstpXstPortDesignatedBridge      BridgeId,
          	mstpXstPortDesignatedPort        INTEGER
        }

        mstpXstPortXstId     OBJECT-TYPE
            SYNTAX      MstiOrCistInstanceIndex
            MAX-ACCESS      not-accessible
            STATUS      current
            DESCRIPTION
              "0 means CIST."
            ::= { mstpXstPortEntry 1 }

        mstpXstPortIndex     OBJECT-TYPE
            SYNTAX      INTEGER(1..65535)
            MAX-ACCESS      read-only
            STATUS      current
            DESCRIPTION
              "The value of mstpPortIndex of the Port
              in mstpPortTable."
            ::= { mstpXstPortEntry 2 }


        mstpXstPortEnable     OBJECT-TYPE
            SYNTAX      EnabledStatus
            MAX-ACCESS      read-write
            STATUS      current
            DESCRIPTION
              "."
            ::= { mstpXstPortEntry 3 }

         mstpXstPortPriority              OBJECT-TYPE
             SYNTAX      Integer32 (0..255)
             MAX-ACCESS      read-write
             STATUS      current
             DESCRIPTION
               "Port priority, in steps of 16."
             DEFVAL       { 128 }
             ::= { mstpXstPortEntry 4 }

         mstpXstPortPathCost              OBJECT-TYPE
             SYNTAX      INTEGER (1..65535)
             MAX-ACCESS      read-write
             STATUS      current
             DESCRIPTION
               "."
             ::= { mstpXstPortEntry 5 }

         mstpXstPortState                 OBJECT-TYPE
             SYNTAX      INTEGER {
               disabled(0),
               discarding(1),
               learning(2),
               forwarding(3),
               unknown(4)
             }
             MAX-ACCESS      read-only
             STATUS      current
             DESCRIPTION
               "."
             ::= { mstpXstPortEntry 6 }

         mstpXstPortDesignatedRoot        OBJECT-TYPE
              SYNTAX      BridgeId
              MAX-ACCESS      read-only
              STATUS      current
              DESCRIPTION
              "."
              ::= { mstpXstPortEntry 7 }

         mstpXstPortDesignatedCost        OBJECT-TYPE
             SYNTAX      Integer32
             MAX-ACCESS      read-only
             STATUS      current
             DESCRIPTION
             "."
             ::= { mstpXstPortEntry 8 }

         mstpXstPortDesignatedBridge      OBJECT-TYPE
             SYNTAX      BridgeId
             MAX-ACCESS      read-only
             STATUS      current
             DESCRIPTION
             "."
             ::= { mstpXstPortEntry 9 }

         mstpXstPortDesignatedPort      OBJECT-TYPE
             SYNTAX      INTEGER
             MAX-ACCESS      read-only
             STATUS      current
             DESCRIPTION
             "."
             ::= { mstpXstPortEntry 10 }

 --		MSTP Traps
 	     mstpNotifications     	OBJECT IDENTIFIER ::= { mstp 70 }

	     newRoot NOTIFICATION-TYPE
         OBJECTS {
                mstpXstId
         }
         STATUS  current
         DESCRIPTION
          ""
         ::= { mstpNotifications 1 }

         topologyChange NOTIFICATION-TYPE
         OBJECTS {
                mstpXstId
         }
         STATUS  current
         DESCRIPTION
          ""
         ::= { mstpNotifications 2 }

-- ******************************************************************
-- *
-- 108. radiusServerSetup
-- *
-- ******************************************************************

        radiusAuthServerSetup OBJECT IDENTIFIER ::= { radiusServerSetup 1 }

        radiusAuthServerMode OBJECT-TYPE
        SYNTAX  INTEGER{
        		indexPriority(1),
				roundRobin(2)
        }
        MAX-ACCESS  read-write
        STATUS  current
        DESCRIPTION
                      	""
        ::= { radiusAuthServerSetup 1 }

        radiusAuthServerTimeout OBJECT-TYPE
        SYNTAX  INTEGER
        MAX-ACCESS  read-write
        STATUS  current
        DESCRIPTION
                      	""
        ::= { radiusAuthServerSetup 2 }

-- 		radiusAuthServerTable
        radiusAuthServerTable OBJECT-TYPE
        SYNTAX	SEQUENCE OF RadiusAuthServerEntry
        MAX-ACCESS  not-accessible
        STATUS  current
        DESCRIPTION
                 	""
        ::= { radiusAuthServerSetup 3 }

		radiusAuthServerEntry OBJECT-TYPE
        SYNTAX	RadiusAuthServerEntry
        MAX-ACCESS	not-accessible
        STATUS	current
        DESCRIPTION    	"An entry in radiusAuthServerTable."
        INDEX          	{ radiusAuthServerIndex }
        ::= { radiusAuthServerTable 1 }

        RadiusAuthServerEntry ::=
           SEQUENCE {
        	radiusAuthServerIndex		INTEGER,
        	radiusAuthServerIpAddr		IpAddress,
        	radiusAuthServerUdpPort		INTEGER,
        	radiusAuthServerSharedSecret	DisplayString
           }

        radiusAuthServerIndex OBJECT-TYPE
        SYNTAX  INTEGER
        MAX-ACCESS  not-accessible
        STATUS  current
        DESCRIPTION
                      	""
        ::= { radiusAuthServerEntry 1 }

        radiusAuthServerIpAddr OBJECT-TYPE
        SYNTAX  IpAddress
        MAX-ACCESS  read-write
        STATUS  current
        DESCRIPTION
                     	""
        ::= { radiusAuthServerEntry 2 }

        radiusAuthServerUdpPort OBJECT-TYPE
        SYNTAX  INTEGER
        MAX-ACCESS  read-write
        STATUS  current
        DESCRIPTION
                     	""
        ::= { radiusAuthServerEntry 3 }

        radiusAuthServerSharedSecret OBJECT-TYPE
        SYNTAX  DisplayString
        MAX-ACCESS  read-write
        STATUS  current
        DESCRIPTION
                     	""
        ::= { radiusAuthServerEntry 4 }

        radiusAcctServerSetup OBJECT IDENTIFIER ::= { radiusServerSetup 2 }

        radiusAcctServerTimeout OBJECT-TYPE
        SYNTAX  INTEGER
        MAX-ACCESS  read-write
        STATUS  current
        DESCRIPTION
                      	""
        ::= { radiusAcctServerSetup 1 }

-- 		radiusAcctServerTable
        radiusAcctServerTable OBJECT-TYPE
        SYNTAX	SEQUENCE OF RadiusAcctServerEntry
        MAX-ACCESS  not-accessible
        STATUS  current
        DESCRIPTION
                 	""
        ::= { radiusAcctServerSetup 2 }

		radiusAcctServerEntry OBJECT-TYPE
        SYNTAX	RadiusAcctServerEntry
        MAX-ACCESS	not-accessible
        STATUS	current
        DESCRIPTION    	"An entry in radiusAcctServerTable."
        INDEX          	{ radiusAcctServerIndex }
        ::= { radiusAcctServerTable 1 }

        RadiusAcctServerEntry ::=
           SEQUENCE {
        	radiusAcctServerIndex		INTEGER,
        	radiusAcctServerIpAddr		IpAddress,
        	radiusAcctServerUdpPort		INTEGER,
        	radiusAcctServerSharedSecret	DisplayString
           }

        radiusAcctServerIndex OBJECT-TYPE
        SYNTAX  INTEGER
        MAX-ACCESS  not-accessible
        STATUS  current
        DESCRIPTION
                      	""
        ::= { radiusAcctServerEntry 1 }

        radiusAcctServerIpAddr OBJECT-TYPE
        SYNTAX  IpAddress
        MAX-ACCESS  read-write
        STATUS  current
        DESCRIPTION
                     	""
        ::= { radiusAcctServerEntry 2 }

        radiusAcctServerUdpPort OBJECT-TYPE
        SYNTAX  INTEGER
        MAX-ACCESS  read-write
        STATUS  current
        DESCRIPTION
                     	""
        ::= { radiusAcctServerEntry 3 }

        radiusAcctServerSharedSecret OBJECT-TYPE
        SYNTAX  DisplayString
        MAX-ACCESS  read-write
        STATUS  current
        DESCRIPTION
                     	""
        ::= { radiusAcctServerEntry 4 }

-- ******************************************************************
-- *
-- 109. tacacsServerSetup
-- *
-- ******************************************************************
        tacacsAuthServerSetup OBJECT IDENTIFIER ::= { tacacsServerSetup 1 }

        tacacsAuthServerMode OBJECT-TYPE
        SYNTAX  INTEGER{
        		indexPriority(1),
				roundRobin(2)
        }
        MAX-ACCESS  read-write
        STATUS  current
        DESCRIPTION
                      	""
        ::= { tacacsAuthServerSetup 1 }

        tacacsAuthServerTimeout OBJECT-TYPE
        SYNTAX  INTEGER
        MAX-ACCESS  read-write
        STATUS  current
        DESCRIPTION
                      	""
        ::= { tacacsAuthServerSetup 2 }

-- 		tacacsAuthServerTable
        tacacsAuthServerTable OBJECT-TYPE
        SYNTAX	SEQUENCE OF TacacsAuthServerEntry
        MAX-ACCESS  not-accessible
        STATUS  current
        DESCRIPTION
                 	""
        ::= { tacacsAuthServerSetup 3 }

		tacacsAuthServerEntry OBJECT-TYPE
        SYNTAX	TacacsAuthServerEntry
        MAX-ACCESS	not-accessible
        STATUS	current
        DESCRIPTION    	"An entry in tacacsAuthServerTable."
        INDEX          	{ tacacsAuthServerIndex }
        ::= { tacacsAuthServerTable 1 }

        TacacsAuthServerEntry ::=
           SEQUENCE {
        	tacacsAuthServerIndex		INTEGER,
        	tacacsAuthServerIpAddr		IpAddress,
        	tacacsAuthServerTcpPort		INTEGER,
        	tacacsAuthServerSharedSecret	DisplayString
           }

        tacacsAuthServerIndex OBJECT-TYPE
        SYNTAX  INTEGER
        MAX-ACCESS  not-accessible
        STATUS  current
        DESCRIPTION
                      	""
        ::= { tacacsAuthServerEntry 1 }

        tacacsAuthServerIpAddr OBJECT-TYPE
        SYNTAX  IpAddress
        MAX-ACCESS  read-write
        STATUS  current
        DESCRIPTION
                     	""
        ::= { tacacsAuthServerEntry 2 }

        tacacsAuthServerTcpPort OBJECT-TYPE
        SYNTAX  INTEGER
        MAX-ACCESS  read-write
        STATUS  current
        DESCRIPTION
                     	""
        ::= { tacacsAuthServerEntry 3 }

        tacacsAuthServerSharedSecret OBJECT-TYPE
        SYNTAX  DisplayString
        MAX-ACCESS  read-write
        STATUS  current
        DESCRIPTION
                     	""
        ::= { tacacsAuthServerEntry 4 }

        tacacsAcctServerSetup OBJECT IDENTIFIER ::= { tacacsServerSetup 2 }

        tacacsAcctServerTimeout OBJECT-TYPE
        SYNTAX  INTEGER
        MAX-ACCESS  read-write
        STATUS  current
        DESCRIPTION
                      	""
        ::= { tacacsAcctServerSetup 1 }

-- 		tacacsAcctServerTable
        tacacsAcctServerTable OBJECT-TYPE
        SYNTAX	SEQUENCE OF TacacsAcctServerEntry
        MAX-ACCESS  not-accessible
        STATUS  current
        DESCRIPTION
                 	""
        ::= { tacacsAcctServerSetup 2 }

		tacacsAcctServerEntry OBJECT-TYPE
        SYNTAX	TacacsAcctServerEntry
        MAX-ACCESS	not-accessible
        STATUS	current
        DESCRIPTION    	"An entry in tacacsAcctServerTable."
        INDEX          	{ tacacsAcctServerIndex }
        ::= { tacacsAcctServerTable 1 }

        TacacsAcctServerEntry ::=
           SEQUENCE {
        	tacacsAcctServerIndex		INTEGER,
        	tacacsAcctServerIpAddr		IpAddress,
        	tacacsAcctServerTcpPort		INTEGER,
        	tacacsAcctServerSharedSecret	DisplayString
           }

        tacacsAcctServerIndex OBJECT-TYPE
        SYNTAX  INTEGER
        MAX-ACCESS  not-accessible
        STATUS  current
        DESCRIPTION
                      	""
        ::= { tacacsAcctServerEntry 1 }

        tacacsAcctServerIpAddr OBJECT-TYPE
        SYNTAX  IpAddress
        MAX-ACCESS  read-write
        STATUS  current
        DESCRIPTION
                     	""
        ::= { tacacsAcctServerEntry 2 }

        tacacsAcctServerTcpPort OBJECT-TYPE
        SYNTAX  INTEGER
        MAX-ACCESS  read-write
        STATUS  current
        DESCRIPTION
                     	""
        ::= { tacacsAcctServerEntry 3 }

        tacacsAcctServerSharedSecret OBJECT-TYPE
        SYNTAX  DisplayString
        MAX-ACCESS  read-write
        STATUS  current
        DESCRIPTION
                     	""
        ::= { tacacsAcctServerEntry 4 }

-- ******************************************************************
-- *
-- 110. aaaSetup
-- *
-- ******************************************************************
    authenticationSetup OBJECT IDENTIFIER ::= { aaaSetup 1 }

-- 		authenticationTypeTable
        authenticationTypeTable OBJECT-TYPE
        SYNTAX	SEQUENCE OF AuthenticationTypeEntry
        MAX-ACCESS  not-accessible
        STATUS  current
        DESCRIPTION
                 	""
        ::= { authenticationSetup 1 }

		authenticationTypeEntry OBJECT-TYPE
        SYNTAX	AuthenticationTypeEntry
        MAX-ACCESS	not-accessible
        STATUS	current
        DESCRIPTION    	"An entry in authenticationTypeTable."
        INDEX          	{ authenticationTypeName }
        ::= { authenticationTypeTable 1 }

        AuthenticationTypeEntry ::=
           SEQUENCE {
        	authenticationTypeName	DisplayString,
        	authenticationTypeMethodList	OCTET STRING,
        	authenticationTypeTryCont	EnabledStatus
           }

        authenticationTypeName OBJECT-TYPE
        SYNTAX  DisplayString
        MAX-ACCESS  read-only
        STATUS  current
        DESCRIPTION
                      	""
        ::= { authenticationTypeEntry 1 }

        authenticationTypeMethodList OBJECT-TYPE
        SYNTAX  OCTET STRING
        MAX-ACCESS  read-write
        STATUS  current
        DESCRIPTION
                     	"0:none, 1:enable, 2:local, 3:radius, tacacs+"
        ::= { authenticationTypeEntry 2 }

		authenticationTypeTryCont OBJECT-TYPE
		SYNTAX  EnabledStatus
		MAX-ACCESS  read-write
		STATUS  current
		DESCRIPTION
              	        	"Try continue next method"
		::= { authenticationTypeEntry 3 }

  	accountingSetup      	OBJECT IDENTIFIER ::= { aaaSetup 2 }
		accountingUpdatePeriod OBJECT-TYPE
		SYNTAX  Integer32
		MAX-ACCESS  read-write
		STATUS  current
		DESCRIPTION
                      	""
		::= { accountingSetup 1 }

-- 		accountingTypeTable
        accountingTypeTable OBJECT-TYPE
        SYNTAX	SEQUENCE OF AccountingTypeEntry
        MAX-ACCESS  not-accessible
        STATUS  current
        DESCRIPTION
                 	""
        ::= { accountingSetup 2 }

		accountingTypeEntry OBJECT-TYPE
        SYNTAX	AccountingTypeEntry
        MAX-ACCESS	not-accessible
        STATUS	current
        DESCRIPTION    	"An entry in accountingTypeTable."
        INDEX          	{ accountingTypeName }
        ::= { accountingTypeTable 1 }

        AccountingTypeEntry ::=
        SEQUENCE {
         	accountingTypeName		DisplayString,
        	accountingTypeActive		EnabledStatus,
         	accountingTypeBroadcast		EnabledStatus,
         	accountingTypeMode		INTEGER,
         	accountingTypeMethod		INTEGER,
         	accountingTypePrivilege		INTEGER
        }

		accountingTypeName OBJECT-TYPE
		SYNTAX  DisplayString
		MAX-ACCESS  read-only
		STATUS  current
		DESCRIPTION
                      			""
		::= { accountingTypeEntry 1 }

		accountingTypeActive OBJECT-TYPE
		SYNTAX  EnabledStatus
		MAX-ACCESS  read-write
		STATUS  current
		DESCRIPTION
                      			""
		::= { accountingTypeEntry 2 }

		accountingTypeBroadcast OBJECT-TYPE
		SYNTAX  EnabledStatus
		MAX-ACCESS  read-write
		STATUS  current
		DESCRIPTION
           		          	""
		::= { accountingTypeEntry 3 }

		accountingTypeMode OBJECT-TYPE
		SYNTAX  INTEGER{
			notAvailable(255),
     	startStop(1),
			stopOnly(2)
		}
		MAX-ACCESS  read-write
		STATUS  current
		DESCRIPTION
       		              	""
		::= { accountingTypeEntry 4 }

		accountingTypeMethod OBJECT-TYPE
		SYNTAX  INTEGER{
     	radius(1),
			tacacs(2)
		}
		MAX-ACCESS  read-write
		STATUS  current
		DESCRIPTION
              	        	""
		::= { accountingTypeEntry 5 }

		accountingTypePrivilege OBJECT-TYPE
		SYNTAX  INTEGER{
			notAvailable(255),
			privilege0(0),
			privilege1(1),
			privilege2(2),
			privilege3(3),
			privilege4(4),
			privilege5(5),
			privilege6(6),
			privilege7(7),
			privilege8(8),
			privilege9(9),
			privilege10(10),
			privilege11(11),
			privilege12(12),
			privilege13(13),
			privilege14(14)
		}
		MAX-ACCESS  read-write
		STATUS  current
		DESCRIPTION
             	       	""
		::= { accountingTypeEntry 6 }

		authorizationSetup      	OBJECT IDENTIFIER ::= { aaaSetup 3 }

-- 		authorizationTypeTable
		authorizationTypeTable OBJECT-TYPE
        SYNTAX	SEQUENCE OF AuthorizationTypeEntry
        MAX-ACCESS  not-accessible
        STATUS  current
        DESCRIPTION
                 	""
        ::= { authorizationSetup 1 }

   		authorizationTypeEntry OBJECT-TYPE
        SYNTAX	AuthorizationTypeEntry
        MAX-ACCESS	not-accessible
        STATUS	current
        DESCRIPTION    	"An entry in authorizationTypeTable."
        INDEX          	{ authorizationTypeName }
        ::= { authorizationTypeTable 1 }

        AuthorizationTypeEntry ::=
           SEQUENCE {
         	authorizationTypeName		DisplayString,
         	authorizationTypeActive		EnabledStatus,
         	authorizationTypeMethod		INTEGER
           }

		authorizationTypeName OBJECT-TYPE
		SYNTAX  DisplayString
		MAX-ACCESS  read-only
		STATUS  current
		DESCRIPTION
                      	""
		::= { authorizationTypeEntry 1 }

		authorizationTypeActive OBJECT-TYPE
		SYNTAX  EnabledStatus
		MAX-ACCESS  read-write
		STATUS  current
		DESCRIPTION
                      	""
		::= { authorizationTypeEntry 2 }

		authorizationTypeMethod OBJECT-TYPE
		SYNTAX  INTEGER{
   	 	radius(1),
			tacacs(2)
		}
		MAX-ACCESS  read-write
		STATUS  current
		DESCRIPTION
                      	""
		::= { authorizationTypeEntry 3 }

-- ******************************************************************
-- *
-- 112. Port Isolation
-- *
-- ******************************************************************
-- portIsolationTable
--
--        portIsolationTable OBJECT-TYPE
--        SYNTAX	SEQUENCE OF PortIsolationEntry
--        MAX-ACCESS  not-accessible
--        STATUS  current
--        DESCRIPTION
--                 	""
--        ::= { portIsolationSetup 1 }
--
--		portIsolationEntry OBJECT-TYPE
--        SYNTAX	PortIsolationEntry
--        MAX-ACCESS	not-accessible
--        STATUS	current
--        DESCRIPTION    	"An entry in portIsolationTable."
--        INDEX          	{ dot1dBasePort }
--        ::= { portIsolationTable 1 }
--
--        PortIsolationEntry ::=
--           SEQUENCE {
--        	portIsolationState		EnabledStatus
--           }
--
--        portIsolationState OBJECT-TYPE
--        SYNTAX  EnabledStatus
--        MAX-ACCESS  read-write
--        STATUS  current
--        DESCRIPTION
--                      	"Port isolation enabled/disabled on the port.
--                      	Enable(1) to be isolated and not exchange packets."
--        ::= { portIsolationEntry 1 }
--
--
-- ******************************************************************
-- *
-- 115. Layer 2 Protocol Tunneling
-- *
-- ******************************************************************
--
--  l2ptState
--        l2ptState OBJECT-TYPE
--        SYNTAX  EnabledStatus
--        MAX-ACCESS  read-write
--        STATUS  current
--        DESCRIPTION
--                       "L2PT feature enabled/disabled for the switch"
--        ::= { l2ptSetup 1 }
--
--        l2ptMacAddr OBJECT-TYPE
--        SYNTAX  MacAddress
--        MAX-ACCESS  read-write
--        STATUS  current
--        DESCRIPTION
--                       "L2PT destination mac address"
--        ::= { l2ptSetup 2 }
--
-- 		l2ptTable
--
--        l2ptTable OBJECT-TYPE
--        SYNTAX SEQUENCE OF L2ptEntry
--        MAX-ACCESS  not-accessible
--        STATUS  current
--        DESCRIPTION
--                  ""
--        ::= { l2ptSetup 3 }
--
-- 		l2ptEntry OBJECT-TYPE
--        SYNTAX L2ptEntry
--        MAX-ACCESS not-accessible
--        STATUS current
--        DESCRIPTION     "An entry in l2ptTable."
--        INDEX           { dot1dBasePort }
--        ::= { l2ptTable 1 }
--
--        L2ptEntry ::=
--           SEQUENCE {
--         l2ptProtocolGroup  BITS,
--         l2ptPointToPointProtocolGroup BITS,
--         l2ptMode   INTEGER
--           }
--
--     	l2ptProtocolGroup OBJECT-TYPE
--        SYNTAX BITS {
--		  cdp(0),
--		  stp(1),
--		  vtp(2)
--		 }
--        MAX-ACCESS  read-write
--        STATUS  current
--        DESCRIPTION
--                       "L2PT protocols enabled/disabled on the port"
--        ::= { l2ptEntry 1 }
--
--     	l2ptPointToPointProtocolGroup OBJECT-TYPE
--        SYNTAX BITS {
--		  pagp(0),
--		  lacp(1),
--		  udld(2)
--		 }
--        MAX-ACCESS  read-write
--        STATUS  current
--        DESCRIPTION
--                       "L2PT point-to-point protocols enabled/disabled on the port"
--        ::= { l2ptEntry 2 }
--
--        l2ptMode OBJECT-TYPE
--        SYNTAX  INTEGER {
--         access(1),
--         tunnel(2)
--        }
--        MAX-ACCESS  read-write
--        STATUS  current
--        DESCRIPTION
--                       "L2PT port role on the port"
--        ::= { l2ptEntry 3 }
--

-- ******************************************************************
-- *
-- 116. vlan translation
-- *
-- ******************************************************************

-- 		vlanTranslationRuleTable
        vlanTranslationRuleTable OBJECT-TYPE
        SYNTAX	SEQUENCE OF VlanTranslationRuleEntry
        MAX-ACCESS  not-accessible
        STATUS  current
        DESCRIPTION
                 	""
        ::= { vlanTranslationSetup 1 }

		vlanTranslationRuleEntry OBJECT-TYPE
        SYNTAX	VlanTranslationRuleEntry
        MAX-ACCESS	not-accessible
        STATUS	current
        DESCRIPTION    	"An entry in vlan-translation rule table"
        INDEX          	{ vlanTranslationRulePort, vlanTranslationRuleOuterVid, vlanTranslationRuleOuterPriority, vlanTranslationRuleInnerVid, vlanTranslationRuleInnerPriority }
        ::= { vlanTranslationRuleTable 1 }

        VlanTranslationRuleEntry ::=
           SEQUENCE {
           	vlanTranslationRuleName		DisplayString,
        	vlanTranslationRulePort		INTEGER,
        	vlanTranslationRuleOuterVid		INTEGER,
        	vlanTranslationRuleOuterPriority	INTEGER,
        	vlanTranslationRuleInnerVid		INTEGER,
        	vlanTranslationRuleInnerPriority	INTEGER,
        	vlanTranslationRuleTransSVid	INTEGER,
        	vlanTranslationRuleSPriority	INTEGER,
        	vlanTranslationRuleTransCVid	INTEGER,
        	vlanTranslationRuleCPriority	INTEGER,
        	vlanTranslationRuleN1Map	INTEGER,
        	vlanTranslationRuleCrossConnect	INTEGER,
        	vlanTranslationRuleCrossPort	INTEGER,
        	vlanTranslationRuleTr156	INTEGER,
        	vlanTranslationRuleRowStatus	RowStatus
           }

        vlanTranslationRuleName OBJECT-TYPE
        SYNTAX  DisplayString
        MAX-ACCESS  read-write
        STATUS  current
        DESCRIPTION
                      	"The name of vlan-translation entry"
        ::= { vlanTranslationRuleEntry 1 }

        vlanTranslationRulePort OBJECT-TYPE
        SYNTAX  INTEGER
        MAX-ACCESS  read-only
        STATUS  current
        DESCRIPTION
                     	"interface port id"
        ::= { vlanTranslationRuleEntry 2 }

        vlanTranslationRuleOuterVid OBJECT-TYPE
        SYNTAX  INTEGER
        MAX-ACCESS  read-only
        STATUS  current
        DESCRIPTION
                     	"outer vid. The range of VID is between 1 and 4094. 0 presents ignore this field"
        ::= { vlanTranslationRuleEntry 3 }

        vlanTranslationRuleOuterPriority OBJECT-TYPE
        SYNTAX  INTEGER {
        		priority0(0),
        		priority1(1),
        		priority2(2),
        		priority3(3),
        		priority4(4),
        		priority5(5),
        		priority6(6),
        		priority7(7),
        		priorityIgnore(8)
        }
        MAX-ACCESS  read-only
        STATUS  current
        DESCRIPTION
                     	"outer priority"
        ::= { vlanTranslationRuleEntry 4 }

        vlanTranslationRuleInnerVid OBJECT-TYPE
        SYNTAX  INTEGER
        MAX-ACCESS  read-only
        STATUS  current
        DESCRIPTION
                     	"inner vid. The range of VID is between 1 and 4094. 0 presents ignore this field"
        ::= { vlanTranslationRuleEntry 5 }

        vlanTranslationRuleInnerPriority OBJECT-TYPE
        SYNTAX  INTEGER {
        		priority0(0),
        		priority1(1),
        		priority2(2),
        		priority3(3),
        		priority4(4),
        		priority5(5),
        		priority6(6),
        		priority7(7),
        		priorityIgnore(8)
        }
        MAX-ACCESS  read-only
        STATUS  current
        DESCRIPTION
                     	"inner priority"
        ::= { vlanTranslationRuleEntry 6 }

        vlanTranslationRuleTransSVid OBJECT-TYPE
        SYNTAX  INTEGER
        MAX-ACCESS  read-write
        STATUS  current
        DESCRIPTION
                     	"translated Svid. The range of VID is between 1 and 4094. 0 presents ignore this field"
        ::= { vlanTranslationRuleEntry 7 }

        vlanTranslationRuleSPriority OBJECT-TYPE
        SYNTAX  INTEGER {
        		priority0(0),
        		priority1(1),
        		priority2(2),
        		priority3(3),
        		priority4(4),
        		priority5(5),
        		priority6(6),
        		priority7(7),
        		priorityIgnore(8)
        }

        MAX-ACCESS  read-write
        STATUS  current
        DESCRIPTION
                     	"S priority"
        ::= { vlanTranslationRuleEntry 8 }

        vlanTranslationRuleTransCVid OBJECT-TYPE
        SYNTAX  INTEGER
        MAX-ACCESS  read-write
        STATUS  current
        DESCRIPTION
                     	"translated Cvid. The range of VID is between 1 and 4094. 0 presents ignore this field"
        ::= { vlanTranslationRuleEntry 9 }

        vlanTranslationRuleCPriority OBJECT-TYPE
        SYNTAX  INTEGER {
        		priority0(0),
        		priority1(1),
        		priority2(2),
        		priority3(3),
        		priority4(4),
        		priority5(5),
        		priority6(6),
        		priority7(7),
        		priorityIgnore(8)
        }

        MAX-ACCESS  read-write
        STATUS  current
        DESCRIPTION
                     	"C priority"
        ::= { vlanTranslationRuleEntry 10 }

        vlanTranslationRuleN1Map OBJECT-TYPE
        SYNTAX  INTEGER
        MAX-ACCESS  read-write
        STATUS  current
        DESCRIPTION
                     	"N:1 mapping group id. 0 presents 1:1 map"
        ::= { vlanTranslationRuleEntry 11 }

        vlanTranslationRuleCrossConnect OBJECT-TYPE
        SYNTAX  INTEGER {
        		enabled(1),
        		disabled(2)
        }
        MAX-ACCESS  read-write
        STATUS  current
        DESCRIPTION
                     	"cross-connect"
        ::= { vlanTranslationRuleEntry 12 }

        vlanTranslationRuleCrossPort OBJECT-TYPE
        SYNTAX  INTEGER
        MAX-ACCESS  read-write
        STATUS  current
        DESCRIPTION
                     	"cross-connect port id"
        ::= { vlanTranslationRuleEntry 13 }

        vlanTranslationRuleTr156 OBJECT-TYPE
        SYNTAX  INTEGER {
        		enabled(1),
        		disabled(2)
        }
        MAX-ACCESS  read-write
        STATUS  current
        DESCRIPTION
                     	"tr156"
        ::= { vlanTranslationRuleEntry 14 }

        vlanTranslationRuleRowStatus OBJECT-TYPE
        SYNTAX  RowStatus
        MAX-ACCESS  read-create
        STATUS  current
        DESCRIPTION
                     	""
        ::= { vlanTranslationRuleEntry 15 }

-- ******************************************************************
-- *
-- 117. transceiverInfoTable
-- *
-- ******************************************************************

-- 		transceiverSerialInfoTable

        transceiverSerialInfoTable	OBJECT-TYPE
        SYNTAX	SEQUENCE OF TransceiverSerialInfoEntry
        MAX-ACCESS  not-accessible
        STATUS  current
        DESCRIPTION
                 	""
        ::= { transceiverInfo 1 }

		transceiverSerialInfoEntry OBJECT-TYPE
        SYNTAX	TransceiverSerialInfoEntry
        MAX-ACCESS	not-accessible
        STATUS	current
        DESCRIPTION    	"An entry in transceiverSerialInfoTable."
        INDEX          	{ transceiverSerialInfoEntryPort }
        ::= { transceiverSerialInfoTable 1 }

        TransceiverSerialInfoEntry ::=
           SEQUENCE {
        	transceiverSerialInfoEntryPort			INTEGER,
        	transceiverSerialInfoEntryStatus		INTEGER,
        	transceiverSerialInfoEntryVendor		DisplayString,
        	transceiverSerialInfoEntryPartNo		DisplayString,
        	transceiverSerialInfoEntrySerialNo		DisplayString,
        	transceiverSerialInfoEntryRevision		DisplayString,
        	transceiverSerialInfoEntryDateCode		DisplayString,
        	transceiverSerialInfoEntryTransceiver	DisplayString
           }

        transceiverSerialInfoEntryPort OBJECT-TYPE
        SYNTAX  INTEGER
        MAX-ACCESS  read-only
        STATUS  current
        DESCRIPTION
                      	"Index of transceiverSerialInfo. It is referred to dot1dBasePort"
        ::= { transceiverSerialInfoEntry 1 }

        transceiverSerialInfoEntryStatus OBJECT-TYPE
        SYNTAX  INTEGER {
        		okWithDdm(1),
        		okWithoutDdm(2),
        		nonOperational(3)
        }
        MAX-ACCESS  read-only
        STATUS  current
        DESCRIPTION
                      	"Transceiver module status. 1:okWithDdm. 2:okWithoutDdm. 3:nonOperational"
        ::= { transceiverSerialInfoEntry 2 }


        transceiverSerialInfoEntryVendor OBJECT-TYPE
        SYNTAX  DisplayString
        MAX-ACCESS  read-only
        STATUS  current
        DESCRIPTION
                      	"Transceiver module vendor name."
        ::= { transceiverSerialInfoEntry 3 }

        transceiverSerialInfoEntryPartNo OBJECT-TYPE
        SYNTAX  DisplayString
        MAX-ACCESS  read-only
        STATUS  current
        DESCRIPTION
                      	"Part number provided by transceiver module vendor."
        ::= { transceiverSerialInfoEntry 4 }

        transceiverSerialInfoEntrySerialNo OBJECT-TYPE
        SYNTAX  DisplayString
        MAX-ACCESS  read-only
        STATUS  current
        DESCRIPTION
                      	"Serial number provided by transceiver module vendor."
        ::= { transceiverSerialInfoEntry 5 }

        transceiverSerialInfoEntryRevision OBJECT-TYPE
        SYNTAX  DisplayString
        MAX-ACCESS  read-only
        STATUS  current
        DESCRIPTION
                      	"Revision level for part number provided by transceiver module vendor."
        ::= { transceiverSerialInfoEntry 6 }

        transceiverSerialInfoEntryDateCode OBJECT-TYPE
        SYNTAX  DisplayString
        MAX-ACCESS  read-only
        STATUS  current
        DESCRIPTION
                      	"Transceiver module vendor's manufacturing date code"
        ::= { transceiverSerialInfoEntry 7 }

        transceiverSerialInfoEntryTransceiver OBJECT-TYPE
        SYNTAX  DisplayString
        MAX-ACCESS  read-only
        STATUS  current
        DESCRIPTION
                      	"Transceiver module type names"
        ::= { transceiverSerialInfoEntry 8 }

-- 		transceiverDdmInfoTable

        transceiverDdmInfoTable	OBJECT-TYPE
        SYNTAX	SEQUENCE OF TransceiverDdmInfoEntry
        MAX-ACCESS  not-accessible
        STATUS  current
        DESCRIPTION
                 	""
        ::= { transceiverInfo 2 }

		transceiverDdmInfoEntry OBJECT-TYPE
        SYNTAX	TransceiverDdmInfoEntry
        MAX-ACCESS	not-accessible
        STATUS	current
        DESCRIPTION    	"An entry in transceiverDdmInfoTable."
        INDEX          	{ transceiverDdmInfoEntryPort, transceiverDdmInfoEntryType }
        ::= { transceiverDdmInfoTable 1 }

        TransceiverDdmInfoEntry ::=
           SEQUENCE {
        	transceiverDdmInfoEntryPort			INTEGER,
        	transceiverDdmInfoEntryType			INTEGER,
        	transceiverDdmInfoEntryAlarmMax		DisplayString,
        	transceiverDdmInfoEntryAlarmMin		DisplayString,
        	transceiverDdmInfoEntryWarnMax		DisplayString,
        	transceiverDdmInfoEntryWarnMin		DisplayString,
        	transceiverDdmInfoEntryCurrent		DisplayString,
        	transceiverDdmInfoEntryDescription	DisplayString
           }

        transceiverDdmInfoEntryPort OBJECT-TYPE
        SYNTAX  INTEGER
        MAX-ACCESS  read-only
        STATUS  current
        DESCRIPTION
                      	"Index of transceiverDdmInfo. This will be referred to dot1dBasePort"
        ::= { transceiverDdmInfoEntry 1 }

        transceiverDdmInfoEntryType OBJECT-TYPE
        SYNTAX  INTEGER
        MAX-ACCESS  read-only
        STATUS  current
        DESCRIPTION
                      	"Transceiver DDM information type.
						 1: Temperature
						 2: Voltage
						 3: TX Bias
						 4: TX power
						 5: RX power"
        ::= { transceiverDdmInfoEntry 2 }


        transceiverDdmInfoEntryAlarmMax OBJECT-TYPE
        SYNTAX  DisplayString
        MAX-ACCESS  read-only
        STATUS  current
        DESCRIPTION
                      	"Transceiver high alarm threshold.
						 The unit for temperature is 0.01C
						 The unit for voltage is 0.01V
						 The unit for TX bias is 0.01mA
						 The unit for TX/RX power is 0.01dbm
						 The value neg inf represents negative infinit(0mW)
						 The value N/A represents not applicable."
        ::= { transceiverDdmInfoEntry 3 }

        transceiverDdmInfoEntryAlarmMin OBJECT-TYPE
        SYNTAX  DisplayString
        MAX-ACCESS  read-only
        STATUS  current
        DESCRIPTION
                      	"Transceiver low alarm threshold.
						 The unit for temperature is 0.01C
						 The unit for voltage is 0.01V
						 The unit for TX bias is 0.01mA
						 The unit for TX/RX power is 0.01dbm
						 The value neg inf represents negative infinit(0mW)
						 The value N/A represents not applicable."
        ::= { transceiverDdmInfoEntry 4 }

        transceiverDdmInfoEntryWarnMax OBJECT-TYPE
        SYNTAX  DisplayString
        MAX-ACCESS  read-only
        STATUS  current
        DESCRIPTION
                      	"Transceiver high warn threshold.
						 The unit for temperature is 0.01C
						 The unit for voltage is 0.01V
						 The unit for TX bias is 0.01mA
						 The unit for TX/RX power is 0.01dbm
						 The value neg inf represents negative infinit(0mW)
						 The value N/A represents not applicable."
        ::= { transceiverDdmInfoEntry 5 }

        transceiverDdmInfoEntryWarnMin OBJECT-TYPE
        SYNTAX  DisplayString
        MAX-ACCESS  read-only
        STATUS  current
        DESCRIPTION
                      	"Transceiver low warn threshold.
						 The unit for temperature is 0.01C
						 The unit for voltage is 0.01V
						 The unit for TX bias is 0.01mA
						 The unit for TX/RX power is 0.01dbm
						 The value neg inf represents negative infinit(0mW)
						 The value N/A represents not applicable."
        ::= { transceiverDdmInfoEntry 6 }

        transceiverDdmInfoEntryCurrent OBJECT-TYPE
        SYNTAX  DisplayString
        MAX-ACCESS  read-only
        STATUS  current
        DESCRIPTION
                      	"Transceiver current DDM value.
						 The unit for temperature is 0.01C
						 The unit for voltage is 0.01V
						 The unit for TX bias is 0.01mA
						 The unit for TX/RX power is 0.01dbm
						 The value neg inf represents negative infinit(0mW)
						 The value N/A represents not applicable."
        ::= { transceiverDdmInfoEntry 7 }

        transceiverDdmInfoEntryDescription OBJECT-TYPE
        SYNTAX  DisplayString
        MAX-ACCESS  read-only
        STATUS  current
        DESCRIPTION
                      	"Transceiver DDM information description. Show N/A if transceiver DDM information is not available."
        ::= { transceiverDdmInfoEntry 8 }

-- 		transceiverDdmInfoProfileTable

        transceiverDdmInfoProfileTable	OBJECT-TYPE
        SYNTAX	SEQUENCE OF TransceiverDdmInfoProfileEntry
        MAX-ACCESS  not-accessible
        STATUS  current
        DESCRIPTION
                 	""
        ::= { transceiverInfo 3 }

		transceiverDdmInfoProfileEntry OBJECT-TYPE
        SYNTAX	TransceiverDdmInfoProfileEntry
        MAX-ACCESS	not-accessible
        STATUS	current
        DESCRIPTION    	"An entry in transceiverDdmInfoProfileTable."
        INDEX          	{ transceiverDdmInfoProfilePort, transceiverDdmInfoProfileType }
        ::= { transceiverDdmInfoProfileTable 1 }

        TransceiverDdmInfoProfileEntry ::=
           SEQUENCE {
        	transceiverDdmInfoProfilePort			INTEGER,
        	transceiverDdmInfoProfileType			INTEGER,
        	transceiverDdmInfoProfileAlarmMax		DisplayString,
        	transceiverDdmInfoProfileAlarmMin		DisplayString,
        	transceiverDdmInfoProfileWarnMax		DisplayString,
        	transceiverDdmInfoProfileWarnMin		DisplayString,
        	transceiverDdmInfoProfileDescription	DisplayString,
        	transceiverDdmInfoProfileRowstatus	RowStatus,
        	timeSlot INTEGER
           }

        transceiverDdmInfoProfilePort OBJECT-TYPE
        SYNTAX  INTEGER
        MAX-ACCESS  read-only
        STATUS  current
        DESCRIPTION
                      	"Index of transceiverDdmInfoProfile. This will be referred to dot1dBasePort"
        ::= { transceiverDdmInfoProfileEntry 1 }

        transceiverDdmInfoProfileType OBJECT-TYPE
        SYNTAX  INTEGER
        MAX-ACCESS  read-only
        STATUS  current
        DESCRIPTION
                      	"Transceiver DDM information type.
						 1: Temperature
						 2: Voltage
						 3: TX Bias
						 4: TX power
						 5: RX power"
        ::= { transceiverDdmInfoProfileEntry 2 }


        transceiverDdmInfoProfileAlarmMax OBJECT-TYPE
        SYNTAX  DisplayString
        MAX-ACCESS  read-write
        STATUS  current
        DESCRIPTION
                       "Transceiver high alarm threshold.
						 The unit for temperature is 0.01C, value range <12800 ~ -12800>
						 The unit for voltage is 0.01V, value range <655 ~ 0>
						 The unit for TX bias is 0.01mA, value range <13100 ~ 0>
						 The unit for TX power is 0.01dbm, value range <820 ~ -4000>
						 The unit for RX power is 0.01dbm, value range <820 ~ -4000>
						 The value N/A represents transceiver DDM information does not setting."
        ::= { transceiverDdmInfoProfileEntry 3 }

        transceiverDdmInfoProfileAlarmMin OBJECT-TYPE
        SYNTAX  DisplayString
        MAX-ACCESS  read-write
        STATUS  current
        DESCRIPTION
                      	"Transceiver low alarm threshold.
						 The unit for temperature is 0.01C, value range <12800 ~ -12800>
						 The unit for voltage is 0.01V, value range <655 ~ 0>
						 The unit for TX bias is 0.01mA, value range <13100 ~ 0>
						 The unit for TX power is 0.01dbm, value range <820 ~ -4000>
						 The unit for RX power is 0.01dbm, value range <820 ~ -4000>
						 The value N/A represents transceiver DDM information does not setting."
        ::= { transceiverDdmInfoProfileEntry 4 }

        transceiverDdmInfoProfileWarnMax OBJECT-TYPE
        SYNTAX  DisplayString
        MAX-ACCESS  read-write
        STATUS  current
        DESCRIPTION
                      	"Transceiver high warn threshold.
						 The unit for temperature is 0.01C, value range <12800 ~ -12800>
						 The unit for voltage is 0.01V, value range <655 ~ 0>
						 The unit for TX bias is 0.01mA, value range <13100 ~ 0>
						 The unit for TX power is 0.01dbm, value range <820 ~ -4000>
						 The unit for RX power is 0.01dbm, value range <820 ~ -4000>
						 The value N/A represents transceiver DDM information does not setting."
        ::= { transceiverDdmInfoProfileEntry 5 }

        transceiverDdmInfoProfileWarnMin OBJECT-TYPE
        SYNTAX  DisplayString
        MAX-ACCESS  read-write
        STATUS  current
        DESCRIPTION
                      	"Transceiver low warn threshold.
						 The unit for temperature is 0.01C, value range <12800 ~ -12800>
						 The unit for voltage is 0.01V, value range <655 ~ 0>
						 The unit for TX bias is 0.01mA, value range <13100 ~ 0>
						 The unit for TX power is 0.01dbm, value range <820 ~ -4000>
						 The unit for RX power is 0.01dbm, value range <820 ~ -4000>
						 The value N/A represents transceiver DDM information does not setting."
        ::= { transceiverDdmInfoProfileEntry 6 }


        transceiverDdmInfoProfileDescription OBJECT-TYPE
        SYNTAX  DisplayString
        MAX-ACCESS  read-only
        STATUS  current
        DESCRIPTION
                      	"Transceiver DDM information description. Show N/A if transceiver DDM information is not available."
        ::= { transceiverDdmInfoProfileEntry 7 }

        transceiverDdmInfoProfileRowstatus OBJECT-TYPE
        SYNTAX  RowStatus
        MAX-ACCESS  read-create
        STATUS  current
        DESCRIPTION
                      	"Profile enabled/disabled status."
        ::= { transceiverDdmInfoProfileEntry 8 }

				timeSlot OBJECT-TYPE
        SYNTAX      INTEGER
        MAX-ACCESS  read-only
        STATUS      current
        DESCRIPTION
         	" Index of each ont DDMI history entry."
    	::= { transceiverDdmInfoProfileEntry 9}

-- 		transceiverPerOntTable

        transceiverPerOntTable	OBJECT-TYPE
        SYNTAX	SEQUENCE OF TransceiverPerOntEntry
        MAX-ACCESS  not-accessible
        STATUS  current
        DESCRIPTION
                 	"Per ONT measure value on OLT GPON transceiver "
        ::= { transceiverInfo 4 }

		transceiverPerOntEntry OBJECT-TYPE
        SYNTAX	TransceiverPerOntEntry
        MAX-ACCESS	not-accessible
        STATUS	current
        DESCRIPTION    	"An entry in transceiverPerOntTable."
        INDEX {
        		dot1dBasePort,
        		transceiverPerOntNumber
        }
        ::= { transceiverPerOntTable 1 }

        TransceiverPerOntEntry ::=
           SEQUENCE {
            transceiverPerOntNumber		     	  INTEGER,
            transceiverPerOntRxPower			DisplayString
        }

	   transceiverPerOntNumber OBJECT-TYPE
        SYNTAX  INTEGER
        MAX-ACCESS  not-accessible
        STATUS  current
        DESCRIPTION
         	" transceiverPerOntNumber is the number of configuration."
    	::= { transceiverPerOntEntry 1 }

        transceiverPerOntRxPower OBJECT-TYPE
        SYNTAX  DisplayString
        MAX-ACCESS  read-only
        STATUS  current
        DESCRIPTION
             	"Transceiver high alarm threshold.
						 ++ : high alarm, + : high warn, - : low warn, -- : low alarm
						 The unit for RX power is 0.01dbm
						 The value neg inf represents negative infinit(0mW)
						 The value N/A represents not applicable."
        ::= { transceiverPerOntEntry 2 }


-- ******************************************************************
-- *
-- 118. dot3OamSetup
-- *
-- ******************************************************************
--
--        dot3OamState OBJECT-TYPE
--        SYNTAX  EnabledStatus
--        MAX-ACCESS  read-write
--        STATUS  current
--        DESCRIPTION
--                      	""
--        ::= { dot3OamSetup 1 }
--
--
-- 		dot3OamPortTable
--
--        dot3OamPortTable OBJECT-TYPE
--        SYNTAX	SEQUENCE OF Dot3OamPortEntry
--        MAX-ACCESS  not-accessible
--        STATUS  current
--        DESCRIPTION
--                 	""
--        ::= { dot3OamSetup 2 }
--
--		dot3OamPortEntry OBJECT-TYPE
--        SYNTAX	Dot3OamPortEntry
--        MAX-ACCESS	not-accessible
--        STATUS	current
--        DESCRIPTION    	"An entry in dot3OamPortTable."
--        INDEX          	{ ifIndex }
--        ::= { dot3OamPortTable 1 }
--
--        Dot3OamPortEntry ::=
--           SEQUENCE {
--	       dot3OamFunctionsSupported          BITS
--           }
--
--        dot3OamFunctionsSupported OBJECT-TYPE
--        SYNTAX      BITS {
--                      unidirectionalSupport (0),
--                      loopbackSupport(1),
--                      eventSupport(2),
--                      variableSupport(3)
--                    }
--        MAX-ACCESS  read-write
--        STATUS	current
--        DESCRIPTION
--          "The OAM functions supported on this Ethernet-like interface.
--          OAM consists of separate functional sets beyond the basic
--          discovery process that is always required.  These functional
--          groups can be supported independently by any implementation.
--          These values are communicated to the peer via the local
--          configuration field of Information OAMPDUs.
--
--          Setting 'unidirectionalSupport(0)' indicates that the OA
--          entity supports the transmission of OAMPDUs on links that are
--          operating in unidirectional mode (traffic flowing in one
--          direction only).  Setting 'loopbackSupport(1)' indicates that
--          the OAM entity can initiate and respond to loopback commands.
--          Setting 'eventSupport(2)' indicates that the OAM entity can
--          send and receive Event Notification OAMPDUs.  Setting
--          'variableSupport(3)' indicates that the OAM entity can send
--          and receive Variable Request and Response OAMPDUs.
--          "
--        REFERENCE   "[802.3ah], 30.3.6.1.6"
--        ::= { dot3OamPortEntry 1 }

-- ******************************************************************
-- *
-- 119. dot1agCfmMib
-- *
-- ******************************************************************

		dot1agCfmMIBObjects         OBJECT IDENTIFIER ::= { dot1agCfmSetup 1 }

	-- ******************************************************************
	-- Groups in the CFM MIB Module
	-- ******************************************************************
		dot1agCfmMep             OBJECT IDENTIFIER ::= { dot1agCfmMIBObjects 7 }

	-- ******************************************************************
	-- The MEP Table
	-- ******************************************************************

		zyswdot1agCfmMepTable OBJECT-TYPE
	    SYNTAX      SEQUENCE OF Zyswdot1agCfmMepEntry
	    MAX-ACCESS  not-accessible
	    STATUS      current
	    DESCRIPTION
	       ""
	    ::= { dot1agCfmMep 1 }

	   	zyswdot1agCfmMepEntry OBJECT-TYPE
	    SYNTAX      Zyswdot1agCfmMepEntry
	    MAX-ACCESS  not-accessible
	    STATUS      current
	    DESCRIPTION
	       "The dot1agCfmMep table entry"
	    INDEX { dot1agCfmMdIndex,
	            dot1agCfmMaIndex,
	            dot1agCfmMepIdentifier
	          }
	    ::= { zyswdot1agCfmMepTable 1 }

		Zyswdot1agCfmMepEntry ::= SEQUENCE {
	      zyswdot1agCfmMepTransmitLbmDataTlvSize           Unsigned32
	    }

		zyswdot1agCfmMepTransmitLbmDataTlvSize OBJECT-TYPE
	    SYNTAX      Unsigned32 (0..1500)
	    MAX-ACCESS  	read-write
	    STATUS      current
	    DESCRIPTION
	       "Size of data to be included in the LBM Data TLV"
	    REFERENCE
	       ""
	    ::= { zyswdot1agCfmMepEntry 1 }


-- ******************************************************************
-- *
-- 122. Vlan counter mib
-- *
-- ******************************************************************
--
----		-- VlanCounter Table
--		vlanCounterTable OBJECT-TYPE
--	    SYNTAX      SEQUENCE OF VlanCounterEntry
--        MAX-ACCESS  not-accessible
--	    STATUS      current
--	    DESCRIPTION
--	            "Defines the Vlan Counter Table for providing, via SNMP,
--       	 		the capability of performing vlan counting operations at
--        		a remote host and having their results of these operations are
--        		stored in the table."
--        ::= { vlanCounterSetup 1 }
--
--    	vlanCounterEntry OBJECT-TYPE
--        SYNTAX      VlanCounterEntry
--        MAX-ACCESS  not-accessible
--        STATUS      current
--        DESCRIPTION
--            "Defines an entry in the VlanCounterTable."
--        INDEX {
--                vlanCounterVlanID
--        }
--    	::= { vlanCounterTable 1 }
--
--   		VlanCounterEntry ::=
--        SEQUENCE {
--            vlanCounterVlanID                  Unsigned32,
--            vlanCounterHCOctets                Counter64,
--            vlanCounterHCPkts                  Counter64,
--            vlanCounterHCMulticastPkts         Counter64,
--            vlanCounterHCBroadcastPkts         Counter64,
--            vlanCounterHCTaggedPkts            Counter64,
--            vlanCounterHCPkts64Octets	       Counter64,
--            vlanCounterHCPkts65to127Octets     Counter64,
--            vlanCounterHCPkts128to255Octets    Counter64,
--            vlanCounterHCPkts256to511Octets    Counter64,
--            vlanCounterHCPkts512to1023Octets   Counter64,
--            vlanCounterHCPkts1024to1518Octets  Counter64,
--            vlanCounterHCOversizePkts          Counter64,
--            vlanCounterTimeout                 Unsigned32,
--            vlanCounterRowStatus               RowStatus,
--			vlanCounterPort                    PortList
--   		}
--
--    	vlanCounterVlanID OBJECT-TYPE
--        SYNTAX      Unsigned32 (1..4094)
--        MAX-ACCESS  read-only
--        STATUS      current
--        DESCRIPTION
--         " VlanID where the vlan counter applies."
--    	::= { vlanCounterEntry 1 }
--
--    	vlanCounterHCOctets OBJECT-TYPE
--        SYNTAX      Counter64
--        UNITS       "Octets"
--        MAX-ACCESS  read-only
--        STATUS      current
--        DESCRIPTION
--            "Average receive Octets"
--        ::= { vlanCounterEntry 2 }
--
--    	vlanCounterHCPkts OBJECT-TYPE
--        SYNTAX      Counter64
--        MAX-ACCESS  read-only
--        STATUS      current
--        DESCRIPTION
--            "Total received packet number"
--        ::= { vlanCounterEntry 3 }
--
--    	vlanCounterHCMulticastPkts OBJECT-TYPE
--        SYNTAX      Counter64
--        MAX-ACCESS  read-only
--        STATUS      current
--        DESCRIPTION
--            "Total received multicast-packet number"
--        ::= { vlanCounterEntry 4 }
--
--    	vlanCounterHCBroadcastPkts OBJECT-TYPE
--        SYNTAX      Counter64
--        MAX-ACCESS  read-only
--        STATUS      current
--        DESCRIPTION
--             "Total received Broadcast-packet number"
--        ::= { vlanCounterEntry 5 }
--
--    	vlanCounterHCTaggedPkts OBJECT-TYPE
--        SYNTAX      Counter64
--        MAX-ACCESS  read-only
--        STATUS      current
--        DESCRIPTION
--             "Total received tagged-packet number"
--        ::= { vlanCounterEntry 6 }
--
--    	vlanCounterHCPkts64Octets OBJECT-TYPE
--        SYNTAX      Counter64
--        MAX-ACCESS  read-only
--        STATUS      current
--        DESCRIPTION
--            "Total received packet number in size of 0 to 64 Octets"
--        ::= { vlanCounterEntry 7 }
--
--    	vlanCounterHCPkts65to127Octets OBJECT-TYPE
--        SYNTAX      Counter64
--        MAX-ACCESS  read-only
--        STATUS      current
--        DESCRIPTION
--            "Total received packet number in size of 65 to127 Octets"
--        ::= { vlanCounterEntry 8 }
--
--    	vlanCounterHCPkts128to255Octets OBJECT-TYPE
--        SYNTAX      Counter64
--        MAX-ACCESS  read-only
--        STATUS      current
--        DESCRIPTION
--            "Total received packet number in size of 128 to 255Octets"
--        ::= { vlanCounterEntry 9 }
--
--    	vlanCounterHCPkts256to511Octets  OBJECT-TYPE
--        SYNTAX      Counter64
--        MAX-ACCESS  read-only
--        STATUS      current
--        DESCRIPTION
--            "Total received packet number in size of 256 to 511 Octets"
--        ::= { vlanCounterEntry 10 }
--
--    	vlanCounterHCPkts512to1023Octets OBJECT-TYPE
--        SYNTAX      Counter64
--        MAX-ACCESS  read-only
--        STATUS      current
--        DESCRIPTION
--            "Total received packet number in size of 512 to 1023 Octets"
--        ::= { vlanCounterEntry 11 }
--
--    	vlanCounterHCPkts1024to1518Octets OBJECT-TYPE
--        SYNTAX      Counter64
--        MAX-ACCESS  read-only
--        STATUS      current
--        DESCRIPTION
--            "Total received packet number in size of 1024 to 1518 Octets"
--        ::= { vlanCounterEntry 12 }
--
--    	vlanCounterHCOversizePkts OBJECT-TYPE
--        SYNTAX     Counter64
--        MAX-ACCESS  read-only
--        STATUS      current
--        DESCRIPTION
--            "Total received packet number in size larger than 1519 Octets"
--        ::= { vlanCounterEntry 13 }
--
--    	vlanCounterTimeout OBJECT-TYPE
--        SYNTAX  Unsigned32
--        MAX-ACCESS  read-write
--        STATUS      current
--        DESCRIPTION
--            "Specifies the time-out value, in seconds, for a vlan counter operation."
--        ::= { vlanCounterEntry 14 }
--
--    	vlanCounterRowStatus OBJECT-TYPE
--        SYNTAX      RowStatus
--        MAX-ACCESS  read-write
--        STATUS      current
--        DESCRIPTION
--         "Specifies the time-out value, in seconds, for a vlan counter operation."
--        ::= { vlanCounterEntry 15 }
--
--        vlanCounterPort OBJECT-TYPE
--    	SYNTAX		PortList
--    	MAX-ACCESS	read-write
--    	STATUS		current
--    	DESCRIPTION
--    		"Port where the vlan counter applies. (Only support one or all bit setting now)"
--    	::= { vlanCounterEntry 16 }

-- ******************************************************************
-- *
-- 124.memory usage MIB
-- *
-- ******************************************************************

		sysMemoryPoolTable OBJECT-TYPE
	    SYNTAX      SEQUENCE OF SysMemoryPoolEntry
	    MAX-ACCESS  not-accessible
	    STATUS      current
	    DESCRIPTION
	    ""
    	::= { sysMemoryPool 1 }

    	sysMemoryPoolEntry OBJECT-TYPE
        SYNTAX      SysMemoryPoolEntry
        MAX-ACCESS  not-accessible
        STATUS      current
        DESCRIPTION
            "A system memory pool entry"
        INDEX {
            sysMemoryPoolId
        }
    	::= { sysMemoryPoolTable 1 }

    	SysMemoryPoolEntry ::=
        SEQUENCE {
            sysMemoryPoolId       Unsigned32,
            sysMemoryPoolName     OCTET STRING,
            sysMemoryPoolTotal    Unsigned32,
            sysMemoryPoolUsed     Unsigned32,
            sysMemoryPoolUtil     Unsigned32
        }

    	sysMemoryPoolId OBJECT-TYPE
        SYNTAX      Unsigned32
        MAX-ACCESS  read-only
        STATUS      current
        DESCRIPTION
         "The memory pool id "
    	::= { sysMemoryPoolEntry 1 }

    	sysMemoryPoolName OBJECT-TYPE
        SYNTAX      OCTET STRING(SIZE (0..32))
        MAX-ACCESS  read-only
        STATUS      current
        DESCRIPTION
         "Name of the memory pool "
    	::= { sysMemoryPoolEntry 2 }

    	sysMemoryPoolTotal OBJECT-TYPE
        SYNTAX      Unsigned32
        MAX-ACCESS  read-only
        STATUS      current
        DESCRIPTION
        "Total size of memory pool in bytes "
    	::= { sysMemoryPoolEntry 3 }

   		sysMemoryPoolUsed OBJECT-TYPE
        SYNTAX      Unsigned32
        MAX-ACCESS  read-only
        STATUS      current
        DESCRIPTION
        "Used size of memory pool in bytes "
    	::= { sysMemoryPoolEntry 4 }

    	sysMemoryPoolUtil OBJECT-TYPE
        SYNTAX      Unsigned32 (0..100)
        MAX-ACCESS  read-only
        STATUS      current
        DESCRIPTION
        "Utilization of memory pool in bytes "
    	::= { sysMemoryPoolEntry 5 }

-- 	******************************************************************
-- *
-- 125. PPPoE IA
-- *
-- ******************************************************************
--
    	pppoeIaSetup	OBJECT IDENTIFIER ::= { pppoe 1 }

        pppoeIaState	OBJECT-TYPE
		SYNTAX	EnabledStatus
		MAX-ACCESS	read-write
		STATUS	current
		DESCRIPTION
                      	"Enable/Disable PPPoE intermediate agent."
		::= { pppoeIaSetup 1 }


--
--      pppoe ia interface table
--

        pppoeIaPortTable    OBJECT-TYPE
        SYNTAX  SEQUENCE OF PppoeIaPortEntry
        MAX-ACCESS  not-accessible
        STATUS  current
        DESCRIPTION
                    ""

        ::= { pppoeIaSetup 7 }

        pppoeIaPortEntry OBJECT-TYPE
        SYNTAX	PppoeIaPortEntry
        MAX-ACCESS	not-accessible
        STATUS	current
        DESCRIPTION
                       "An entry in pppoeIaPortTable."
        INDEX          	{ dot1dBasePort }
        ::= { pppoeIaPortTable 1 }

        PppoeIaPortEntry ::=
        SEQUENCE {
        	pppoeIaPortEntryPort			INTEGER,
        	pppoeIaPortEntryTrust			EnabledStatus
        }

        pppoeIaPortEntryPort OBJECT-TYPE
        SYNTAX  INTEGER
        MAX-ACCESS  read-only
        STATUS  current
        DESCRIPTION
                      	"Port index of the specified entry."
        ::= { pppoeIaPortEntry 1 }

        pppoeIaPortEntryTrust OBJECT-TYPE
        SYNTAX  EnabledStatus
        MAX-ACCESS  read-write
        STATUS  current
        DESCRIPTION
                      	"Set the specified port as pppoe-ia trusted port."
        ::= { pppoeIaPortEntry 2 }

--
--
--  	pppoe ia vlan table
--
        pppoeIaVlanTable	OBJECT-TYPE
        SYNTAX	SEQUENCE OF PppoeIaVlanEntry
        MAX-ACCESS  not-accessible
        STATUS  current
        DESCRIPTION
                 	""
        ::= { pppoeIaSetup 8 }

		pppoeIaVlanEntry OBJECT-TYPE
        SYNTAX	PppoeIaVlanEntry
        MAX-ACCESS	not-accessible
        STATUS	current
        DESCRIPTION    	""
        INDEX          	{ pppoeIaVlanEntryVid }
        ::= { pppoeIaVlanTable 1 }

        PppoeIaVlanEntry ::=
		SEQUENCE {
        	pppoeIaVlanEntryVid				INTEGER,
        	pppoeIaVlanEntryCircuitID		EnabledStatus,
        	pppoeIaVlanEntryRemoteID		EnabledStatus,
        	pppoeIaVlanEntryRowStatus		RowStatus
        }

        pppoeIaVlanEntryVid	OBJECT-TYPE
        SYNTAX  INTEGER (1..4094)
        MAX-ACCESS  read-only
        STATUS  current
        DESCRIPTION
                      	"The vlan id."
        ::= { pppoeIaVlanEntry 1 }

        pppoeIaVlanEntryCircuitID	OBJECT-TYPE
        SYNTAX  EnabledStatus
        MAX-ACCESS  read-write
        STATUS  current
        DESCRIPTION
                      	"Enable/Disable circuit-id in corresponding vlan."
        ::= { pppoeIaVlanEntry 2 }

        pppoeIaVlanEntryRemoteID	OBJECT-TYPE
        SYNTAX  EnabledStatus
        MAX-ACCESS  read-write
        STATUS  current
        DESCRIPTION
                      	"Enable/Disable remote-id in corresponding vlan."
        ::= { pppoeIaVlanEntry 3 }

        pppoeIaVlanEntryRowStatus	OBJECT-TYPE
        SYNTAX  RowStatus
        MAX-ACCESS  read-create
        STATUS  current
        DESCRIPTION
                      	"The status of pppoe ia vlan entry."
        ::= { pppoeIaVlanEntry 4 }



		--
--  	pppoe ia vlan Opt82 table
--
        pppoeIaVlanOpt82Table	OBJECT-TYPE
        SYNTAX	SEQUENCE OF PppoeIaVlanOpt82Entry
        MAX-ACCESS  not-accessible
        STATUS  current
        DESCRIPTION
                 	""
        ::= { pppoeIaSetup 10 }

		pppoeIaVlanOpt82Entry OBJECT-TYPE
        SYNTAX	PppoeIaVlanOpt82Entry
        MAX-ACCESS	not-accessible
        STATUS	current
        DESCRIPTION    	""
        INDEX          	{ pppoeIaVlanOpt82EntryVid }
        ::= { pppoeIaVlanOpt82Table 1 }

        PppoeIaVlanOpt82Entry ::=
		SEQUENCE {
        	pppoeIaVlanOpt82EntryVid				INTEGER,
        	pppoeIaVlanOpt82Enable					EnabledStatus,
			pppoeIaVlanOpt82EntryCircuitIDString		DisplayString,
        	pppoeIaVlanOpt82EntryRemoteIDString		DisplayString,
        	pppoeIaVlanOpt82EntryRowStatus		RowStatus
        }

        pppoeIaVlanOpt82EntryVid	OBJECT-TYPE
        SYNTAX  INTEGER (1..4094)
        MAX-ACCESS  read-only
        STATUS  current
        DESCRIPTION
                      	"The vlan id."
        ::= { pppoeIaVlanOpt82Entry 1 }

        pppoeIaVlanOpt82Enable	OBJECT-TYPE
        SYNTAX  EnabledStatus
        MAX-ACCESS  read-write
        STATUS  current
        DESCRIPTION
                      	"Enable/Disable Option82 in corresponding vlan."
        ::= { pppoeIaVlanOpt82Entry 2 }

		pppoeIaVlanOpt82EntryCircuitIDString OBJECT-TYPE
        SYNTAX  DisplayString
        MAX-ACCESS  read-write
        STATUS  current
        DESCRIPTION
                      	"The Option82 circuit-id string of pppoe ia vlan entry."
        ::= { pppoeIaVlanOpt82Entry 3 }

       pppoeIaVlanOpt82EntryRemoteIDString OBJECT-TYPE
        SYNTAX  DisplayString
        MAX-ACCESS  read-write
        STATUS  current
        DESCRIPTION
                      	"The Option82 remote-id string of pppoe ia vlan entry."
        ::= { pppoeIaVlanOpt82Entry 4 }

        pppoeIaVlanOpt82EntryRowStatus	OBJECT-TYPE
        SYNTAX  RowStatus
        MAX-ACCESS  read-create
        STATUS  current
        DESCRIPTION
                      	"The status of pppoe ia vlan Opt82 entry."
        ::= { pppoeIaVlanOpt82Entry 5 }

--
--  	pppoe client test table
--
        pppoeClientTestTable OBJECT-TYPE
        SYNTAX	SEQUENCE OF PppoeClientTestEntry
        MAX-ACCESS  not-accessible
        STATUS  current
        DESCRIPTION
                 	""
        ::= { pppoe 2 }

		pppoeClientTestEntry OBJECT-TYPE
        SYNTAX	PppoeClientTestEntry
        MAX-ACCESS	not-accessible
        STATUS	current
        DESCRIPTION    	"An entry in pppoe client test table."
        INDEX          	{ pppoeClientTestEntryIndex}
        ::= { pppoeClientTestTable 1 }

        PppoeClientTestEntry ::=
           SEQUENCE {
        	pppoeClientTestEntryIndex				INTEGER,
        	pppoeClientTestEntryPort				INTEGER,
        	pppoeClientTestEntryOntId				INTEGER,
        	pppoeClientTestEntryOntCardId				INTEGER,
        	pppoeClientTestEntryUniport				INTEGER,
        	pppoeClientTestEntryUsername		DisplayString,
        	pppoeClientTestEntryPassword		DisplayString,
        	pppoeClientTestEntrySNISVID				INTEGER,
        	pppoeClientTestEntrySNICVID				INTEGER,
        	pppoeClientTestEntryNNISVID				INTEGER,
        	pppoeClientTestEntryUNIVID				INTEGER,
        	pppoeClientTestEntrySn		DisplayString,
        	pppoeClientTestEntryTimeout				INTEGER,
        	pppoeClientTestEntryIpaddr				IpAddress,
        	pppoeClientTestEntryStatus				INTEGER
           }
        pppoeClientTestEntryIndex OBJECT-TYPE
        SYNTAX  INTEGER
        MAX-ACCESS  read-only
        STATUS  current
        DESCRIPTION
                     	"The pppoe client test id."
        ::= { pppoeClientTestEntry 1 }

        pppoeClientTestEntryPort OBJECT-TYPE
        SYNTAX  INTEGER
        MAX-ACCESS  read-write
        STATUS  current
        DESCRIPTION
                     	"The bridge port of pppoe client test ont uniport."
        ::= { pppoeClientTestEntry 2 }

        pppoeClientTestEntryOntId OBJECT-TYPE
        SYNTAX  INTEGER
        MAX-ACCESS  read-write
        STATUS  current
        DESCRIPTION
                     	"The ontid of pppoe client test ont uniport."
        ::= { pppoeClientTestEntry 3 }

        pppoeClientTestEntryOntCardId OBJECT-TYPE
        SYNTAX  INTEGER
        MAX-ACCESS  read-write
        STATUS  current
        DESCRIPTION
                     	"The ontcard id of pppoe client test ont uniport."
        ::= { pppoeClientTestEntry 4 }

        pppoeClientTestEntryUniport OBJECT-TYPE
        SYNTAX  INTEGER
        MAX-ACCESS  read-write
        STATUS  current
        DESCRIPTION
                     	"The uniport id of pppoe client test ont uniport."
        ::= { pppoeClientTestEntry 5 }

        pppoeClientTestEntryUsername OBJECT-TYPE
        SYNTAX  DisplayString
        MAX-ACCESS  read-write
        STATUS  current
        DESCRIPTION
                      	"The username of pppoe client test, max length 31."
        ::= { pppoeClientTestEntry 6 }

        pppoeClientTestEntryPassword OBJECT-TYPE
        SYNTAX  DisplayString
        MAX-ACCESS  read-write
        STATUS  current
        DESCRIPTION
                      	"The password of pppoe client test, max length 31."
        ::= { pppoeClientTestEntry 7 }

        pppoeClientTestEntrySNISVID OBJECT-TYPE
        SYNTAX  INTEGER (1..4094)
        MAX-ACCESS  read-write
        STATUS  current
        DESCRIPTION
                     	"The snisvid of pppoe client test for pppoe ia info."
        ::= { pppoeClientTestEntry 8 }

        pppoeClientTestEntrySNICVID OBJECT-TYPE
        SYNTAX  INTEGER (0..4094)
        MAX-ACCESS  read-write
        STATUS  current
        DESCRIPTION
                     	"The snicvid of pppoe client test for pppoe ia info."
        ::= { pppoeClientTestEntry 9 }

        pppoeClientTestEntryNNISVID OBJECT-TYPE
        SYNTAX  INTEGER (0..4094)
        MAX-ACCESS  read-write
        STATUS  current
        DESCRIPTION
                     	"The nnisvid of pppoe client test for pppoe ia info."
        ::= { pppoeClientTestEntry 10 }

        pppoeClientTestEntryUNIVID OBJECT-TYPE
        SYNTAX  INTEGER (0..4094)
        MAX-ACCESS  read-write
        STATUS  current
        DESCRIPTION
                     	"The univid of pppoe client test for pppoe ia info."
        ::= { pppoeClientTestEntry 11 }

        pppoeClientTestEntrySn OBJECT-TYPE
        SYNTAX  DisplayString
        MAX-ACCESS  read-write
        STATUS  current
        DESCRIPTION
                      	"The serial number of ont to pppoe client test, length 16."
        ::= { pppoeClientTestEntry 12 }

        pppoeClientTestEntryTimeout OBJECT-TYPE
        SYNTAX  INTEGER (10..300)
        MAX-ACCESS  read-write
        STATUS  current
        DESCRIPTION
                     	"The timeout of pppoe client test <10-300>."
        ::= { pppoeClientTestEntry 13 }

        pppoeClientTestEntryIpaddr OBJECT-TYPE
        SYNTAX  IpAddress
        MAX-ACCESS  read-only
        STATUS  current
        DESCRIPTION
                     	"The ip address pppoe client test get"
        ::= { pppoeClientTestEntry 14 }

        pppoeClientTestEntryStatus OBJECT-TYPE
        SYNTAX  INTEGER{
        	idle(0),
        	onging(1),
        	success(2),
        	fail(3),
        	start(4)
        }
        MAX-ACCESS  read-write
        STATUS  current
        DESCRIPTION
                     	"The status of pppoe client test."
        ::= { pppoeClientTestEntry 15 }


-- 	******************************************************************
-- *
-- 126.arpLearningPortTable
-- *
-- ******************************************************************

        arpLearningPortTable OBJECT-TYPE
        SYNTAX	SEQUENCE OF ArpLearningPortEntry
        MAX-ACCESS  not-accessible
        STATUS  current
        DESCRIPTION
                 	""
        ::= { arpLearningSetup 1 }

		arpLearningPortEntry OBJECT-TYPE
        SYNTAX	ArpLearningPortEntry
        MAX-ACCESS	not-accessible
        STATUS	current
        DESCRIPTION    	"An entry in arpLearningPortTable.
        				 Modes: arp-reply(0), gratuitous-arp(1), arp-request(2)"
        INDEX          	{ dot1dBasePort }
        ::= { arpLearningPortTable 1 }

        ArpLearningPortEntry ::=
           SEQUENCE {
        	arpLearningPortMode		INTEGER
           }

        arpLearningPortMode OBJECT-TYPE
        SYNTAX  INTEGER {
        		arpReply(0),
        		gratuitousArp(1),
        		arpRequest(2)
       	}
        MAX-ACCESS  read-write
        STATUS  current
        DESCRIPTION
                      	"ArpLearning Mode on the port."
        ::= { arpLearningPortEntry 1 }



-- 	******************************************************************
-- *
-- 127. Static Route ( ECMP )
-- *
-- ******************************************************************

        maxNumberOfStaticRoutes OBJECT-TYPE
        SYNTAX  INTEGER
        MAX-ACCESS  read-only
        STATUS  current
        DESCRIPTION
                      	"The maximum number of static route entries that can be created"
        ::= { staticRouteSetup 1 }

-- 		staticRouteTable
        staticRouteTable OBJECT-TYPE
        SYNTAX	SEQUENCE OF StaticRouteEntry
        MAX-ACCESS  not-accessible
        STATUS  current
        DESCRIPTION
                 	""
        ::= { staticRouteSetup 2 }

		staticRouteEntry OBJECT-TYPE
        SYNTAX	StaticRouteEntry
        MAX-ACCESS	not-accessible
        STATUS	current
        DESCRIPTION    	"The static route table entry."
        INDEX          	{ staticRouteIp, staticRouteMask, staticRouteGateway}
        ::= { staticRouteTable 1 }

        StaticRouteEntry ::=
           SEQUENCE {
           	staticRouteName		DisplayString,
        	staticRouteIp		IpAddress,
        	staticRouteMask		IpAddress,
        	staticRouteGateway	IpAddress,
        	staticRouteMetric	INTEGER,
        	staticRouteRowStatus	RowStatus
           }

        staticRouteName OBJECT-TYPE
        SYNTAX  DisplayString
        MAX-ACCESS  read-write
        STATUS  current
        DESCRIPTION
                      	"The name of the static route entry."
        ::= { staticRouteEntry 1 }

        staticRouteIp OBJECT-TYPE
        SYNTAX  IpAddress
        MAX-ACCESS  not-accessible
        STATUS  current
        DESCRIPTION
                     	"The destination ip address of the static route entry."
        ::= { staticRouteEntry 2 }

        staticRouteMask OBJECT-TYPE
        SYNTAX  IpAddress
        MAX-ACCESS  not-accessible
        STATUS  current
        DESCRIPTION
                     	"The mask of the static route entry."
        ::= { staticRouteEntry 3 }

        staticRouteGateway OBJECT-TYPE
        SYNTAX  IpAddress
        MAX-ACCESS  not-accessible
        STATUS  current
        DESCRIPTION
                     	"The gateway of the static route entry."
        ::= { staticRouteEntry 4 }

        staticRouteMetric OBJECT-TYPE
        SYNTAX  INTEGER
        MAX-ACCESS  read-write
        STATUS  current
        DESCRIPTION
                     	"The metric of the static route entry."
        ::= { staticRouteEntry 5 }

        staticRouteRowStatus OBJECT-TYPE
        SYNTAX  RowStatus
        MAX-ACCESS  read-create
        STATUS  current
        DESCRIPTION
                     	"The status of the static route entry."

        ::= { staticRouteEntry 6 }

-- 	******************************************************************
-- *
-- 128. Routing Status ( ECMP )
-- *
-- ******************************************************************

        routingStatusTable	OBJECT-TYPE
        SYNTAX	SEQUENCE OF RoutingStatusEntry
        MAX-ACCESS  not-accessible
        STATUS  current
        DESCRIPTION
                 	"The routing table"
        ::= { routingStatus 1 }

		routingStatusEntry OBJECT-TYPE
        SYNTAX	RoutingStatusEntry
        MAX-ACCESS	not-accessible
        STATUS	current
        DESCRIPTION    	""
		INDEX          	{ routingStatusDestAddress, routingStatusDestMaskbits, routingStatusGateway}
        ::= { routingStatusTable 1 }

        RoutingStatusEntry ::=
		SEQUENCE {
        	routingStatusDestAddress	IpAddress,
        	routingStatusDestMaskbits	INTEGER,
        	routingStatusGateway  		IpAddress,
        	routingStatusInterface		IpAddress,
         routingStatusMetric   		INTEGER,
         routingStatusType   		INTEGER
        }
        routingStatusDestAddress OBJECT-TYPE
        SYNTAX  IpAddress
        MAX-ACCESS  read-only
        STATUS  current
        DESCRIPTION
                      	"The destination ip address of the route entry"
        ::= { routingStatusEntry 1 }

        routingStatusDestMaskbits OBJECT-TYPE
        SYNTAX  INTEGER
        MAX-ACCESS  read-only
        STATUS  current
        DESCRIPTION
                      	"The mask of the route entry"
        ::= { routingStatusEntry 2 }

        routingStatusGateway OBJECT-TYPE
        SYNTAX  IpAddress
        MAX-ACCESS  read-only
        STATUS  current
        DESCRIPTION
                      	"The gateway of the route entry"
        ::= { routingStatusEntry 3 }

        routingStatusInterface OBJECT-TYPE
        SYNTAX  IpAddress
        MAX-ACCESS  read-only
        STATUS  current
        DESCRIPTION
                      	"The interface of the route entry"
        ::= { routingStatusEntry 4 }

        routingStatusMetric OBJECT-TYPE
        SYNTAX  INTEGER
        MAX-ACCESS  read-only
        STATUS  current
        DESCRIPTION
                      	"The metric of the route entry"
        ::= { routingStatusEntry 5 }

        routingStatusType OBJECT-TYPE
        SYNTAX  INTEGER{
			rip(1),
			bgp(2),
			ospf(3),
			static(4)
        }
        MAX-ACCESS  read-only
        STATUS  current
        DESCRIPTION
                      	"The type of the route entry."
        ::= { routingStatusEntry 6 }


-- 	******************************************************************
-- *
-- 129. External Alarm Setup
-- *
-- ******************************************************************

        externalAlarmTable	OBJECT-TYPE
        SYNTAX	SEQUENCE OF ExternalAlarmEntry
        MAX-ACCESS  not-accessible
        STATUS  current
        DESCRIPTION
                 	"The external alarm table"
        ::= { externalAlarmSetup 1 }

		externalAlarmEntry OBJECT-TYPE
        SYNTAX	ExternalAlarmEntry
        MAX-ACCESS	not-accessible
        STATUS	current
        DESCRIPTION    	""
		INDEX          	{ externalAlarmIndex }
        ::= { externalAlarmTable 1 }

        ExternalAlarmEntry ::=
		SEQUENCE {
        	externalAlarmIndex     INTEGER,
        	externalAlarmName      DisplayString,
        	externalAlarmStatus    INTEGER
        }
        externalAlarmIndex OBJECT-TYPE
        SYNTAX  INTEGER
        MAX-ACCESS  read-only
        STATUS  current
        DESCRIPTION
                      	"The external Alarm Index"
        ::= { externalAlarmEntry 1 }

        externalAlarmName OBJECT-TYPE
        SYNTAX  DisplayString
        MAX-ACCESS  read-write
        STATUS  current
        DESCRIPTION
                      	"The external Alarm Name"
        ::= { externalAlarmEntry 2 }

        externalAlarmStatus OBJECT-TYPE
        SYNTAX  INTEGER{
            asserted(1),
            notasserted(2)
        }
        MAX-ACCESS  read-only
        STATUS  current
        DESCRIPTION
                      	"The external alarm status"
        ::= { externalAlarmEntry 3 }


-- ******************************************************************
-- *
-- 130. errdisable
-- *
-- ******************************************************************

	recovery             OBJECT IDENTIFIER ::= { errdisable 1 }


	errdisableRecoverySetup  OBJECT IDENTIFIER ::= { recovery 1 }

        errdisableRecoveryState OBJECT-TYPE
        SYNTAX  EnabledStatus
        MAX-ACCESS  read-write
        STATUS  current
        DESCRIPTION
                      ""
        ::= { errdisableRecoverySetup 1 }

--	errdisableRecoveryReasonTable
	errdisableRecoveryReasonTable OBJECT-TYPE
        SYNTAX	SEQUENCE OF ErrdisableRecoveryReasonEntry
        MAX-ACCESS  not-accessible
        STATUS  current
        DESCRIPTION
                 	""
        ::= { errdisableRecoverySetup 2 }

	errdisableRecoveryReasonEntry OBJECT-TYPE
        SYNTAX	ErrdisableRecoveryReasonEntry
        MAX-ACCESS	not-accessible
        STATUS	current
        DESCRIPTION    	""
        INDEX          	{ errdisableRecoveryReason }
        ::= { errdisableRecoveryReasonTable 1 }

        ErrdisableRecoveryReasonEntry ::=
           SEQUENCE {
        	errdisableRecoveryReason	INTEGER,
        	errdisableRecoveryReasonActive	EnabledStatus,
			errdisableRecoveryReasonInterval	INTEGER
           }

        errdisableRecoveryReason OBJECT-TYPE
        SYNTAX  INTEGER {
        		loopguard(0),
        		arp(1),
        		bpdu(2),
			igmp(3),
         		pppoe(4),
        		ftp(5),
        		icmp(6)
       }
        MAX-ACCESS  read-only
        STATUS  current
        DESCRIPTION
                      	""
        ::= { errdisableRecoveryReasonEntry 1 }

        errdisableRecoveryReasonActive OBJECT-TYPE
        SYNTAX  INTEGER {
        		enabled(1),
        		disabled(2)
        }

        MAX-ACCESS  read-write
        STATUS  current
        DESCRIPTION
                      	""
        ::= { errdisableRecoveryReasonEntry 2 }

        errdisableRecoveryReasonInterval OBJECT-TYPE
        SYNTAX  INTEGER (30..2592000)
        MAX-ACCESS  read-write
        STATUS  current
        DESCRIPTION
                      	""
        ::= { errdisableRecoveryReasonEntry 3 }

--	errdisableRecoveryIfStatusTable
	errdisableRecoveryIfStatusTable OBJECT-TYPE
        SYNTAX	SEQUENCE OF ErrdisableRecoveryIfStatusEntry
        MAX-ACCESS  not-accessible
        STATUS  current
        DESCRIPTION
                 	""
        ::= { errdisableRecoverySetup 3 }

	errdisableRecoveryIfStatusEntry OBJECT-TYPE
        SYNTAX	ErrdisableRecoveryIfStatusEntry
        MAX-ACCESS	not-accessible
        STATUS	current
        DESCRIPTION    	""
        INDEX          	{ errdisableRecoveryIfStatusReason,errdisableRecoveryIfStatusPort }
        ::= { errdisableRecoveryIfStatusTable 1 }

        ErrdisableRecoveryIfStatusEntry ::=
           SEQUENCE {
        	errdisableRecoveryIfStatusReason	INTEGER,
        	errdisableRecoveryIfStatusPort	    INTEGER,
			errdisableRecoveryIfStatusTimeToRecover	INTEGER
           }

        errdisableRecoveryIfStatusReason OBJECT-TYPE
        SYNTAX  INTEGER {
        	loopguard(0),
        	arp(1),
        	bpdu(2),
        	igmp(3),
        	pppoe(4),
        	ftp(5),
        	icmp(6)
        }
        MAX-ACCESS  read-only
        STATUS  current
        DESCRIPTION
                      	""
        ::= { errdisableRecoveryIfStatusEntry 1 }

        errdisableRecoveryIfStatusPort OBJECT-TYPE
        SYNTAX  INTEGER
        MAX-ACCESS  read-only
        STATUS  current
        DESCRIPTION
                      	""
        ::= { errdisableRecoveryIfStatusEntry 2 }

        errdisableRecoveryIfStatusTimeToRecover OBJECT-TYPE
        SYNTAX  INTEGER (30..2592000)
        MAX-ACCESS  read-only
        STATUS  current
        DESCRIPTION
                     	""
        ::= { errdisableRecoveryIfStatusEntry 3 }

	detect             OBJECT IDENTIFIER ::= { errdisable 2 }


	    errdisableDetectReasonTable	OBJECT-TYPE
        SYNTAX	SEQUENCE OF  ErrdisableDetectReasonEntry
        MAX-ACCESS  not-accessible
        STATUS  current
        DESCRIPTION
                 	""
        ::= { detect 1 }

       	errdisableDetectReasonEntry OBJECT-TYPE
        SYNTAX	ErrdisableDetectReasonEntry
        MAX-ACCESS	not-accessible
        STATUS	current
        DESCRIPTION    	"An entry in errdisableDetectReasonTable."
        INDEX          	{ errdisableDetectReason }
        ::= { errdisableDetectReasonTable 1 }

        ErrdisableDetectReasonEntry ::=
	SEQUENCE {
        	errdisableDetectReason    INTEGER,
        	errdisableDetectReasonEnable	EnabledStatus,
        	errdisableDetectReasonMode	INTEGER
         }


        errdisableDetectReason OBJECT-TYPE
        SYNTAX  INTEGER{
        	arp(1),
        	bpdu(2),
		igmp(3),
        	pppoe(4),
        	ftp(5),
        	icmp(6)
       	}
        MAX-ACCESS  read-only
        STATUS  current
        DESCRIPTION
                      	""
        ::= { errdisableDetectReasonEntry 1 }



        errdisableDetectReasonEnable OBJECT-TYPE
        SYNTAX  EnabledStatus
        MAX-ACCESS  read-write
        STATUS  current
        DESCRIPTION
                      	""
        ::= { errdisableDetectReasonEntry 2 }


        errdisableDetectReasonMode OBJECT-TYPE
        SYNTAX  INTEGER{
        	inactivePort(1),
        	inactiveReason(2),
			rateLimitation(3)
        }
        MAX-ACCESS  read-write
        STATUS  current
        DESCRIPTION
                      	""
        ::= { errdisableDetectReasonEntry 3 }

	errdisableTrapInfoObject  OBJECT IDENTIFIER ::= { errdisable 3 }

    errdisableTrapPort OBJECT-TYPE
        SYNTAX  INTEGER
        MAX-ACCESS   read-only
        STATUS  current
        DESCRIPTION
                      ""
        ::= { errdisableTrapInfoObject 1 }

    errdisableTrapReason OBJECT-TYPE
        SYNTAX  INTEGER
        {
        	loopguard(0),
			arp(1),
			bpdu(2),
			igmp(3),
			pppoe(4),
			ftp(5),
			icmp(6)
        }
        MAX-ACCESS  read-only
        STATUS  current
        DESCRIPTION
                      ""
        ::= { errdisableTrapInfoObject 2 }


	errdisableTrapMode  OBJECT-TYPE
        SYNTAX  INTEGER
        {
        	inactivePort(0),
        	inactiveReason(1),
        	rateLimitation(2)
        }
        MAX-ACCESS   read-only
        STATUS  current
        DESCRIPTION
                      ""
        ::= { errdisableTrapInfoObject 3 }


	errdisableTrapNotifications  OBJECT IDENTIFIER ::= { errdisable 4 }


	     errdisableDetectTrap NOTIFICATION-TYPE
         OBJECTS {
               errdisableTrapPort,
               errdisableTrapReason,
               errdisableTrapMode
         }
         STATUS  current
         DESCRIPTION
          ""

		  ::= { errdisableTrapNotifications 1 }

         errdisableRecoveryTrap NOTIFICATION-TYPE
         OBJECTS {
               errdisableTrapPort,
               errdisableTrapReason,
               errdisableTrapMode
         }
         STATUS  current
         DESCRIPTION
          ""
		   ::= { errdisableTrapNotifications 2 }

-- ******************************************************************
-- *
-- 131. CPU protection
-- *
-- ******************************************************************

     cpuProtectionTable	OBJECT-TYPE
        SYNTAX	SEQUENCE OF CPUProtectionEntry
        MAX-ACCESS  not-accessible
        STATUS  current
        DESCRIPTION
                 	""
        ::= { cpuProtectionSetup 1 }

		cpuProtectionEntry OBJECT-TYPE
        SYNTAX	CPUProtectionEntry
        MAX-ACCESS	not-accessible
        STATUS	current
        DESCRIPTION    	"An entry in CPUProtectionTable."
        INDEX          	{ cpuProtectionPort, cpuProtectionReason}
        ::= { cpuProtectionTable 1 }

        CPUProtectionEntry ::=
	SEQUENCE {
        	cpuProtectionPort          INTEGER,
        	cpuProtectionReason    	INTEGER,
        	cpuProtectionRateLimitSet 	INTEGER
          }

        cpuProtectionPort OBJECT-TYPE
        SYNTAX  INTEGER
        MAX-ACCESS  read-only
        STATUS  current
        DESCRIPTION
                      	"The Protected Port"
        ::= { cpuProtectionEntry 1 }


        cpuProtectionReason OBJECT-TYPE
        SYNTAX  INTEGER{
        arp(1),
        bpdu(2),
	igmp(3),
        pppoe(4),
        ftp(5),
        icmp(6)
        }
        MAX-ACCESS  read-only
        STATUS  current
        DESCRIPTION
                      	"The Protected Reason"
        ::= { cpuProtectionEntry 2}


        cpuProtectionRateLimitSet OBJECT-TYPE
        SYNTAX  INTEGER(0..256)
        MAX-ACCESS  read-write
        STATUS  current
        DESCRIPTION
                      	"The rate limit of a reason on a port"
        ::= { cpuProtectionEntry 3}

-- ******************************************************************
-- *
-- 132. Policy Route
-- *
-- ******************************************************************

----	--policy route profile
--     	policyRouteProfileTable	OBJECT-TYPE
--        SYNTAX	SEQUENCE OF PolicyRouteProfileEntry
--        MAX-ACCESS  not-accessible
--        STATUS  current
--        DESCRIPTION
--                 	""
--        ::= { policyRouteSetup 1 }

--		policyRouteProfileEntry OBJECT-TYPE
--        SYNTAX	PolicyRouteProfileEntry
--        MAX-ACCESS	not-accessible
--        STATUS	current
--        DESCRIPTION    	"An profile entry in policyRouteTable."
--        INDEX          	{ policyRouteProfileName}
--        ::= { policyRouteProfileTable 1 }

--        PolicyRouteProfileEntry ::=
--		SEQUENCE {
--        	policyRouteProfileEnable          EnabledStatus,
--        	policyRouteProfileName    		  DisplayString,
--        	policyRouteProfileRowStatus 	  RowStatus
--          }

--        policyRouteProfileEnable OBJECT-TYPE
--        SYNTAX  EnabledStatus
--        MAX-ACCESS  read-write
--        STATUS  current
--        DESCRIPTION
--                      	"Profile enabled/disabled status."
--        ::= { policyRouteProfileEntry 1 }


--        policyRouteProfileName OBJECT-TYPE
--        SYNTAX  DisplayString
--        MAX-ACCESS  read-only
--        STATUS  current
--        DESCRIPTION
--                      	"Profile name of policy route profile."
--        ::= { policyRouteProfileEntry 2 }



--        policyRouteProfileRowStatus OBJECT-TYPE
--        SYNTAX  RowStatus
--        MAX-ACCESS  read-create
--        STATUS  current
--        DESCRIPTION
--                     	"Row Status for policy route profile."

--        ::= { policyRouteProfileEntry 3 }

----	--policy route rule
--     	policyRouteRuleTable	OBJECT-TYPE
--        SYNTAX	SEQUENCE OF PolicyRouteRuleEntry
--        MAX-ACCESS  not-accessible
--        STATUS  current
--        DESCRIPTION
--                 	""
--        ::= { policyRouteSetup 2 }

--		policyRouteRuleEntry OBJECT-TYPE
--        SYNTAX	PolicyRouteRuleEntry
--        MAX-ACCESS	not-accessible
--        STATUS	current
--        DESCRIPTION    	"An rule entry in policyRouteTable."
--        INDEX          	{ policyRouteRuleProfileName, policyRouteRuleSequence}
--        ::= { policyRouteRuleTable 1 }

--        PolicyRouteRuleEntry ::=
--		SEQUENCE {
--        	policyRouteRuleProfileName          DisplayString,
--        	policyRouteRuleSequence    		  	INTEGER,
--        	policyRouteRuleStatement 	  		INTEGER,
--        	policyRouteRuleCalssifier    	    DisplayString,
--        	policyRouteRuleSetNextHop           IpAddress,
--        	policyRouteRuleRowStatus            RowStatus
--          }

--        policyRouteRuleProfileName OBJECT-TYPE
--        SYNTAX  DisplayString
--        MAX-ACCESS  read-only
--        STATUS  current
--        DESCRIPTION
--                      	"Profile name of policy route rule."
--        ::= { policyRouteRuleEntry 1 }


--        policyRouteRuleSequence OBJECT-TYPE
--        SYNTAX  INTEGER
--        MAX-ACCESS  read-only
--        STATUS  current
--        DESCRIPTION
--                      	"Sequence number of policy route rule."
--        ::= { policyRouteRuleEntry 2 }

--  		policyRouteRuleStatement OBJECT-TYPE
--        SYNTAX  INTEGER{
--	        permit(0),
--	        deny(1)
--        }
--        MAX-ACCESS  read-write
--        STATUS  current
--        DESCRIPTION
--                      	"Statement of policy route rule."
--        ::= { policyRouteRuleEntry 3 }

--        policyRouteRuleCalssifier OBJECT-TYPE
--        SYNTAX  DisplayString
--        MAX-ACCESS  read-write
--        STATUS  current
--        DESCRIPTION
--                      	"Classifier of policy route rule."
--        ::= { policyRouteRuleEntry 4 }

--        policyRouteRuleSetNextHop OBJECT-TYPE
--        SYNTAX  IpAddress
--        MAX-ACCESS  read-write
--        STATUS  current
--        DESCRIPTION
--                      	"Next hop IP address if the incoming packets match the criteria. 0.0.0.0 means do nothing."
--        ::= { policyRouteRuleEntry 5 }


--        policyRouteRuleRowStatus OBJECT-TYPE
--        SYNTAX  RowStatus
--        MAX-ACCESS  read-create
--        STATUS  current
--        DESCRIPTION
--                     	"Row Status for policy route rule."
--
--        ::= { policyRouteRuleEntry 6 }

-- ******************************************************************
-- *
-- 133. Private Vlan mib
-- *
-- ******************************************************************
--
--	privateVLANTable OBJECT-TYPE
--		SYNTAX      SEQUENCE OF PrivateVLANEntry
--        MAX-ACCESS  not-accessible
--		STATUS      current
--		DESCRIPTION
--	            ""
--        ::= { privateVLANSetup 1 }
--
--	privateVLANEntry OBJECT-TYPE
--        SYNTAX      PrivateVLANEntry
--        MAX-ACCESS  not-accessible
--        STATUS      current
--        DESCRIPTION ""
--        INDEX { privateVLANVid}
--    	::= { privateVLANTable 1 }
--
--	PrivateVLANEntry ::=
--        SEQUENCE {
--            privateVLANName               DisplayString,
--            privateVLANVid                INTEGER,
--            privateVLANPromiscuousPorts   PortList,
--            privateVLANRowStatus          RowStatus
--   	}
--
--	privateVLANName OBJECT-TYPE
--        SYNTAX      DisplayString
--        MAX-ACCESS  read-write
--        STATUS      current
--        DESCRIPTION
--         	" Private VLAN name."
--    	::= { privateVLANEntry 1 }
--
--	privateVLANVid OBJECT-TYPE
--        SYNTAX      INTEGER (1..4094)
--        MAX-ACCESS  read-only
--        STATUS      current
--        DESCRIPTION
--         	" Private VLAN ID."
--    	::= { privateVLANEntry 2 }
--
--	privateVLANPromiscuousPorts OBJECT-TYPE
--        SYNTAX      PortList
--        MAX-ACCESS  read-write
--        STATUS      current
--        DESCRIPTION
--         	" Private VLAN promiscuous ports."
--    	::= { privateVLANEntry 3 }
--
--	privateVLANRowStatus OBJECT-TYPE
--        SYNTAX      RowStatus
--        MAX-ACCESS  read-write
--        STATUS      current
--        DESCRIPTION
--         	""
--    	::= { privateVLANEntry 4 }
--
-- ******************************************************************
-- *
-- 134.sFlow mib
-- *
-- ******************************************************************
--
--    sFlowState OBJECT-TYPE
--        SYNTAX  EnabledStatus
--        MAX-ACCESS  read-write
--        STATUS  current
--        DESCRIPTION
--        "Sflow enabled/disabled for the switch."
--        ::= { sFlowSetup 1 }
-- *
-- * sFlow Collector Table
-- *
--	sFlowCollectorTable OBJECT-TYPE
--	 	      SYNTAX      SEQUENCE OF SFlowCollectorEntry
--	          MAX-ACCESS  not-accessible
--	          STATUS      current
--	          DESCRIPTION
--	            ""
--              ::= { sFlowSetup 2 }
--
--    sFlowCollectorEntry OBJECT-TYPE
--        SYNTAX      SFlowCollectorEntry
--        MAX-ACCESS  not-accessible
--        STATUS      current
--        DESCRIPTION
--            "An entry in sflowCollectorTable."
--        INDEX {
--            sFlowCollectorAddressType,
--            sFlowCollectorAddress
--        }
--    ::= { sFlowCollectorTable 1 }
--
--    SFlowCollectorEntry ::=
--        SEQUENCE {
--            sFlowCollectorAddressType    InetAddressType,
--            sFlowCollectorAddress        InetAddress,
--            sFlowCollectorUdpPort        Unsigned32,
--            sFlowCollectorRowStatus      RowStatus
--        }
--
--    sFlowCollectorAddressType OBJECT-TYPE
--        SYNTAX      InetAddressType
--        MAX-ACCESS  read-only
--        STATUS      current
--        DESCRIPTION
--         " The Type of IP address for sflow collector entry."
--    ::= { sFlowCollectorEntry 1 }
--
--    sFlowCollectorAddress OBJECT-TYPE
--        SYNTAX      InetAddress
--        MAX-ACCESS  read-only
--        STATUS      current
--        DESCRIPTION
--         "The IP address for sflow collector entry."
--    ::= { sFlowCollectorEntry 2 }
--
--    sFlowCollectorUdpPort OBJECT-TYPE
--        SYNTAX      Unsigned32 (1..65535)
--        MAX-ACCESS  read-write
--        STATUS      current
--        DESCRIPTION
--         "The UDP port for sflow collector entry. The range of UDP port is between 1 and 65535."
--    ::= { sFlowCollectorEntry 3 }
--
--    sFlowCollectorRowStatus OBJECT-TYPE
--        SYNTAX      RowStatus
--        MAX-ACCESS  read-write
--        STATUS      current
--        DESCRIPTION
--         ""
--        ::= { sFlowCollectorEntry 4 }
--
-- *
-- * sFlow Port Table
-- *
--	sFlowPortTable OBJECT-TYPE
--	 	      SYNTAX      SEQUENCE OF SFlowPortEntry
--	          MAX-ACCESS  not-accessible
--	          STATUS      current
--	          DESCRIPTION
--	            ""
--              ::= { sFlowSetup 3 }
--
--    sFlowPortEntry OBJECT-TYPE
--        SYNTAX      SFlowPortEntry
--        MAX-ACCESS  not-accessible
--        STATUS      current
--        DESCRIPTION
--            "An entry in sflowPortTable."
--        INDEX {
--            dot1dBasePort
--        }
--    ::= { sFlowPortTable 1 }
--
--    SFlowPortEntry ::=
--        SEQUENCE {
--           sFlowPortState	EnabledStatus
--         }
--
--    sFlowPortState OBJECT-TYPE
--        SYNTAX  EnabledStatus
--        MAX-ACCESS  read-write
--        STATUS  current
--        DESCRIPTION
--        "Sflow enabled/disabled on the port."
--        ::= { sFlowPortEntry 1 }
--
-- *
-- * sFlow Port Collector Table
-- *
--	sFlowPortCollectorTable OBJECT-TYPE
--	 	      SYNTAX      SEQUENCE OF SFlowPortCollectorEntry
--	          MAX-ACCESS  not-accessible
--	          STATUS      current
--	          DESCRIPTION
--	          ""
--              ::= { sFlowSetup 4 }
--
--    sFlowPortCollectorEntry OBJECT-TYPE
--        SYNTAX      SFlowPortCollectorEntry
--        MAX-ACCESS  not-accessible
--        STATUS      current
--        DESCRIPTION
--            "An entry in sflowCollectorTable."
--        INDEX {
--            dot1dBasePort,
--            sFlowPortCollectorAddressType,
--            sFlowPortCollectorAddress
--        }
--    ::= { sFlowPortCollectorTable 1 }
--
--    SFlowPortCollectorEntry ::=
--        SEQUENCE {
--            sFlowPortCollectorAddressType    InetAddressType,
--            sFlowPortCollectorAddress        InetAddress,
--            sFlowPortCollectorSampleRate     Unsigned32,
--            sFlowPortCollectorPollInterval   Unsigned32,
--            sFlowPortCollectorRowStatus      RowStatus
--        }
--
--    sFlowPortCollectorAddressType OBJECT-TYPE
--        SYNTAX      InetAddressType
--        MAX-ACCESS  read-only
--        STATUS      current
--        DESCRIPTION
--         " The Type of IP address for sflow port collector entry."
--    ::= { sFlowPortCollectorEntry 1 }
--
--    sFlowPortCollectorAddress OBJECT-TYPE
--        SYNTAX      InetAddress
--        MAX-ACCESS  read-only
--        STATUS      current
--        DESCRIPTION
--         "The IP address for sflow port collector entry."
--    ::= { sFlowPortCollectorEntry 2 }
--
--    sFlowPortCollectorSampleRate OBJECT-TYPE
--        SYNTAX      Unsigned32 (256..65535)
--        MAX-ACCESS  read-write
--        STATUS      current
--        DESCRIPTION
--         "The sample rate. The range of samle rate is beteen 256 and 65535."
--    ::= { sFlowPortCollectorEntry 3 }
--
--    sFlowPortCollectorPollInterval OBJECT-TYPE
--        SYNTAX      Unsigned32 (20..120)
--        MAX-ACCESS  read-write
--        STATUS      current
--        DESCRIPTION
--         "The poll interval. The range of poll interval is between 20 and 120."
--    ::= { sFlowPortCollectorEntry 4 }
--
--    sFlowPortCollectorRowStatus OBJECT-TYPE
--        SYNTAX      RowStatus
--        MAX-ACCESS  read-write
--        STATUS      current
--        DESCRIPTION
--         ""
--    ::= { sFlowPortCollectorEntry 5 }


-- ******************************************************************
-- *
-- 135.remoteOnt mib
-- *
-- ******************************************************************

-- *
-- * ont Setup
-- *

    ontSetup OBJECT IDENTIFIER ::= { remoteOnt 1 }

--  ont Table
	ontTable OBJECT-TYPE
		SYNTAX      SEQUENCE OF OntEntry
        MAX-ACCESS  not-accessible
        STATUS  current
        DESCRIPTION
                 	""
        ::= { ontSetup 1 }

	ontEntry OBJECT-TYPE
        SYNTAX      OntEntry
        MAX-ACCESS  not-accessible
        STATUS	current
        DESCRIPTION
        		"An entry in ontTable"
        INDEX {
        		dot1dBasePort,
        		ontNumber
        }
    	::= { ontTable 1 }

	OntEntry ::=
           SEQUENCE {
            ontNumber                     INTEGER,
--            macLimit                    INTEGER,
--            macLimitState               EnabledStatus,
            password                      DisplayString,
            planVersion              	  DisplayString,
            sn                            DisplayString,
            loopbackConfig                EnabledStatus,
            loopbackStatus                INTEGER,
            model                         INTEGER,
            ontRowStatus                  RowStatus,
            ontAction                     INTEGER,
            alarmProfile                  DisplayString,
            fullBridg			  INTEGER,
            antiMacSpoofing		  INTEGER,
            description                   DisplayString,
            templateDescription           DisplayString,
            usFecMode			  EnabledStatus,
            option82DisableDhcp               INTEGER,
            option82PassThroughDhcp           INTEGER,
			option82DisablePppoe               INTEGER,
            option82PassThroughPppoe           INTEGER, 
			ipbinding                EnabledStatus
           }

	ontNumber OBJECT-TYPE
        SYNTAX  INTEGER
        MAX-ACCESS  not-accessible
        STATUS  current
        DESCRIPTION
         	" ontNumber."
    	::= { ontEntry 1 }

--    macLimit OBJECT-TYPE
--        SYNTAX  INTEGER
--        MAX-ACCESS  read-write
--        STATUS  current
--        DESCRIPTION
--         	" mac-limit."
--   	::= { ontEntry 2 }

--    macLimitState OBJECT-TYPE
--        SYNTAX  EnabledStatus
--        MAX-ACCESS  read-write
--        STATUS  current
--        DESCRIPTION
--         	" mac-limit enabled/disabled status."
--    	::= { ontEntry 3 }

 	password OBJECT-TYPE
        SYNTAX  DisplayString
        MAX-ACCESS  read-write
        STATUS  current
        DESCRIPTION
         	" password."
    	::= { ontEntry 4 }

 	planVersion OBJECT-TYPE
        SYNTAX  DisplayString
        MAX-ACCESS  read-write
        STATUS  current
        DESCRIPTION
         	" plan-version."
    	::= { ontEntry 5 }

   	sn OBJECT-TYPE
        SYNTAX      DisplayString
        MAX-ACCESS  read-write
        STATUS      current
        DESCRIPTION
         	" serial number."
    	::= { ontEntry 6 }

		loopbackConfig OBJECT-TYPE
        SYNTAX  EnabledStatus
        MAX-ACCESS  read-write
        STATUS  current
        DESCRIPTION
        	"enabled/disabled loopback on the port."
        ::= { ontEntry 7 }

		loopbackStatus OBJECT-TYPE
        SYNTAX  INTEGER {
        	none(0),
        	underTesting(1),
        	success(2),
        	fail(3)
        }
        MAX-ACCESS  read-only
        STATUS  current
        DESCRIPTION
               "This entry display latest loopback test status of port while performing remote-ont loopback test."
        ::= { ontEntry 8 }

    model OBJECT-TYPE
        SYNTAX  INTEGER {
            default(0),
            pmg1006ORpmg2006ORpmg1005ORpmg2005(1),
            pmg5318b20a(2),
            pmg3000b20a(3),
            na1(4),
            gpt2542gnaucORpmg5318b20bORpmg5318b20cORpmg5317ORpmg5323(5),
            o00xx0vpq(6),
            na2(7),
            gpt2820gnORgpt2840gnORgpt2841hntORgpt2840hnt(8)
        }
        MAX-ACCESS  read-write
        STATUS  current
        DESCRIPTION
               " Model ID."
        ::= { ontEntry 9 }

    ontRowStatus OBJECT-TYPE
        SYNTAX  RowStatus
        MAX-ACCESS  read-create
        STATUS      current
        DESCRIPTION
         ""
        ::= { ontEntry 10 }

    ontAction OBJECT-TYPE
        SYNTAX  INTEGER {
            idle(0),
            rebootOnt(1),
            checkUpgardeFW(2),
            upgradingFW(3),
            delAllConfig(4),
            downloadFile(5),
            uploadFile(6),
            switchImageRule(7),
            clearUpgradeStatus(8),
            clearWaitingQueue(9)
        }
        MAX-ACCESS  read-write
        STATUS  current
        DESCRIPTION
               "Setting this MIB with value below to request an action to occur for the ONU.
               1 Reboot the ONU.
               2 Perform a FW version check. If the current version mismatches with planned one, do FW upgrade if possible.
               4 Delete all configuration stored in OLT related to the ONU.
               5 Perform a file transfer. Download a file located in <ontFileTransferFileUri> with user name / password defined in
               <ontFileTransferUserName> and <ontFileTransferPassword> to the ONU and rename it to <ontFileTransferLocalFileName>.
               6 Perform a file transfer. Upload a file <ontFileTransferLocalFileName> from the ONU to destination defined in
               <ontFileTransferFileUri> with user name / password defined in <ontFileTransferUserName> and <ontFileTransferPassword>.
               7 Switch the ONU active/standby image rule and reboot.
               8 Clear the ont FW upgrade status.
               9 Clear the ont from FW upgrade waiting queue.

               This MIB returns following status to a get request.
               0 This ONU is not doing any action above.
               3 The FW upgrading is in progress."
        ::= { ontEntry 11 }

    alarmProfile OBJECT-TYPE
        SYNTAX  DisplayString
        MAX-ACCESS  read-write
        STATUS  current
        DESCRIPTION
         	"apply an alarm profile to configure remote ONT ddmi threshold."
    	  ::= { ontEntry 12 }

		fullBridg OBJECT-TYPE
        SYNTAX  INTEGER {
         		enable(1),
         		disable(2)
        }
        MAX-ACCESS  read-write
        STATUS  current
        DESCRIPTION
                "full-bridge mode"
        ::= { ontEntry 13 }

    antiMacSpoofing OBJECT-TYPE
        SYNTAX  INTEGER {
         		enable(1),
         		disable(2)
        }
        MAX-ACCESS  read-write
        STATUS  current
        DESCRIPTION
                "anti-mac-spoofing active or inactive"
        ::= { ontEntry 14 }

   	description OBJECT-TYPE
        SYNTAX      DisplayString
        MAX-ACCESS  read-write
        STATUS      current
        DESCRIPTION
         	"description"
    	::= { ontEntry 15 }

   	templateDescription OBJECT-TYPE
        SYNTAX      DisplayString
        MAX-ACCESS  read-write
        STATUS      current
        DESCRIPTION
         	"ONT template description"
    	::= { ontEntry 16 }

   	usFecMode OBJECT-TYPE
        SYNTAX      EnabledStatus
        MAX-ACCESS  read-only
        STATUS      current
        DESCRIPTION
         	"enabled/disabled usFec."
    	::= { ontEntry 17 }

    option82DisableDhcp OBJECT-TYPE
        SYNTAX  INTEGER {
         		enable(1),
         		disable(2)
        }
        MAX-ACCESS  read-write
        STATUS  current
        DESCRIPTION
                "Disable DHCP option82"
        ::= { ontEntry 18 }

    option82PassThroughDhcp OBJECT-TYPE
        SYNTAX  INTEGER {
         		enable(1),
         		disable(2)
        }
        MAX-ACCESS  read-write
        STATUS  current
        DESCRIPTION
                "Pass through DHCP packets with option82"
        ::= { ontEntry 19 }

	   option82DisablePppoe OBJECT-TYPE
        SYNTAX  INTEGER {
         		enable(1),
         		disable(2)
        }
        MAX-ACCESS  read-write
        STATUS  current
        DESCRIPTION
                "Disable PPPoe option82"
        ::= { ontEntry 20 }

    option82PassThroughPppoe OBJECT-TYPE
        SYNTAX  INTEGER {
         		enable(1),
         		disable(2)
        }
        MAX-ACCESS  read-write
        STATUS  current
        DESCRIPTION
                "Pass through PPPoe packets with option82"
        ::= { ontEntry 21 }

	ipbinding OBJECT-TYPE
        SYNTAX  EnabledStatus
        MAX-ACCESS  read-write
        STATUS  current
        DESCRIPTION
        	"enabled/disabled ipbinding with this ONT."
        ::= { ontEntry 22 }
		
--  ontBwGroup Table
    ontBwGroupTable OBJECT-TYPE
	SYNTAX      SEQUENCE OF OntBwGroupEntry
    MAX-ACCESS  not-accessible
    STATUS  current
    DESCRIPTION
        ""
    ::= { ontSetup 2 }

    ontBwGroupEntry OBJECT-TYPE
    SYNTAX      OntBwGroupEntry
    MAX-ACCESS  not-accessible
    STATUS	current
    DESCRIPTION
        "An entry in ontBwGroupTable"
    INDEX {
        dot1dBasePort,
        ontNumber,
        ontBwGroupId
    }
    ::= { ontBwGroupTable 1 }

    OntBwGroupEntry ::=
    SEQUENCE {
        ontBwGroupId                INTEGER,
    	ontBwGroupUsbwprofname    DisplayString,
        ontBwGroupDsbwprofname    DisplayString,
        ontBwGroupRowStatus       RowStatus
    }

    ontBwGroupId OBJECT-TYPE
    SYNTAX  INTEGER (1..40)
    MAX-ACCESS  not-accessible
    STATUS  current
    DESCRIPTION
        " Bandwidth group means US T-CONT (Transmission container)and DS BW meter"
    ::= { ontBwGroupEntry 1 }

    ontBwGroupUsbwprofname OBJECT-TYPE
    SYNTAX  DisplayString
    MAX-ACCESS  read-write
    STATUS  current
    DESCRIPTION
        " Upstream bandwidth profile name."
    ::= { ontBwGroupEntry 3 }

    ontBwGroupDsbwprofname OBJECT-TYPE
    SYNTAX  DisplayString
    MAX-ACCESS  read-write
    STATUS  current
    DESCRIPTION
        " Downstream bandwidth profile name."
    ::= { ontBwGroupEntry 4 }

    ontBwGroupRowStatus OBJECT-TYPE
    SYNTAX      RowStatus
    MAX-ACCESS  read-create
    STATUS      current
    DESCRIPTION
        ""
    ::= { ontBwGroupEntry 5 }

--  ONU File Transfer Parameter Table
    ontFileTransferParamTable OBJECT-TYPE
    SYNTAX      SEQUENCE OF OntFileTransferParamEntry
    MAX-ACCESS  not-accessible
    STATUS  current
    DESCRIPTION
        ""
    ::= { ontSetup 3 }

    ontFileTransferParamEntry OBJECT-TYPE
    SYNTAX      OntFileTransferParamEntry
    MAX-ACCESS  not-accessible
    STATUS	current
    DESCRIPTION
        "Entry in ontFileTransferParamTable"
    INDEX {
        dot1dBasePort,
        ontNumber
    }
    ::= { ontFileTransferParamTable 1 }

    OntFileTransferParamEntry ::=
    SEQUENCE {
        ontFileTransferFileUri        OCTET STRING,
        ontFileTransferLocalFileName  OCTET STRING,
    	ontFileTransferUserName       OCTET STRING,
        ontFileTransferPassword       OCTET STRING
    }

    ontFileTransferFileUri OBJECT-TYPE
    SYNTAX  OCTET STRING
    MAX-ACCESS  read-write
    STATUS  current
    DESCRIPTION
        "The URL to be used in file transfer.
        For example: ftp://a.b.c/dir/config.xml"
    ::= { ontFileTransferParamEntry 1 }

    ontFileTransferLocalFileName OBJECT-TYPE
    SYNTAX  OCTET STRING
    MAX-ACCESS  read-write
    STATUS  current
    DESCRIPTION
        "The file name of the target file in the ONU.
        For example: config.xml"
    ::= { ontFileTransferParamEntry 2 }

    ontFileTransferUserName OBJECT-TYPE
    SYNTAX  OCTET STRING
    MAX-ACCESS  read-write
    STATUS  current
    DESCRIPTION
        "The user name to be used for the file transfer."
    ::= { ontFileTransferParamEntry 3 }

    ontFileTransferPassword OBJECT-TYPE
    SYNTAX  OCTET STRING
    MAX-ACCESS  read-write
    STATUS  current
    DESCRIPTION
        "The password to be used for the file transfer."
    ::= { ontFileTransferParamEntry 4 }

--  ontWanConfig Table
    ontWanConfigTable OBJECT-TYPE
	SYNTAX      SEQUENCE OF OntWanConfigEntry
    MAX-ACCESS  not-accessible
    STATUS  current
    DESCRIPTION
        ""
    ::= { ontSetup 4 }

    ontWanConfigEntry OBJECT-TYPE
    SYNTAX      OntWanConfigEntry
    MAX-ACCESS  not-accessible
    STATUS	current
    DESCRIPTION
        "An entry in ontWanConfigTable"
    INDEX {
        dot1dBasePort,
        ontNumber,
        ontWanConfigId
    }
    ::= { ontWanConfigTable 1 }

    OntWanConfigEntry ::=
    SEQUENCE {
        ontWanConfigId           INTEGER,
        ontWanConfigVlan         INTEGER,
        ontWanConfigPriority     INTEGER,
        ontWanConfigNat          INTEGER,
    	ontWanConfigUsername     DisplayString,
        ontWanConfigPassword     DisplayString,
        ontWanConfigRowStatus    RowStatus,

        ontWanConfigConnectionEnable        TruthValue,
        ontWanConfigConnectionType          INTEGER,
        ontWanConfigConnectionServiceType   BITS,
        ontWanConfigConnectionDefault       TruthValue,
        ontWanConfigIpAddress               IpAddress,
        ontWanConfigIpMaskBits              INTEGER,
        ontWanConfigIpGateway               IpAddress,
        ontWanConfigPrimaryDns              IpAddress,
        ontWanConfigSecondaryDns            IpAddress,
        ontWanConfigIpDhcpEnable            TruthValue,
        ontWanConfigBridgePortBinding       BITS,
        ontWanConfigWifiSSIDBinding         BITS,
        ontWanConfigWifi5GSSIDBinding       BITS,
        ontWanConfigMvlan     INTEGER        
    }

    ontWanConfigId OBJECT-TYPE
    SYNTAX  INTEGER (1..8)
    MAX-ACCESS  not-accessible
    STATUS  current
    DESCRIPTION
        " ont wan config wan id"
    ::= { ontWanConfigEntry 1 }

    ontWanConfigVlan OBJECT-TYPE
    SYNTAX  INTEGER (0..4094)
    MAX-ACCESS  read-write
    STATUS  current
    DESCRIPTION
        " ont wan vlan. 0 means disable."
    ::= { ontWanConfigEntry 2 }

	ontWanConfigPriority OBJECT-TYPE
    SYNTAX  INTEGER (0..7)
    MAX-ACCESS  read-write
    STATUS  current
    DESCRIPTION
        " ont wan priority."
    ::= { ontWanConfigEntry 3 }

    ontWanConfigNat OBJECT-TYPE
    SYNTAX  INTEGER {
        disable(0),
        enable(1)
    }
    MAX-ACCESS  read-write
    STATUS  current
    DESCRIPTION
        " ont wan nat config."
    ::= { ontWanConfigEntry 4 }

    ontWanConfigUsername OBJECT-TYPE
    SYNTAX  DisplayString (SIZE (0..50))
    MAX-ACCESS  read-write
    STATUS  current
    DESCRIPTION
        " ont wan config username.
				- ontWanConfigUsername is unique setting
				- modify unique setting in ONT will not influence refTemplate relation
				- modify unique setting in Template will not apply to existing reference ONT"
    ::= { ontWanConfigEntry 5 }

    ontWanConfigPassword OBJECT-TYPE
    SYNTAX  DisplayString (SIZE (0..50))
    MAX-ACCESS  read-write
    STATUS  current
    DESCRIPTION
        " ont wan config password.
				- ontWanConfigUsername is unique setting
				- modify unique setting in ONT will not influence refTemplate relation
				- modify unique setting in Template will not apply to existing reference ONT"
    ::= { ontWanConfigEntry 6 }

    ontWanConfigRowStatus OBJECT-TYPE
    SYNTAX      RowStatus
    MAX-ACCESS  read-create
    STATUS      current
    DESCRIPTION
        ""
    ::= { ontWanConfigEntry 7 }

    ontWanConfigConnectionEnable OBJECT-TYPE
    SYNTAX  TruthValue
    MAX-ACCESS  read-write
    STATUS  current
    DESCRIPTION
        "This attribute indicates the WAN connection for this WAN interface"
    ::= { ontWanConfigEntry 8 }

    ontWanConfigConnectionType OBJECT-TYPE
    SYNTAX  INTEGER {
        ipoe(1),
        pppoe(2),
        bridge(3)
    }
    MAX-ACCESS  read-write
    STATUS  current
    DESCRIPTION
        "This attribute indicates the WAN connection type for this WAN interface."
    ::= { ontWanConfigEntry 9 }

    ontWanConfigConnectionServiceType OBJECT-TYPE
    SYNTAX  BITS{
        data(7),
        voip(6),
        tr069(5),
        iptv(4)
    }
    MAX-ACCESS  read-write
    STATUS  current
    DESCRIPTION
        "This attribute indicates the WAN connection type for this WAN interface."
    ::= { ontWanConfigEntry 10 }

    ontWanConfigConnectionDefault OBJECT-TYPE
    SYNTAX  TruthValue
    MAX-ACCESS  read-write
    STATUS  current
    DESCRIPTION
        "This attribute indicates this is the default WAN interface."
    ::= { ontWanConfigEntry 11 }

    ontWanConfigIpAddress OBJECT-TYPE
    SYNTAX  IpAddress
    MAX-ACCESS  read-write
    STATUS  current
    DESCRIPTION
        "The IP address for the WAN interface.
				- ontWanConfigIpAddress is unique setting
				- modify unique setting in ONT will not influence refTemplate relation
				- modify unique setting in Template will not apply to existing reference ONT"
    ::= { ontWanConfigEntry 12 }

    ontWanConfigIpMaskBits OBJECT-TYPE
    SYNTAX  INTEGER  (0..32)
    MAX-ACCESS  read-write
    STATUS  current
    DESCRIPTION
        "The subnet mask for the WAN interface.
				- ontWanConfigIpMaskBits is unique setting
				- modify unique setting in ONT will not influence refTemplate relation
				- modify unique setting in Template will not apply to existing reference ONT"
    ::= { ontWanConfigEntry 13 }

    ontWanConfigIpGateway OBJECT-TYPE
    SYNTAX  IpAddress
    MAX-ACCESS  read-write
    STATUS  current
    DESCRIPTION
        "The default gateway address used for the WAN interface.
				- ontWanConfigIpGateway is unique setting
				- modify unique setting in ONT will not influence refTemplate relation
				- modify unique setting in Template will not apply to existing reference ONT"
    ::= { ontWanConfigEntry 14 }

    ontWanConfigPrimaryDns OBJECT-TYPE
    SYNTAX  IpAddress
    MAX-ACCESS  read-write
    STATUS  current
    DESCRIPTION
        "The address of the primary DNS server.
				- ontWanConfigPrimaryDns is unique setting
				- modify unique setting in ONT will not influence refTemplate relation
				- modify unique setting in Template will not apply to existing reference ONT"
    ::= { ontWanConfigEntry 15 }

    ontWanConfigSecondaryDns OBJECT-TYPE
    SYNTAX  IpAddress
    MAX-ACCESS  read-write
    STATUS  current
    DESCRIPTION
        "The address of the secondary DNS server.
				- ontWanConfigSecondaryDns is unique setting
				- modify unique setting in ONT will not influence refTemplate relation
				- modify unique setting in Template will not apply to existing reference ONT"
    ::= { ontWanConfigEntry 16 }

    ontWanConfigIpDhcpEnable OBJECT-TYPE
    SYNTAX  TruthValue
    MAX-ACCESS  read-write
    STATUS  current
    DESCRIPTION
        "true: get WAN IP by DHCP automatically for this WAN interface.
		false: ontWanConfigIpAddress and ontWanConfigPrimaryDns should not be 0.0.0.0"
    ::= { ontWanConfigEntry 17 }

    ontWanConfigBridgePortBinding OBJECT-TYPE
    SYNTAX  BITS{
        port1(7),
        port2(6),
        port3(5),
        port4(4)
    }
    MAX-ACCESS  read-write
    STATUS  current
    DESCRIPTION
        "This attribute indicates the WAN Bridge Port Binding for this WAN interface."
    ::= { ontWanConfigEntry 18 }

    ontWanConfigWifiSSIDBinding OBJECT-TYPE
    SYNTAX BITS{
        ssid1(7),
        ssid2(6),
        ssid3(5),
        ssid4(4)
    }
    MAX-ACCESS  read-write
    STATUS  current
    DESCRIPTION
        "This attribute indicates the WAN Bridge 2.4G SSID Binding for this WAN interface"
    ::= { ontWanConfigEntry 19 }

    ontWanConfigWifi5GSSIDBinding OBJECT-TYPE
    SYNTAX BITS{
        ssid1(7),
        ssid2(6),
        ssid3(5),
        ssid4(4)
    }
    MAX-ACCESS  read-write
    STATUS  current
    DESCRIPTION
        "This attribute indicates the WAN Bridge 5G SSID Binding for this WAN interface."
    ::= { ontWanConfigEntry 20 }

    ontWanConfigMvlan OBJECT-TYPE
    SYNTAX  INTEGER (0..4094)
    MAX-ACCESS  read-write
    STATUS  current
    DESCRIPTION
        " ont wan mvlan. Default value is the same as ontWanConfigVlan. 
		  ontWanConfigMvlan will be 0 if ontWanConfigVlan is disable(0). "
    ::= { ontWanConfigEntry 21 }
    

--  ontResetTable Table
    ontResetTable OBJECT-TYPE
	SYNTAX      SEQUENCE OF OntResetEntry
    MAX-ACCESS  not-accessible
    STATUS  current
    DESCRIPTION
        ""
    ::= { ontSetup 5 }

    ontResetEntry OBJECT-TYPE
    SYNTAX      OntResetEntry
    MAX-ACCESS  not-accessible
    STATUS	current
    DESCRIPTION
        "An entry in ontResetTable1102"
    INDEX {
        dot1dBasePort,
        ontNumber
     }
    ::= { ontResetTable 1 }

    OntResetEntry ::=
    SEQUENCE {
        ontResetAction         	  INTEGER,
        ontConfgurationStatus     INTEGER,
        ontTimeOfRestore     	  INTEGER
    }

    ontResetAction OBJECT-TYPE
    SYNTAX  INTEGER (0..1)
    MAX-ACCESS  read-write
    STATUS  current
    DESCRIPTION
        " ont Reset Action,Value 1: Reset to default configuration, 2: Reset to factory default"
    ::= { ontResetEntry 1 }

    ontConfgurationStatus OBJECT-TYPE
    SYNTAX  INTEGER
    MAX-ACCESS  read-write
    STATUS  current
    DESCRIPTION
        " ont Confguration Status.Value 0: In default state"
    ::= { ontResetEntry 2 }

    ontTimeOfRestore OBJECT-TYPE
    SYNTAX  INTEGER
    MAX-ACCESS  read-write
    STATUS  current
    DESCRIPTION
        " Unix time seconds since midnight January 1,1970)."
    ::= { ontResetEntry 3 }

--  ontStormingTable Table
    ontStormingTable OBJECT-TYPE
	SYNTAX      SEQUENCE OF OntStormingEntry
    MAX-ACCESS  not-accessible
    STATUS  current
    DESCRIPTION
        ""
    ::= { ontSetup 6 }

    ontStormingEntry OBJECT-TYPE
    SYNTAX      OntStormingEntry
    MAX-ACCESS  not-accessible
    STATUS	current
    DESCRIPTION
        "An entry in ontStormingTable"
    INDEX {
        dot1dBasePort,
        ontNumber
     }
    ::= { ontStormingTable 1 }

    OntStormingEntry ::=
    SEQUENCE {
        ontStormingThreshold      INTEGER,
        ontStormingLoopGuard		INTEGER,
        ontLoopGuardDetectionTime	INTEGER,
        ontLoopGuardRecoveryTime	INTEGER
    }

    ontStormingThreshold OBJECT-TYPE
    SYNTAX  INTEGER
    MAX-ACCESS  read-write
    STATUS  current
    DESCRIPTION
        "Configure storm control threshold for ONT (0 ~ 65535, 0 is disable)"
    ::= { ontStormingEntry 1 }

    ontStormingLoopGuard OBJECT-TYPE
    SYNTAX  INTEGER{
           disable(0),
           enable(1)
    }
    MAX-ACCESS  read-write
    STATUS  current
    DESCRIPTION
        " enable or disable ont loopguard"
    ::= { ontStormingEntry 2 }

    ontLoopGuardDetectionTime OBJECT-TYPE
    SYNTAX  INTEGER
    MAX-ACCESS  read-write
    STATUS  current
    DESCRIPTION
        "Configure ont loopguard detection time. (1 ~ 60 seconds)"
    ::= { ontStormingEntry 3 }

    ontLoopGuardRecoveryTime OBJECT-TYPE
    SYNTAX  INTEGER
    MAX-ACCESS  read-write
    STATUS  current
    DESCRIPTION
        "Configure ont loopguard recovery time. (30 ~ 3600 seconds)"
    ::= { ontStormingEntry 4 }


--  ontAclService Table
    ontAclServiceTable OBJECT-TYPE
    SYNTAX      SEQUENCE OF OntAclServiceEntry
    MAX-ACCESS  not-accessible
    STATUS  current
    DESCRIPTION
        ""
    ::= { ontSetup 7 }

    ontAclServiceEntry OBJECT-TYPE
    SYNTAX      OntAclServiceEntry
    MAX-ACCESS  not-accessible
    STATUS  current
    DESCRIPTION
        "An entry in ontAclServiceTable"
    INDEX {
        dot1dBasePort,
        ontNumber,
        ontAclRuleId
    }
    ::= { ontAclServiceTable 1 }

    OntAclServiceEntry ::=
    SEQUENCE {
        ontAclRuleId                INTEGER,
        ontAclProfName              DisplayString,
        ontAclServiceRowStatus      RowStatus
    }

    ontAclRuleId OBJECT-TYPE
    SYNTAX  INTEGER (1..16)
    MAX-ACCESS  not-accessible
    STATUS  current
    DESCRIPTION
        "ONT ACL service rule ID."
    ::= { ontAclServiceEntry 1 }

    ontAclProfName OBJECT-TYPE
    SYNTAX  DisplayString
    MAX-ACCESS  read-write
    STATUS  current
    DESCRIPTION
        "ONT ACL profile name."
    ::= { ontAclServiceEntry 2 }

    ontAclServiceRowStatus OBJECT-TYPE
    SYNTAX      RowStatus
    MAX-ACCESS  read-create
    STATUS      current
    DESCRIPTION
        "Row status for ONT ACL service."
    ::= { ontAclServiceEntry 3 }

--  ontServiceControlTable Table
    ontServiceControlTable OBJECT-TYPE
	SYNTAX      SEQUENCE OF OntServiceControlEntry
    MAX-ACCESS  not-accessible
    STATUS  current
    DESCRIPTION
        ""
    ::= { ontSetup 8 }

    ontServiceControlEntry OBJECT-TYPE
    SYNTAX      OntServiceControlEntry
    MAX-ACCESS  not-accessible
    STATUS	current
    DESCRIPTION
        "An entry in ontServiceControlTable"
    INDEX {
        dot1dBasePort,
        ontNumber
     }
    ::= { ontServiceControlTable 1 }

    OntServiceControlEntry ::=
    SEQUENCE {
        ontFtpEnable		BITS,
        ontFtpPort			INTEGER,
        ontHttpEnable		BITS,
        ontHttpPort			INTEGER,
        ontHttpsEnable		BITS,
        ontHttpsPort		INTEGER,
        ontIcmpEnable		BITS,
        ontSnmpEnable		BITS,
        ontSnmpPort			INTEGER,
        ontSshEnable		BITS,
        ontSshPort			INTEGER,
        ontTelnetEnable		BITS,
        ontTelnetPort		INTEGER,
        ontControlService	INTEGER
    }

	ontFtpEnable OBJECT-TYPE
	SYNTAX	BITS {
		LAN(7),
		WAN(6)
	}
	MAX-ACCESS  read-write
	STATUS  current
	DESCRIPTION
		"Enable ONT FTP access via LAN/WAN, default: LAN"
    ::= { ontServiceControlEntry 1 }

	ontFtpPort OBJECT-TYPE
	SYNTAX  INTEGER
	MAX-ACCESS  read-write
	STATUS  current
	DESCRIPTION
		"ONT FTP service port, default: 21"
	::= { ontServiceControlEntry 2 }	
	
	ontHttpEnable OBJECT-TYPE
	SYNTAX	BITS {
		LAN(7),
		WAN(6)
	}
	MAX-ACCESS  read-write
	STATUS  current
	DESCRIPTION
		"Enable ONT HTTP access via LAN/WAN, default: LAN"
    ::= { ontServiceControlEntry 3 }

	ontHttpPort OBJECT-TYPE
	SYNTAX  INTEGER
	MAX-ACCESS  read-write
	STATUS  current
	DESCRIPTION
		"ONT HTTP service port, default: 80"
	::= { ontServiceControlEntry 4 }	

	ontHttpsEnable OBJECT-TYPE
	SYNTAX	BITS {
		LAN(7),
		WAN(6)
	}
	MAX-ACCESS  read-write
	STATUS  current
	DESCRIPTION
		"Enable ONT HTTPS access via LAN/WAN, default: LAN"
    ::= { ontServiceControlEntry 5 }

	ontHttpsPort OBJECT-TYPE
	SYNTAX  INTEGER
	MAX-ACCESS  read-write
	STATUS  current
	DESCRIPTION
		"ONT HTTPS service port, default: 443"
	::= { ontServiceControlEntry 6 }	

	ontIcmpEnable OBJECT-TYPE
	SYNTAX	BITS {
		LAN(7),
		WAN(6)
	}
	MAX-ACCESS  read-write
	STATUS  current
	DESCRIPTION
		"Enable ONT ICMP access via LAN/WAN, default: LAN"
    ::= { ontServiceControlEntry 7 }

	ontSnmpEnable OBJECT-TYPE
	SYNTAX	BITS {
		LAN(7),
		WAN(6)
	}
	MAX-ACCESS  read-write
	STATUS  current
	DESCRIPTION
		"Enable ONT SNMP access via LAN/WAN, default: LAN"
    ::= { ontServiceControlEntry 8 }

	ontSnmpPort OBJECT-TYPE
	SYNTAX  INTEGER
	MAX-ACCESS  read-write
	STATUS  current
	DESCRIPTION
		"ONT SNMP service port, default: 161"
	::= { ontServiceControlEntry 9 }
	
	ontSshEnable OBJECT-TYPE
	SYNTAX	BITS {
		LAN(7),
		WAN(6)
	}
	MAX-ACCESS  read-write
	STATUS  current
	DESCRIPTION
		"Enable ONT SSH access via LAN/WAN, default: LAN"
    ::= { ontServiceControlEntry 10 }

	ontSshPort OBJECT-TYPE
	SYNTAX  INTEGER
	MAX-ACCESS  read-write
	STATUS  current
	DESCRIPTION
		"ONT SSH service port, default: 22"
	::= { ontServiceControlEntry 11 }

	ontTelnetEnable OBJECT-TYPE
	SYNTAX	BITS {
		LAN(7),
		WAN(6)
	}
	MAX-ACCESS  read-write
	STATUS  current
	DESCRIPTION
		"Enable ONT TELNET access via LAN/WAN, default: LAN"
    ::= { ontServiceControlEntry 12 }

	ontTelnetPort OBJECT-TYPE
	SYNTAX  INTEGER
	MAX-ACCESS  read-write
	STATUS  current
	DESCRIPTION
		"ONT Telnet service port, default: 23"
	::= { ontServiceControlEntry 13 }
	
    ontControlService OBJECT-TYPE
    SYNTAX  INTEGER{
           disable(0),
           enable(1)
    }
    MAX-ACCESS  read-write
    STATUS  current
    DESCRIPTION
        "Disable control ONT service control. 
		disable: OLT set the setting under OntServiceControlEntry to default value, and ONT will keep its current setting.
		enable: not writable, enabled if user configures any setting under OntServiceControlEntry."
    ::= { ontServiceControlEntry 14 }
	
	
--  ontLanSetup Table
    ontLanSetupTable OBJECT-TYPE
    SYNTAX      SEQUENCE OF OntLanSetupEntry
    MAX-ACCESS  not-accessible
    STATUS  current
    DESCRIPTION
        ""
    ::= { ontSetup 9 }

    ontLanSetupEntry OBJECT-TYPE
    SYNTAX      OntLanSetupEntry
    MAX-ACCESS  not-accessible
    STATUS  current
    DESCRIPTION
        "An entry in ontLanSetupTable"
    INDEX {
        dot1dBasePort,
        ontNumber,
        ontLanId
    }
    ::= { ontLanSetupTable 1 }

    OntLanSetupEntry ::=
    SEQUENCE {
        ontLanId                     INTEGER,
        ontLanStaticIpAddr           IpAddress,
        ontLanStaticIpMask           IpAddress,
        ontLanDHCPMode               INTEGER,
        ontLanDHCPRelayServerIP      IpAddress,
        ontLanDHCPServerPoolBegin    IpAddress,
        ontLanDHCPServerPoolEnd      IpAddress,
        ontLanSetupRowStatus         RowStatus,
        ontLanSetupDnsType           INTEGER,
        ontLanSetupPrimaryDns        IpAddress,
        ontLanSetupSecondaryDns      IpAddress
    }

    ontLanId OBJECT-TYPE
    SYNTAX  INTEGER (0..8)
    MAX-ACCESS  not-accessible
    STATUS  current
    DESCRIPTION
        "ONT LAN Setup Instance ID in 0-8"
    ::= { ontLanSetupEntry 1 }

	ontLanStaticIpAddr OBJECT-TYPE
	SYNTAX  IpAddress
	MAX-ACCESS  read-write
	STATUS  current
	DESCRIPTION
		"ONT LAN Setup Static IP Address.
		    - ip address in 1.0.0.1-126.255.255.254, 128.0.0.1-223.255.255.254
		    - ip address must be subnet address
		    - ip address must not be subnet broadcast address
		    - default: 0.0.0.0
		"
	::= { ontLanSetupEntry 2 }

	ontLanStaticIpMask OBJECT-TYPE
	SYNTAX  IpAddress
	MAX-ACCESS  read-write
	STATUS  current
	DESCRIPTION
		"ONT LAN Setup Static IP Mask.
		    - ip mask in 128.0.0.0-255.255.255.254
		    - ip mask must be contiguous 1 bits format
		    - ip subnet must be unique in this ont
		    - if dhcp server pool exist
		   	- dhcp server pool must be ip subnet
		        - dhcp server pool must not be static ip subnet broadcast address
		        - dhcp server pool must not be static ip address
		    - default: 0.0.0.0
		"
	::= { ontLanSetupEntry 3 }

    ontLanDHCPMode OBJECT-TYPE
    SYNTAX  INTEGER{
           disable(0),
           server(1),
		   relay(2)
    }
    MAX-ACCESS  read-write
    STATUS  current
    DESCRIPTION
        "ONT LAN Setup DHCP Mode, 
		    disable:
		        DHCP Relay Server IP: must 0.0.0.0
		        DHCP Server Pool Begin: must 0.0.0.0
		        DHCP Server Pool End: must 0.0.0.0
			server:
		        DHCP Relay Server IP: must 0.0.0.0
		        DHCP Server Pool Begin: mandatory
		        DHCP Server Pool End: mandatory
			relay:
		        DHCP Relay Server IP: mandatory
		        DHCP Server Pool Begin: must 0.0.0.0
		        DHCP Server Pool End: must 0.0.0.0			
		"
    ::= { ontLanSetupEntry 4 }

	ontLanDHCPRelayServerIP OBJECT-TYPE
	SYNTAX  IpAddress
	MAX-ACCESS  read-write
	STATUS  current
	DESCRIPTION
		"ONT LAN Setup DHCP Relay Server IP Address.
		    - if relay server ip is not 0.0.0.0
			    - DHCP mode must be relay
				- DHCP Server Pool Begin: must 0.0.0.0
				- DHCP Server Pool End: must 0.0.0.0
		    - relay server ip in 0.0.0.1-223.255.255.255
		    - default: 0.0.0.0
		"
	::= { ontLanSetupEntry 5 }

	ontLanDHCPServerPoolBegin OBJECT-TYPE
	SYNTAX  IpAddress
	MAX-ACCESS  read-write
	STATUS  current
	DESCRIPTION
		"ONT LAN Setup DHCP Server IP Pool Begin IP Address.
		    - if pool begin ip is not 0.0.0.0
			    - DHCP mode must be server
				- DHCP Relay Server IP: must 0.0.0.0
		    - pool begin ip in in 1.0.0.1-126.255.255.254, 128.0.0.1-223.255.255.254
		    - default: 0.0.0.0
		"
	::= { ontLanSetupEntry 6 }

	ontLanDHCPServerPoolEnd OBJECT-TYPE
	SYNTAX  IpAddress
	MAX-ACCESS  read-write
	STATUS  current
	DESCRIPTION
		"ONT LAN Setup DHCP Server IP Pool End IP Address.
		    - dhcp server pool must be unique in this ont
		    - if pool end ip is not 0.0.0.0
			    - DHCP mode must be server
				- DHCP Relay Server IP: must 0.0.0.0
		    - pool end ip in in 1.0.0.1-126.255.255.254, 128.0.0.1-223.255.255.254
		    - pool end ip must greater than pool begin ip
		    - if static ip exist
		      - dhcp server pool must be static ip subnet
		      - dhcp server pool must not be static ip subnet broadcast address
		      - dhcp server pool must not be static ip address
		    - default: 0.0.0.0
		"
	::= { ontLanSetupEntry 7 }

    ontLanSetupRowStatus OBJECT-TYPE
    SYNTAX      RowStatus
    MAX-ACCESS  read-create
    STATUS      current
    DESCRIPTION
        "Row status for ONT Lan Setup."
    ::= { ontLanSetupEntry 8 }
	
    ontLanSetupDnsType OBJECT-TYPE
    SYNTAX  INTEGER{
           proxy(0),
           static(1),
		   isp(2)
    }
    MAX-ACCESS  read-write
    STATUS  current
    DESCRIPTION
        "ONT LAN Setup DNS Type. 
		    - proxy:
		        Primary Dns: must 0.0.0.0
		        Secondary Dns: must 0.0.0.0
			- static:
		        Primary Dns is mandatory
		        Secondary Dns is optional
			- isp:
		        Primary Dns: must 0.0.0.0
		        Secondary Dns: must 0.0.0.0
            - default: proxy            
		"
    ::= { ontLanSetupEntry 9 }

	ontLanSetupPrimaryDns OBJECT-TYPE
	SYNTAX  IpAddress
	MAX-ACCESS  read-write
	STATUS  current
	DESCRIPTION
		"ONT LAN Setup primary DNS server.
		    - DNS ip address in 0.0.0.1-223.255.255.255
		    - default: 0.0.0.0
		"
	::= { ontLanSetupEntry 10 }

	ontLanSetupSecondaryDns OBJECT-TYPE
	SYNTAX  IpAddress
	MAX-ACCESS  read-write
	STATUS  current
	DESCRIPTION
		"ONT LAN Setup secondary DNS server.
		    - DNS ip address in 0.0.0.1-223.255.255.255
		    - default: 0.0.0.0
		"
	::= { ontLanSetupEntry 11 }
	
--  ontAcsServerTable Table
    ontAcsServerTable OBJECT-TYPE
	SYNTAX      SEQUENCE OF OntAcsServerEntry
    MAX-ACCESS  not-accessible
    STATUS  current
    DESCRIPTION
        ""
    ::= { ontSetup 10 }

    ontAcsServerEntry OBJECT-TYPE
    SYNTAX      OntAcsServerEntry
    MAX-ACCESS  not-accessible
    STATUS	current
    DESCRIPTION
        "An entry in ontAcsServerTable"
    INDEX {
        dot1dBasePort,
        ontNumber
     }
    ::= { ontAcsServerTable 1 }

    OntAcsServerEntry ::=
    SEQUENCE {
        ontAcsServerEnable       INTEGER,      
        ontAcsServerUsername       DisplayString,
        ontAcsServerPassword       DisplayString,
        ontAcsServerUrl            DisplayString,
        ontAcsServerInform         INTEGER,
        ontAcsServerInformInterval INTEGER,
        ontAcsServerControl        INTEGER
    }
    ontAcsServerEnable OBJECT-TYPE
    SYNTAX  INTEGER {
        disable(0),
        enable(1)
    }
    MAX-ACCESS  read-write
    STATUS  current
    DESCRIPTION
                    "Enable ontAcsServer,
                    need to be set via multiple variable binding with non-empty
                    ontAcsServerUsername, ontAcsServerPassword and ontAcsServerUrl.
                    Disable ontAcsServer,
                    need to be set via multiple variable binding with empty
                    ontAcsServerUsername, ontAcsServerPassword and ontAcsServerUrl."
    ::= { ontAcsServerEntry 1 }
    ontAcsServerUsername OBJECT-TYPE
    SYNTAX  DisplayString (SIZE (0..50))
    MAX-ACCESS  read-write
    STATUS  current
    DESCRIPTION
        " ont acs-server username."
    ::= { ontAcsServerEntry 2 }
    ontAcsServerPassword OBJECT-TYPE
    SYNTAX  DisplayString (SIZE (0..50))
    MAX-ACCESS  read-write
    STATUS  current
    DESCRIPTION
        " ont acs-server password."
    ::= { ontAcsServerEntry 3 }
    ontAcsServerUrl OBJECT-TYPE
    SYNTAX  DisplayString (SIZE (0..256))
    MAX-ACCESS  read-write
    STATUS  current
    DESCRIPTION
        " ont acs-server url."
    ::= { ontAcsServerEntry 4 }
    ontAcsServerInform OBJECT-TYPE
    SYNTAX  INTEGER {
        disable(0),
        enable(1)
    }
    MAX-ACCESS  read-write
    STATUS  current
    DESCRIPTION
        " Enable periodic inform to acs server."
    ::= { ontAcsServerEntry 5 }
    ontAcsServerInformInterval OBJECT-TYPE
    SYNTAX  INTEGER
    MAX-ACCESS  read-write
    STATUS  current
    DESCRIPTION
        " Configure the periodic inform interval.(10 ~ 1000000) seconds"
    ::= { ontAcsServerEntry 6 }

    ontAcsServerControl OBJECT-TYPE
    SYNTAX  INTEGER {
        disable(0),
        enable(1)
    }
    MAX-ACCESS  read-write
    STATUS  current
    DESCRIPTION
        "Disable control ONT AcsServer. 
		disable: OLT set the setting under ontAcsServerEntry to default value, and ONT will keep its current setting.
		enable: not writable, enabled if user configures any setting under ontAcsServerEntry."
    ::= { ontAcsServerEntry 7 }    

    ontWifiSetup OBJECT IDENTIFIER ::= { ontSetup 11 }
--  ontWifiSetupTable Table
    ontWifiSetupTable OBJECT-TYPE
    SYNTAX      SEQUENCE OF OntWifiSetupEntry
    MAX-ACCESS  not-accessible
    STATUS  current
    DESCRIPTION
        ""
    ::= { ontWifiSetup 1 }

    ontWifiSetupEntry OBJECT-TYPE
    SYNTAX      OntWifiSetupEntry
    MAX-ACCESS  not-accessible
    STATUS	current
    DESCRIPTION
        "An entry in ontWifiSetupTable"
    INDEX {
        dot1dBasePort,
        ontNumber,
        ontWifiSetupWifiId
     }
    ::= { ontWifiSetupTable 1 }

    OntWifiSetupEntry ::=
    SEQUENCE {
        ontWifiSetupWifiId          INTEGER,
        ontWifiSetupWifiEnable      INTEGER,
        ontWifiSetupWifiSSid        DisplayString,
        ontWifiSetupWifiChannel     INTEGER,
        ontWifiSetupWifiBandwidth   INTEGER,
        ontWifiSetupWifiMaxclients  INTEGER,
        ontWifiSetupWifiSecMode     INTEGER,
        ontWifiSetupWifiPassword    DisplayString,
        ontWifiSetupWifiTxpower     INTEGER,
        ontWifiSetupRowStatus       RowStatus
    }
    ontWifiSetupWifiId OBJECT-TYPE
    SYNTAX  INTEGER  (1..4)
    MAX-ACCESS  read-write
    STATUS  current
    DESCRIPTION
        " Configure the 2.4g wifi Id"
    ::= { ontWifiSetupEntry 1 }
    ontWifiSetupWifiEnable OBJECT-TYPE
    SYNTAX  INTEGER {
        disable(0),
        enable_and_broadcast_ssid(1),
        enable_and_not_broadcast_ssid(2)
    }
    MAX-ACCESS  read-write
    STATUS  current
    DESCRIPTION
        " Enable 2.4g wifi the SSID."
    ::= { ontWifiSetupEntry 2 }
    ontWifiSetupWifiSSid OBJECT-TYPE
    SYNTAX  DisplayString (SIZE (0..32))
    MAX-ACCESS  read-write
    STATUS  current
    DESCRIPTION
        " ont 2.4g wifi ssid.
		  default ssid for index 1: ZYXEL1234
		                   index 2: ZYXEL1234guest1
		                   index 3: ZYXEL1234guest2
		                   index 4: ZYXEL1234guest3
				- ontWifiSetupWifiSSid is unique setting
				- modify unique setting in ONT will not influence refTemplate relation
				- modify unique setting in Template will not apply to existing reference ONT"
    ::= { ontWifiSetupEntry 3 }

    ontWifiSetupWifiChannel OBJECT-TYPE
    SYNTAX  INTEGER  (0..13)
    MAX-ACCESS  read-write
    STATUS  current
    DESCRIPTION
        " Configure the 2.4g wifi channel.(0: auto scan,1 ~ 13)"
    ::= { ontWifiSetupEntry 4 }

    ontWifiSetupWifiBandwidth OBJECT-TYPE
    SYNTAX  INTEGER {
        bandwidth_20MHz(1),
        bandwidth_40MHz(2),
        bandwidth_20_40MHz(3)
    }  
    MAX-ACCESS  read-write
    STATUS  current
    DESCRIPTION
        " Configure the 2.4g wifi bandwidth."
    ::= { ontWifiSetupEntry 5 }
    ontWifiSetupWifiMaxclients OBJECT-TYPE 
    SYNTAX  INTEGER  (1..32)
    MAX-ACCESS  read-write
    STATUS  current
    DESCRIPTION
        " Configure the 2.4g wifi max-clients."
    ::= { ontWifiSetupEntry 6 }
    ontWifiSetupWifiSecMode OBJECT-TYPE
    SYNTAX  INTEGER {
        None(1),
        WPA2-PSK(2),
        WEP(3)
    }  
    MAX-ACCESS  read-write
    STATUS  current
    DESCRIPTION
        " Configure the 2.4g wifi security-mode."
    ::= { ontWifiSetupEntry 7 }
    ontWifiSetupWifiPassword OBJECT-TYPE
    SYNTAX  DisplayString
    MAX-ACCESS  read-write
    STATUS  current
    DESCRIPTION
        "ont 2.4g wifi password.
         8-63 ASCII characters or 64 hexadecimal digits(0-9, a-f, A-F)
		  default password for index 1: ZYXEL1ABCD
		                       index 2: ZYXEL2ABCD
		                       index 3: ZYXEL3ABCD
		                       index 4: ZYXEL4ABCD
				- ontWifiSetupWifiPassword is unique setting
				- modify unique setting in ONT will not influence refTemplate relation
				- modify unique setting in Template will not apply to existing reference ONT"
    ::= { ontWifiSetupEntry 8 }
    ontWifiSetupWifiTxpower OBJECT-TYPE
    SYNTAX  INTEGER {
        txpower_20(1),
        txpower_40(2),
        txpower_60(3),
        txpower_80(4),
        txpower_100(5)
    }  
    MAX-ACCESS  read-write
    STATUS  current
    DESCRIPTION
        " Configure the 2.4g wifi txpower."
    ::= { ontWifiSetupEntry 9 }
    ontWifiSetupRowStatus OBJECT-TYPE
    SYNTAX      RowStatus
    MAX-ACCESS  read-create
    STATUS      current
    DESCRIPTION
        ""
    ::= { ontWifiSetupEntry 10 }

--  ont5gWifiSetupTable Table
    ont5gWifiSetupTable OBJECT-TYPE
	SYNTAX      SEQUENCE OF Ont5gWifiSetupEntry
    MAX-ACCESS  not-accessible
    STATUS  current
    DESCRIPTION
        ""
    ::= { ontWifiSetup 2 }

    ont5gWifiSetupEntry OBJECT-TYPE
    SYNTAX      Ont5gWifiSetupEntry
    MAX-ACCESS  not-accessible
    STATUS	current
    DESCRIPTION
        "An entry in ont5gWifiSetupTable"
    INDEX {
        dot1dBasePort,
        ontNumber,
		ont5gWifiSetupWifiId
     }
    ::= { ont5gWifiSetupTable 1 }

    Ont5gWifiSetupEntry ::=
    SEQUENCE {
        ont5gWifiSetupWifiId INTEGER,
        ont5gWifiSetupWifiEnable INTEGER,
        ont5gWifiSetupWifiSSid	DisplayString,
        ont5gWifiSetupWifiChannel INTEGER,
        ont5gWifiSetupWifiBandwidth INTEGER,
        ont5gWifiSetupWifiMaxclients INTEGER,
        ont5gWifiSetupWifiSecMode INTEGER,
        ont5gWifiSetupWifiPassword	DisplayString,
        ont5gWifiSetupWifiTxpower	INTEGER,
        ont5gWifiSetupRowStatus	RowStatus
    }
    ont5gWifiSetupWifiId OBJECT-TYPE
    SYNTAX  INTEGER  (1..4)
    MAX-ACCESS  read-write
    STATUS  current
    DESCRIPTION
        " Configure the 5g wifi Id"
    ::= { ont5gWifiSetupEntry 1 }
    ont5gWifiSetupWifiEnable OBJECT-TYPE
    SYNTAX  INTEGER {
        disable(0),
        enable_and_broadcast_ssid(1),
        enable_and_not_broadcast_ssid(2)
    }
    MAX-ACCESS  read-write
    STATUS  current
    DESCRIPTION
        " Enable 5g wifi the SSID."
    ::= { ont5gWifiSetupEntry 2 }
    ont5gWifiSetupWifiSSid OBJECT-TYPE
    SYNTAX  DisplayString (SIZE (0..32))
    MAX-ACCESS  read-write
    STATUS  current
    DESCRIPTION
        " ont 5g wifi ssid.
		  default ssid for index 1: ZYXEL12345G
		                   index 2: ZYXEL12345Gguest1
		                   index 3: ZYXEL12345Gguest2
		                   index 4: ZYXEL12345Gguest3
				- ont5gWifiSetupWifiSSid is unique setting
				- modify unique setting in ONT will not influence refTemplate relation
				- modify unique setting in Template will not apply to existing reference ONT"
    ::= { ont5gWifiSetupEntry 3 }
	
    ont5gWifiSetupWifiChannel OBJECT-TYPE
    SYNTAX  INTEGER  (0..128)
    MAX-ACCESS  read-write
    STATUS  current
    DESCRIPTION
        " Configure the 5g wifi channel.(0: auto scan, 
                      36, 40, 44, 48, 52, 56, 60, 64, 100, 104, 108,
                              112, 116, 120, 124, 128)"
    ::= { ont5gWifiSetupEntry 4 }
	
    ont5gWifiSetupWifiBandwidth OBJECT-TYPE
    SYNTAX  INTEGER {
        bandwidth_20MHz(1),
        bandwidth_20_40MHz(3),
        bandwidth_20_40_80MHz(4)
    }  
    MAX-ACCESS  read-write
    STATUS  current
    DESCRIPTION
        " Configure the 5g wifi bandwidth."
    ::= { ont5gWifiSetupEntry 5 }
    ont5gWifiSetupWifiMaxclients OBJECT-TYPE 
    SYNTAX  INTEGER  (1..32)
    MAX-ACCESS  read-write
    STATUS  current
    DESCRIPTION
        " Configure the 5g wifi max-clients."
    ::= { ont5gWifiSetupEntry 6 }
    ont5gWifiSetupWifiSecMode OBJECT-TYPE
    SYNTAX  INTEGER {
        None(1),
        WPA2-PSK(2),
        WEP(3)
    }  
    MAX-ACCESS  read-write
    STATUS  current
    DESCRIPTION
        " Configure the 5g wifi security-mode."
    ::= { ont5gWifiSetupEntry 7 }
    ont5gWifiSetupWifiPassword OBJECT-TYPE
    SYNTAX  DisplayString 
    MAX-ACCESS  read-write
    STATUS  current
    DESCRIPTION
        "ont 5g wifi password.
         8-63 ASCII characters or 64 hexadecimal digits(0-9, a-f, A-F)
		  default password for index 1: ZYXEL15GABCD
		                       index 2: ZYXEL25GABCD
		                       index 3: ZYXEL35GABCD
		                       index 4: ZYXEL45GABCD
				- ont5gWifiSetupWifiPassword is unique setting
				- modify unique setting in ONT will not influence refTemplate relation
				- modify unique setting in Template will not apply to existing reference ONT"
    ::= { ont5gWifiSetupEntry 8 }
    ont5gWifiSetupWifiTxpower OBJECT-TYPE
    SYNTAX  INTEGER {
        txpower_20(1),
        txpower_40(2),
        txpower_60(3),
        txpower_80(4),
        txpower_100(5)
    }  
    MAX-ACCESS  read-write
    STATUS  current
    DESCRIPTION
        " Configure the 5g wifi txpower."
    ::= { ont5gWifiSetupEntry 9 }
    ont5gWifiSetupRowStatus OBJECT-TYPE
    SYNTAX      RowStatus
    MAX-ACCESS  read-create
    STATUS      current
    DESCRIPTION
        ""
    ::= { ont5gWifiSetupEntry 10 }

--  ontDmzTable Table
    ontDmzTable OBJECT-TYPE
	SYNTAX      SEQUENCE OF OntDmzEntry
    MAX-ACCESS  not-accessible
    STATUS  current
    DESCRIPTION
        ""
    ::= { ontSetup 12 }

    ontDmzEntry OBJECT-TYPE
    SYNTAX      OntDmzEntry
    MAX-ACCESS  not-accessible
    STATUS	current
    DESCRIPTION
        "An entry in ontDmzTable"
    INDEX {
        dot1dBasePort,
        ontNumber
     }
    ::= { ontDmzTable 1 }

    OntDmzEntry ::=
    SEQUENCE {
        ontDmzIpaddress	IpAddress,
        ontControlDmz	INTEGER
    }
	
	ontDmzIpaddress OBJECT-TYPE
	SYNTAX  IpAddress
	MAX-ACCESS  read-write
	STATUS  current
	DESCRIPTION
		"ONT DMZ server IP. default: 0.0.0.0"
	::= { ontDmzEntry 1 }

    ontControlDmz OBJECT-TYPE
    SYNTAX  INTEGER{
           disable(0),
           enable(1)
    }
    MAX-ACCESS  read-write
    STATUS  current
    DESCRIPTION
        "Disable control ONT DMZ. 
		disable: OLT set ontDmzIpaddress to default value, and ONT will keep its current setting.
		enable: not writable, enabled if user configures ontDmzIpaddress setting."
    ::= { ontDmzEntry 2 }
	
--  ontUPnPTable Table
    ontUpnpTable OBJECT-TYPE
	SYNTAX      SEQUENCE OF OntUpnpEntry
    MAX-ACCESS  not-accessible
    STATUS  current
    DESCRIPTION
        ""
    ::= { ontSetup 13 }

    ontUpnpEntry OBJECT-TYPE
    SYNTAX      OntUpnpEntry
    MAX-ACCESS  not-accessible
    STATUS	current
    DESCRIPTION
        "An entry in ontUpnpTable"
    INDEX {
        dot1dBasePort,
        ontNumber
     }
    ::= { ontUpnpTable 1 }

    OntUpnpEntry ::=
    SEQUENCE {
        ontUpnpEnable	INTEGER,
        ontControlUpnp	INTEGER
    }
	
    ontUpnpEnable OBJECT-TYPE
    SYNTAX  INTEGER{
           disable(0),
           enable(1)
    }
    MAX-ACCESS  read-write
    STATUS  current
    DESCRIPTION
        " enable or disable ONT UPNP, default: disable"
    ::= { ontUpnpEntry 1 }

    ontControlUpnp OBJECT-TYPE
    SYNTAX  INTEGER{
           disable(0),
           enable(1)
    }
    MAX-ACCESS  read-write
    STATUS  current
    DESCRIPTION
        "Disable control ONT UPnP. 
		disable: OLT set ontUpnpEnable to default value, and ONT will keep its current setting.
		enable: not writable, enabled if user configures ontUpnpEnable setting."
    ::= { ontUpnpEntry 2 }
	
--  ontFirewallTable Table
    ontFirewallTable OBJECT-TYPE
	SYNTAX      SEQUENCE OF OntFirewallEntry
    MAX-ACCESS  not-accessible
    STATUS  current
    DESCRIPTION
        ""
    ::= { ontSetup 14 }

    ontFirewallEntry OBJECT-TYPE
    SYNTAX      OntFirewallEntry
    MAX-ACCESS  not-accessible
    STATUS	current
    DESCRIPTION
        "An entry in ontFirewallTable"
    INDEX {
        dot1dBasePort,
        ontNumber
     }
    ::= { ontFirewallTable 1 }

    OntFirewallEntry ::=
    SEQUENCE {
        ontFirewallEnable	BITS,
        ontFirewallLevel	INTEGER,
        ontControlFirewall	INTEGER
    }
	
    ontFirewallEnable OBJECT-TYPE
	SYNTAX	BITS {
		IPv4(7),
		IPv6(6)
	}
    MAX-ACCESS  read-write
    STATUS  current
    DESCRIPTION
        " enable or disable ONT firewall on IPv4/IPv6, default: both IPv4 and IPv6 enable"
    ::= { ontFirewallEntry 1 }

	ontFirewallLevel OBJECT-TYPE
    SYNTAX  INTEGER{
           low(1),
           medium(2), 
		   high(3)
    }
	MAX-ACCESS  read-write
	STATUS  current
	DESCRIPTION
		"set ont firewall level, default: medium"
    ::= { ontFirewallEntry 2 }

    ontControlFirewall OBJECT-TYPE
    SYNTAX  INTEGER{
           disable(0),
           enable(1)
    }
    MAX-ACCESS  read-write
    STATUS  current
    DESCRIPTION
        "Disable control ONT Firewall. 
		disable: OLT set ontFirewallEnable/ontFirewallLevel to default value, and ONT will keep its current setting.
		enable: not writable, enabled if user configures ontFirewallEnable/ontFirewallLevel setting."
    ::= { ontFirewallEntry 3 }
	
--  ontHostIpTable Table
--    ontHostIpTable OBJECT-TYPE
--	SYNTAX      SEQUENCE OF OntHostIpEntry
--    MAX-ACCESS  not-accessible
--    STATUS  current
--    DESCRIPTION
--        ""
--    ::= { ontSetup 15 }

--    ontHostIpEntry OBJECT-TYPE
--    SYNTAX      OntHostIpEntry
--    MAX-ACCESS  not-accessible
--    STATUS	current
--    DESCRIPTION
--        "An entry in ontHostIpTable"
--    INDEX {
--        dot1dBasePort,
--        ontNumber
--     }
--    ::= { ontHostIpTable 1 }

--    OntHostIpEntry ::=
--    SEQUENCE {
--        ontHostIpVlan           INTEGER,
--        ontHostIpType           INTEGER,
--        ontHostIpIpAddress      IpAddress,
--        ontHostIpIpMask         IpAddress,
--        ontHostIpIpGateway      IpAddress,
--        ontHostIpPrimaryDns     IpAddress,
--        ontHostIpSecondaryDns   IpAddress
--    }
--    ontHostIpVlan OBJECT-TYPE
--    SYNTAX  INTEGER (0..4094)
--    MAX-ACCESS  read-write
--    STATUS  current
--    DESCRIPTION
--        "not set: 0
--				- Vlan id in 1-4094
--				- Vlan id must be unique in this ONT"
--    ::= { ontHostIpEntry 1 }
--    ontHostIpType OBJECT-TYPE
--    SYNTAX  INTEGER {
--		static(2),
--		dhcp(3)
--    }
--    MAX-ACCESS  read-write
--    STATUS  current
--    DESCRIPTION
--                    "static: ontHostIpIpAddress and ontHostIpIpMask must be set
--					 dhcp : will clear all ip related setting
--					"
--    ::= { ontHostIpEntry 2 }
--     ontHostIpIpAddress OBJECT-TYPE
--    SYNTAX  IpAddress
--    MAX-ACCESS  read-write
--    STATUS  current
--    DESCRIPTION
--        "The static ip address config for this host instance.
--				- not set: 0.0.0.0
--				- ip address in 1.0.0.0-126.255.255.255, 128.0.0.1-223.255.255.255
--				- ip address must be subnet address
--				- ip address must not be subnet broadcast address"
--    ::= { ontHostIpEntry 3 }

--    ontHostIpIpMask OBJECT-TYPE
--    SYNTAX  IpAddress
--    MAX-ACCESS  read-write
--    STATUS  current
--    DESCRIPTION
--        "The static ip mask config for this host instance.
--				- not set: 0.0.0.0
--				- ip mask in 128.0.0.0-255.255.255.254
--				- ip mask must be contiguous 1 bits format
--				- ip subnet must be unique in this ont"
--    ::= { ontHostIpEntry 4 }

--    ontHostIpIpGateway OBJECT-TYPE
--    SYNTAX  IpAddress
--    MAX-ACCESS  read-write
--    STATUS  current
--    DESCRIPTION
--        "The ip address of gateway for this host instance(optional).
--				- not set: 0.0.0.0
--				- gateway ip address in 0.0.0.1-223.255.255.255"
--    ::= { ontHostIpEntry 5 }

--    ontHostIpPrimaryDns OBJECT-TYPE
--    SYNTAX  IpAddress
--    MAX-ACCESS  read-write
--    STATUS  current
--    DESCRIPTION
--        "The ip address of primary DNS server for this host instance(optional).
--				- not set: 0.0.0.0
--				- DNS ip address in 0.0.0.1-223.255.255.255"
--    ::= { ontHostIpEntry 6 }

--    ontHostIpSecondaryDns OBJECT-TYPE
--    SYNTAX  IpAddress
--    MAX-ACCESS  read-write
--    STATUS  current
--    DESCRIPTION
--        "The ip address of secondary DNS server for this host instance.
--				- not set: 0.0.0.0
--				- DNS ip address in 0.0.0.1-223.255.255.255"
--    ::= { ontHostIpEntry 7 }
	
--  ontFileTable Table
--    ontFileTable OBJECT-TYPE
--	SYNTAX      SEQUENCE OF OntFileEntry
--    MAX-ACCESS  not-accessible
--    STATUS  current
--    DESCRIPTION
--        ""
--    ::= { ontSetup 16 }

--    ontFileEntry OBJECT-TYPE
--    SYNTAX      OntFileEntry
--    MAX-ACCESS  not-accessible
--    STATUS	current
--    DESCRIPTION
--        "An entry in ontFileTable"
--    INDEX {
--        dot1dBasePort,
--        ontNumber
--     }
--    ::= { ontFileTable 1 }

--    OntFileEntry ::=
--    SEQUENCE {
--        ontFileUrl            DisplayString,
--        ontFileFileName       DisplayString,
--        ontFileIpLocalFile      DisplayString,
--        ontFileUserName         DisplayString,
--        ontFilePassword      DisplayString,
--        ontFileRowStatus     RowStatus,
--        ontFileAction        INTEGER
--    }
--    ontFileUrl OBJECT-TYPE
--    SYNTAX  DisplayString (SIZE(0..63))
--    MAX-ACCESS  read-write
--    STATUS  current
--    DESCRIPTION
--        "Configure an URL of a FTP/TFTP server.
--		        - url format: ftp://<host>/
--                              tftp://<host>/"
--    ::= { ontFileEntry 1 }
--    ontFileFileName OBJECT-TYPE
--    SYNTAX  DisplayString (SIZE(0..31))
--    MAX-ACCESS  read-write
--    STATUS  current
--    DESCRIPTION
--       "Configure a file name of a file.
--		        - filename format: [folder/]filename
--				- none: Send an empty file name to ONT and let ONT decide a file name"
--    ::= { ontFileEntry 2 }
--    ontFileIpLocalFile OBJECT-TYPE
--    SYNTAX  DisplayString (SIZE(0..31))
--    MAX-ACCESS  read-write
--    STATUS  current
--    DESCRIPTION
--        "Configure a local file name on the ONT."
--    ::= { ontFileEntry 3 }

--    ontFileUserName OBJECT-TYPE
--    SYNTAX  DisplayString (SIZE(0..31))
--    MAX-ACCESS  read-write
--    STATUS  current
--    DESCRIPTION
--        "Configure an user name on the FTP server."
--    ::= { ontFileEntry 4 }

--    ontFilePassword OBJECT-TYPE
--    SYNTAX  DisplayString (SIZE(0..31))
--    MAX-ACCESS  read-write
--    STATUS  current
--    DESCRIPTION
--        "Configure a password on the FTP server."
--    ::= { ontFileEntry 5 }

--    ontFileRowStatus OBJECT-TYPE
--    SYNTAX  RowStatus
--    MAX-ACCESS  read-create
--    STATUS  current
--    DESCRIPTION
--        "Row status for ONT File."
--    ::= { ontFileEntry 6 }

--    ontFileAction OBJECT-TYPE
--    SYNTAX  INTEGER {
--            idle(0),
--            startDownload(1)
--        }
--    MAX-ACCESS  read-write
--    STATUS  current
--    DESCRIPTION
--        "Action for ONT File."
--    ::= { ontFileEntry 7 }
	
		

	--  gpon remote ontPoeTable
	ontPoeTable OBJECT-TYPE
	SYNTAX      SEQUENCE OF OntPoeEntry
	MAX-ACCESS  not-accessible
	STATUS  current
	DESCRIPTION
	""
	::= { ontSetup 17 }

	ontPoeEntry OBJECT-TYPE
	SYNTAX      OntPoeEntry
	MAX-ACCESS  not-accessible
	STATUS current
	DESCRIPTION
	"An entry in ontPoeTable"
    INDEX {
        dot1dBasePort,
        ontNumber

    }
	::= { ontPoeTable 1 }

	OntPoeEntry ::=
	SEQUENCE {
		ontPoeMode       INTEGER,
		ontPoeManagement           INTEGER,
		ontTotalPowerConsumptionStatus 	INTEGER
	}

	ontPoeMode OBJECT-TYPE
	SYNTAX  INTEGER {
		auto(1),
		manual(2)
	}
	MAX-ACCESS  read-write
	STATUS  current
	DESCRIPTION
	"manual: maximum power setting can be modified under per uniport setting: power priority <priority> max <classx> default: class3
	 auto: maximum power is auto, the setting under per uniport will be ignored.
	"
	::= { ontPoeEntry 1 }

	ontPoeManagement OBJECT-TYPE
	SYNTAX  INTEGER {
		reserved(1),
		consumption(2)
	}
	MAX-ACCESS  read-write
	STATUS  current
	DESCRIPTION
	""
	::= { ontPoeEntry 2 }

	ontTotalPowerConsumptionStatus OBJECT-TYPE
	SYNTAX  INTEGER
	MAX-ACCESS  read-only
	STATUS  current
	DESCRIPTION
	""
	::= { ontPoeEntry 3 }



	--  gpon remote ontRoamingTable
	ontRoamingTable OBJECT-TYPE
	SYNTAX      SEQUENCE OF OntRoamingEntry
	MAX-ACCESS  not-accessible
	STATUS  current
	DESCRIPTION
	""
	::= { ontSetup 18 }

	ontRoamingEntry OBJECT-TYPE
	SYNTAX      OntRoamingEntry
	MAX-ACCESS  not-accessible
	STATUS current
	DESCRIPTION
	"An entry in ontRoamingTable"
    INDEX {
        dot1dBasePort,
        ontNumber
    }
	::= { ontRoamingTable 1 }

	OntRoamingEntry ::=
	SEQUENCE {
		ontRoaming       INTEGER,
		ontRoamingStatus           INTEGER
	}

	ontRoaming OBJECT-TYPE
	SYNTAX  INTEGER
	MAX-ACCESS  read-write
	STATUS  current
	DESCRIPTION
	"AP Steering Setup, 0: Disable; 90~40: RSSI Threshold -90dBm~-40dBm."
	::= { ontRoamingEntry 1 }


	ontRoamingStatus OBJECT-TYPE
	SYNTAX  INTEGER
	MAX-ACCESS  read-only
	STATUS  current
	DESCRIPTION
	""
	::= { ontRoamingEntry 2 }




		
-- *
-- * ontcard Table
-- *
  	ontcardTable OBJECT-TYPE
		SYNTAX      SEQUENCE OF OntcardEntry
        MAX-ACCESS  not-accessible
        STATUS  current
        DESCRIPTION
                      	""
        ::= { remoteOnt 2 }

	ontcardEntry OBJECT-TYPE
        SYNTAX      OntcardEntry
        MAX-ACCESS  not-accessible
        STATUS      current
        DESCRIPTION
        		"An entry in ontcardTable"
        INDEX {
        		dot1dBasePort,
        		ontNumber,
        		ontcard
        }
    	::= { ontcardTable 1 }

	OntcardEntry ::=
        SEQUENCE {
            ontcard		     	      	  INTEGER,
            ontcardType                      INTEGER,
            numofport                      INTEGER,
            ontcardRowStatus              RowStatus,
            ontcardAction                 INTEGER
   	}

	ontcard OBJECT-TYPE
        SYNTAX      INTEGER
        MAX-ACCESS  not-accessible
        STATUS      current
        DESCRIPTION
         	" ontcard."
    	::= { ontcardEntry 1 }

	ontcardType OBJECT-TYPE
        SYNTAX      INTEGER {
                     vdsl2(35),
                     speed10or100BaseT(24),
                     speed10or100or1000BaseT(47),
                     veip(48),
                     pots(32),
                     video(38),
                     etherOrVeip(49)
        }
        MAX-ACCESS  read-write
        STATUS      current
        DESCRIPTION
         	" cardtype."
    	::= { ontcardEntry 2 }

     numofport OBJECT-TYPE
        SYNTAX      INTEGER
        MAX-ACCESS  read-write
        STATUS      current
        DESCRIPTION
         	" numofport."
    	::= { ontcardEntry 3 }

     ontcardRowStatus OBJECT-TYPE
        SYNTAX      RowStatus
        MAX-ACCESS  read-create
        STATUS      current
        DESCRIPTION
         ""
        ::= { ontcardEntry 4 }

     ontcardAction OBJECT-TYPE
         SYNTAX  INTEGER {
             idle(0),
             delAllConfig(1)
         }
         MAX-ACCESS  read-write
         STATUS  current
         DESCRIPTION
                "Delete all configurations relating to ontcard."
         ::= { ontcardEntry 5 }

-- *
-- * ontenet Table
-- *
  	ontenetTable OBJECT-TYPE
		SYNTAX      SEQUENCE OF OntenetEntry
        MAX-ACCESS  not-accessible
		STATUS      current
		DESCRIPTION
	            ""
        ::= { remoteOnt 3 }

	ontenetEntry OBJECT-TYPE
        SYNTAX      OntenetEntry
        MAX-ACCESS  not-accessible
        STATUS      current
        DESCRIPTION
        		"An entry in ontenetTable"
        INDEX {
        		dot1dBasePort,
        		ontNumber,
        		ontcard,
        		ontenetCardPort
        }
    	::= { ontenetTable 1 }

	OntenetEntry ::=
        SEQUENCE {
            ontenetCardPort		     	      INTEGER,
            pmenetEnable                      INTEGER,
            portSpeed                    INTEGER,
            ontenetRowStatus              RowStatus,
            ontenetAction              INTEGER
   	}

	ontenetCardPort OBJECT-TYPE
        SYNTAX      INTEGER
        MAX-ACCESS  not-accessible
        STATUS      current
        DESCRIPTION
         	" ontenetCardPort."
    	::= { ontenetEntry 1 }

   	pmenetEnable OBJECT-TYPE
        SYNTAX      INTEGER {
             disable(0),
             baseOnModelID(1),
			 bit64(2),
			 bit32(3)
         }
        MAX-ACCESS  read-write
        STATUS      current
        DESCRIPTION
         	" pmenetEnable. When set value is baseOnModelId(1), ONT PMG5318 will use 64bit PM counter, other ont will use 32bit"
    	::= { ontenetEntry 2 }

  	portSpeed OBJECT-TYPE
        SYNTAX      INTEGER {
             auto(0),
             speed2500Full(2),
             speed1000Full(3),
             speed100Full(5),
             speed10Full(7)
         }
        MAX-ACCESS  read-write
        STATUS      current
        DESCRIPTION
         	" port-speed."
    	::= { ontenetEntry 3 }

	ontenetRowStatus OBJECT-TYPE
        SYNTAX      RowStatus
        MAX-ACCESS  read-create
        STATUS      current
        DESCRIPTION
         ""
        ::= { ontenetEntry 4 }

     ontenetAction OBJECT-TYPE
         SYNTAX  INTEGER {
             idle(0),
             delAllConfig(1)
         }
         MAX-ACCESS  read-write
         STATUS  current
         DESCRIPTION
                "Delete all configurations relating to ontenet."
         ::= { ontenetEntry 5 }

-- *
-- * ontvdsl Table
-- *
  	ontvdslTable OBJECT-TYPE
		SYNTAX      SEQUENCE OF OntvdslEntry
        MAX-ACCESS  not-accessible
		STATUS      current
		DESCRIPTION
	            ""
        ::= { remoteOnt 4 }

	ontvdslEntry OBJECT-TYPE
        SYNTAX      OntvdslEntry
        MAX-ACCESS  not-accessible
        STATUS      current
        DESCRIPTION
        		"An entry in ontvdslTable"
        INDEX {
        		dot1dBasePort,
        		ontNumber,
        		ontcard,
        		ontvdslCardPort
        }
    	::= { ontvdslTable 1 }

	OntvdslEntry ::=
        SEQUENCE {
            ontvdslCardPort		     	      INTEGER,
            lineTemplate                 DisplayString,
            ontvdslRowStatus              RowStatus,
            ontvdslAction              INTEGER
   	}

	ontvdslCardPort OBJECT-TYPE
        SYNTAX      INTEGER
        MAX-ACCESS  not-accessible
        STATUS      current
        DESCRIPTION
         	" ontvdslCardPort."
    	::= { ontvdslEntry 1 }

 	lineTemplate OBJECT-TYPE
        SYNTAX      DisplayString
        MAX-ACCESS  read-write
        STATUS      current
        DESCRIPTION
         	" line-template."
    	::= { ontvdslEntry 2 }

    ontvdslRowStatus OBJECT-TYPE
        SYNTAX      RowStatus
        MAX-ACCESS  read-create
        STATUS      current
        DESCRIPTION
         ""
        ::= { ontvdslEntry 3 }

     ontvdslAction OBJECT-TYPE
         SYNTAX  INTEGER {
             idle(0),
             delAllConfig(1)
         }
         MAX-ACCESS  read-write
         STATUS  current
         DESCRIPTION
                "Delete all configurations relating to ontvdsl."
         ::= { ontvdslEntry 4 }
-- *
-- * ontuniport Setup
-- *

    	ontuniportSetup OBJECT IDENTIFIER ::= { remoteOnt 5 }

-- 		ontuniportTable
        ontuniportTable OBJECT-TYPE
        SYNTAX	SEQUENCE OF OntuniportEntry
        MAX-ACCESS  not-accessible
        STATUS  current
        DESCRIPTION
                 	""
        ::= { ontuniportSetup 1 }

		ontuniportEntry OBJECT-TYPE
        SYNTAX	OntuniportEntry
        MAX-ACCESS	not-accessible
        STATUS	current
        DESCRIPTION    	"An entry in ontuniportTable."
        INDEX          	{
        		dot1dBasePort,
        		ontNumber,
        		ontcard,
        		uniPort }
        ::= { ontuniportTable 1 }

        OntuniportEntry ::=
           SEQUENCE {
        	uniPort						INTEGER,
        	uniPortRowStatus      RowStatus,
        	uniPortAction              INTEGER,
        	uniportMacLimit              INTEGER
    }

        uniPort	 OBJECT-TYPE
        SYNTAX  INTEGER
        MAX-ACCESS  read-only
        STATUS  current
        DESCRIPTION
            "uniport"
        ::= { ontuniportEntry 1 }

        uniPortRowStatus OBJECT-TYPE
        SYNTAX      RowStatus
        MAX-ACCESS  read-create
        STATUS      current
        DESCRIPTION
            ""
        ::= { ontuniportEntry 2 }

        uniPortAction OBJECT-TYPE
        SYNTAX  INTEGER {
            idle(0),
            delAllConfig(1)
        }
        MAX-ACCESS  read-write
        STATUS      current
        DESCRIPTION
            "Delete all configurations relating to uniport."
        ::= { ontuniportEntry 3 }

        uniportMacLimit OBJECT-TYPE
        SYNTAX  INTEGER {
        		inactive(0)
       	}
        MAX-ACCESS  read-write
        STATUS  current
        DESCRIPTION
         	"maximum number of mac addresses can be learned per uniport. Zero value means mac-limit is inactive and no mac-address limitation."
    		::= { ontuniportEntry 4 }

--      uniportIgmpchannelTable
        uniportIgmpchannelTable OBJECT-TYPE
        SYNTAX  SEQUENCE OF UniportIgmpchannelEntry
        MAX-ACCESS  not-accessible
        STATUS  current
        DESCRIPTION
            ""
        ::= { ontuniportSetup 2 }

        uniportIgmpchannelEntry OBJECT-TYPE
        SYNTAX  UniportIgmpchannelEntry
        MAX-ACCESS  not-accessible
        STATUS  current
        DESCRIPTION
            "An entry in igmpchannelTable."
        INDEX {
            dot1dBasePort,
            ontNumber,
            ontcard,
            uniPort,
            uniportIgmpchannelUniSvid,
            uniportIgmpchannelUniCvid
        }
        ::= { uniportIgmpchannelTable 1 }

        UniportIgmpchannelEntry ::=
        SEQUENCE {
            uniportIgmpchannelUniSvid        INTEGER,
            uniportIgmpchannelUniCvid        INTEGER,
            uniportIgmpchannelVersion        INTEGER,
            uniportIgmpchannelMaxgroup       INTEGER,
            uniportIgmpchannelMaxmsg         INTEGER,
            uniportIgmpchannelSignaling      INTEGER,
            uniportIgmpchannelPreviewpkg     DisplayString,
            uniportIgmpchannelFullviewpkg    DisplayString,
--            uniportIgmpchannelTrafficRxTag   INTEGER,
            uniportIgmpchannelRowStatus      RowStatus,
            uniportIgmpchannelTrafficTxTag   INTEGER,
            uniportIgmpchannelCacProf        DisplayString,
            uniportIgmpchannelTrafficTxTagRepVid   INTEGER
        }

        uniportIgmpchannelUniSvid OBJECT-TYPE
        SYNTAX  INTEGER (1..4096)
        MAX-ACCESS  read-only
        STATUS  current
        DESCRIPTION
            "uni-svid"
        ::= { uniportIgmpchannelEntry 1 }

        uniportIgmpchannelUniCvid OBJECT-TYPE
        SYNTAX  INTEGER (1..4094)
        MAX-ACCESS  read-only
        STATUS  current
        DESCRIPTION
            "uni-cvid"
        ::= { uniportIgmpchannelEntry 2 }

        uniportIgmpchannelVersion OBJECT-TYPE
        SYNTAX  INTEGER {
            igmpv2(2),
            igmpv3(3)
        }
        MAX-ACCESS  read-write
        STATUS  current
        DESCRIPTION
            "IGMP version"
        ::= { uniportIgmpchannelEntry 3 }

        uniportIgmpchannelMaxgroup OBJECT-TYPE
        SYNTAX  INTEGER (0..512)
        MAX-ACCESS  read-write
        STATUS  current
        DESCRIPTION
            "Maximum number of groups."
        ::= { uniportIgmpchannelEntry 4 }

        uniportIgmpchannelMaxmsg OBJECT-TYPE
        SYNTAX  INTEGER (0..255)
        MAX-ACCESS  read-write
        STATUS  current
        DESCRIPTION
            "Maximum number of reports per second."
        ::= { uniportIgmpchannelEntry 5 }

        uniportIgmpchannelSignaling OBJECT-TYPE
        SYNTAX  INTEGER {
            off(0),
            on(1)
        }
        MAX-ACCESS  read-write
        STATUS  current
        DESCRIPTION
            "IGMP signaling mode."
        ::= { uniportIgmpchannelEntry 6 }

        uniportIgmpchannelPreviewpkg OBJECT-TYPE
        SYNTAX  DisplayString
        MAX-ACCESS  read-write
        STATUS  current
        DESCRIPTION
            "Multicast package members with preview privilege"
        ::= { uniportIgmpchannelEntry 7 }

        uniportIgmpchannelFullviewpkg OBJECT-TYPE
        SYNTAX  DisplayString
        MAX-ACCESS  read-write
        STATUS  current
        DESCRIPTION
            "Multicast package members with fullview privilege"
        ::= { uniportIgmpchannelEntry 8 }

--        uniportIgmpchannelTrafficRxTag OBJECT-TYPE
--        SYNTAX  INTEGER {
--            mvlan(0),
--            univlan(1),
--            untag(2)
--        }
--        MAX-ACCESS  read-write
--        STATUS  current
--        DESCRIPTION
--            "Traffic tag on ANI port."
--        ::= { uniportIgmpchannelEntry 9 }

        uniportIgmpchannelRowStatus OBJECT-TYPE
        SYNTAX      RowStatus
        MAX-ACCESS  read-create
        STATUS      current
        DESCRIPTION
            ""
        ::= { uniportIgmpchannelEntry 10 }

        uniportIgmpchannelTrafficTxTag OBJECT-TYPE
        SYNTAX  INTEGER {
            transparent(3),
            untag(4),
            replace(5)
        }
        MAX-ACCESS  read-write
        STATUS  current
        DESCRIPTION
            "Traffic tag on UNI port. If replace(5) is set, then uniportIgmpchannelTrafficTxTagRepVid will be applied."
        ::= { uniportIgmpchannelEntry 11 }

        uniportIgmpchannelCacProf OBJECT-TYPE
        SYNTAX  DisplayString
        MAX-ACCESS  read-write
        STATUS  current
        DESCRIPTION
            "The maximum multicast bandwidth for this channel"
        ::= { uniportIgmpchannelEntry 12 }

        uniportIgmpchannelTrafficTxTagRepVid OBJECT-TYPE
        SYNTAX  INTEGER (1..4094)
        MAX-ACCESS  read-write
        STATUS  current
        DESCRIPTION
            "Replaced downstream VID. It is applied only when uniportIgmpchannelTrafficTxTag is set to replace(5)."
        ::= { uniportIgmpchannelEntry 13 }

-- 		uniportProtoBasedTable
        uniportProtoBasedTable OBJECT-TYPE
        SYNTAX	SEQUENCE OF UniportProtoBasedEntry
        MAX-ACCESS  not-accessible
        STATUS  current
        DESCRIPTION
                 	""
        ::= { ontuniportSetup 3 }

		uniportProtoBasedEntry OBJECT-TYPE
        SYNTAX	UniportProtoBasedEntry
        MAX-ACCESS	not-accessible
        STATUS	current
        DESCRIPTION    	"An entry in protocol-basedTable."
        INDEX          	{
        		dot1dBasePort,
        		ontNumber,
        		ontcard,
        		uniPort,
        		uniportProtoBasedEtherType }
        ::= { uniportProtoBasedTable 1 }

        UniportProtoBasedEntry ::=
           SEQUENCE {
          uniportProtoBasedEtherType						INTEGER,
        	uniportProtoBasedSvid						INTEGER,
        	uniportProtoBasedCvid						INTEGER,
        	uniportProtoBasedPriority                    INTEGER,
        	uniportProtoBasedRowStatus	RowStatus
    }
        uniportProtoBasedEtherType	 OBJECT-TYPE
        SYNTAX  INTEGER
        MAX-ACCESS  not-accessible
        STATUS  current
        DESCRIPTION
                "ethernet Type"
        ::= { uniportProtoBasedEntry 1 }

        uniportProtoBasedSvid	 OBJECT-TYPE
        SYNTAX  INTEGER
        MAX-ACCESS  read-write
        STATUS  current
        DESCRIPTION
                "SVID"
        ::= { uniportProtoBasedEntry 2 }

        uniportProtoBasedCvid	 OBJECT-TYPE
        SYNTAX  INTEGER
        MAX-ACCESS  read-write
        STATUS  current
        DESCRIPTION
                "CVID"
        ::= { uniportProtoBasedEntry 3 }

        uniportProtoBasedPriority OBJECT-TYPE
        SYNTAX  INTEGER
        MAX-ACCESS  read-write
        STATUS  current
        DESCRIPTION
                "priority"
        ::= { uniportProtoBasedEntry 4 }

    		uniportProtoBasedRowStatus OBJECT-TYPE
        SYNTAX      RowStatus
        MAX-ACCESS  read-create
        STATUS      current
        DESCRIPTION
         ""
        ::= { uniportProtoBasedEntry 5 }

-- 		pvidTable
        uniportPvidTable OBJECT-TYPE
        SYNTAX	SEQUENCE OF UniportPvidEntry
        MAX-ACCESS  not-accessible
        STATUS  current
        DESCRIPTION
                 	""
        ::= { ontuniportSetup 4 }

		uniportPvidEntry OBJECT-TYPE
        SYNTAX	UniportPvidEntry
        MAX-ACCESS	not-accessible
        STATUS	current
        DESCRIPTION    	"An entry in pvidTable."
        INDEX          	{
        		dot1dBasePort,
        		ontNumber,
        		ontcard,
        		uniPort }
        ::= { uniportPvidTable 1 }

        UniportPvidEntry ::=
           SEQUENCE {
        	uniportPvidUniSvid						INTEGER,
        	uniportPvidUniCvid						INTEGER,
        	uniportPvidPriority            INTEGER,
        	uniportPvidRowStatus	RowStatus
    }

        uniportPvidUniSvid	 OBJECT-TYPE
        SYNTAX  INTEGER
        MAX-ACCESS  read-write
        STATUS  current
        DESCRIPTION
                "SVID"
        ::= { uniportPvidEntry 1 }

        uniportPvidUniCvid	 OBJECT-TYPE
        SYNTAX  INTEGER
        MAX-ACCESS  read-write
        STATUS  current
        DESCRIPTION
                "CVID"
        ::= { uniportPvidEntry 2 }

        uniportPvidPriority OBJECT-TYPE
        SYNTAX  INTEGER
        MAX-ACCESS  read-write
        STATUS  current
        DESCRIPTION
                "Pvid priority"
        ::= { uniportPvidEntry 3 }

    		uniportPvidRowStatus OBJECT-TYPE
        SYNTAX      RowStatus
        MAX-ACCESS  read-create
        STATUS      current
        DESCRIPTION
         ""
        ::= { uniportPvidEntry 4 }

-- 		uniportQueueTable
        uniportQueueTable OBJECT-TYPE
        SYNTAX	SEQUENCE OF UniportQueueEntry
        MAX-ACCESS  not-accessible
        STATUS  current
        DESCRIPTION
                 	""
        ::= { ontuniportSetup 5 }

		uniportQueueEntry OBJECT-TYPE
        SYNTAX	UniportQueueEntry
        MAX-ACCESS	not-accessible
        STATUS	current
        DESCRIPTION    	"An entry in queueTable."
        INDEX          	{
        		dot1dBasePort,
        		ontNumber,
        		ontcard,
        		uniPort,
        		uniportQueueTc }
        ::= { uniportQueueTable 1 }

        UniportQueueEntry ::=
           SEQUENCE {
           	uniportQueueTc		INTEGER,
        	uniportQueuePriority	INTEGER,
        	uniportQueueWeight	INTEGER,
        	uniportQueueUsbwprofname	DisplayString,
            uniportQueueDsbwprofname	DisplayString,
            uniportQueueDsoption	INTEGER,
        	uniportQueueUsbwsharegroupid	INTEGER,
        	uniportQueueRowStatus	RowStatus,
        	uniportQueueDsbwsharegroupid	INTEGER
    	}

        uniportQueueTc	 OBJECT-TYPE
        SYNTAX  INTEGER {
        		tc0(0),
        		tc1(1),
        		tc2(2),
        		tc3(3),
        		tc4(4),
        		tc5(5),
        		tc6(6),
        		tc7(7),
        		tcNull(8)
        }
        MAX-ACCESS  not-accessible
        STATUS  current
        DESCRIPTION
                "traffic class 0-7"
        ::= { uniportQueueEntry 1 }

        uniportQueuePriority OBJECT-TYPE
        SYNTAX  INTEGER {
        		priority0(0),
        		priority1(1),
        		priority2(2),
        		priority3(3),
        		priority4(4),
        		priority5(5),
        		priority6(6),
        		priority7(7)
        }
        MAX-ACCESS  read-write
        STATUS  current
        DESCRIPTION
                "Usqueue priority 0-7"
        ::= { uniportQueueEntry 2 }

        uniportQueueWeight OBJECT-TYPE
        SYNTAX  INTEGER
        MAX-ACCESS  read-write
        STATUS  current
        DESCRIPTION
                "Usqueue weight 0-255"
        ::= { uniportQueueEntry 3 }

        uniportQueueUsbwprofname OBJECT-TYPE
        SYNTAX  DisplayString
        MAX-ACCESS  read-write
        STATUS  current
        DESCRIPTION
                "usbwprof name"
        ::= { uniportQueueEntry 4 }

        uniportQueueDsbwprofname OBJECT-TYPE
        SYNTAX  DisplayString
        MAX-ACCESS  read-write
        STATUS  current
        DESCRIPTION
                "dsbwprof name"
        ::= { uniportQueueEntry 5 }

        uniportQueueDsoption OBJECT-TYPE
        SYNTAX  INTEGER {
        		olt(0),
        		ont(1)
        }
        MAX-ACCESS  read-write
        STATUS  current
        DESCRIPTION
                "queue ds option,do metering at OLT side or ONT side"
        ::= { uniportQueueEntry 6 }

        uniportQueueUsbwsharegroupid  OBJECT-TYPE
        SYNTAX  INTEGER
        MAX-ACCESS  read-write
        STATUS  current
        DESCRIPTION
                "upstream bandwidth group id"
        ::= { uniportQueueEntry 7 }

        uniportQueueRowStatus OBJECT-TYPE
        SYNTAX      RowStatus
        MAX-ACCESS  read-create
        STATUS      current
        DESCRIPTION
         ""
        ::= { uniportQueueEntry 8 }

        uniportQueueDsbwsharegroupid  OBJECT-TYPE
        SYNTAX  INTEGER
        MAX-ACCESS  read-write
        STATUS  current
        DESCRIPTION
                "downstream bandwidth group id"
        ::= { uniportQueueEntry 9 }


-- 		uniportVlanTable
        uniportVlanTable OBJECT-TYPE
        SYNTAX	SEQUENCE OF UniportVlanEntry
        MAX-ACCESS  not-accessible
        STATUS  current
        DESCRIPTION
                 	""
        ::= { ontuniportSetup 6 }

		uniportVlanEntry OBJECT-TYPE
        SYNTAX	UniportVlanEntry
        MAX-ACCESS	not-accessible
        STATUS	current
        DESCRIPTION    	"An entry in uniportVlanTable."
        INDEX          	{
        		dot1dBasePort,
        		ontNumber,
        		ontcard,
        		uniPort,
        		uniportVlanUniSvid,
        		uniportVlanUniCvid }
        ::= { uniportVlanTable 1 }

        UniportVlanEntry ::=
           SEQUENCE {
        	uniportVlanUniSvid				   	INTEGER,
        	uniportVlanUniCvid				   	INTEGER,
        	uniportVlanNetworkSvid                	INTEGER,
        	uniportVlanNetworkSpri                	INTEGER,
        	uniportVlanNetworkCvid                	INTEGER,
        	uniportVlanIngProf                	DisplayString,
        	uniportVlanGemPort                	INTEGER,
        	uniportVlanTr156                	INTEGER,
        	uniportVlanTxTag                	INTEGER,
        	uniportVlanPbitProf                	DisplayString,
        	uniportVlanDscpToPbit                	INTEGER,
        	uniportVlanAesEncrypt                	INTEGER,
        	uniportVlanRowStatus	RowStatus,
        	uniportVlanSharePriority                	INTEGER,
        	uniportVlanMacNum                	INTEGER,
        	uniportVlanRoute                	INTEGER
    }

        uniportVlanUniSvid	 OBJECT-TYPE
        SYNTAX  INTEGER
        MAX-ACCESS  not-accessible
        STATUS  current
        DESCRIPTION
                "uni-svid"
        ::= { uniportVlanEntry 1 }

        uniportVlanUniCvid	 OBJECT-TYPE
        SYNTAX  INTEGER
        MAX-ACCESS  not-accessible
        STATUS  current
        DESCRIPTION
                "uni-cvid"
        ::= { uniportVlanEntry 2 }

        uniportVlanNetworkSvid OBJECT-TYPE
        SYNTAX  INTEGER
        MAX-ACCESS  read-write
        STATUS  current
        DESCRIPTION
                "network-svid"
        ::= { uniportVlanEntry 3 }

        uniportVlanNetworkSpri OBJECT-TYPE
        SYNTAX  INTEGER {
        		priority0(0),
        		priority1(1),
        		priority2(2),
        		priority3(3),
        		priority4(4),
        		priority5(5),
        		priority6(6),
        		priority7(7),
        		priorityNull(8)
        }
        MAX-ACCESS  read-write
        STATUS  current
        DESCRIPTION
                "network-spri"
        ::= { uniportVlanEntry 4 }

        uniportVlanNetworkCvid OBJECT-TYPE
        SYNTAX  INTEGER
        MAX-ACCESS  read-write
        STATUS  current
        DESCRIPTION
                "network-cvid"
        ::= { uniportVlanEntry 5 }

        uniportVlanIngProf OBJECT-TYPE
        SYNTAX  DisplayString
        MAX-ACCESS  read-write
        STATUS  current
        DESCRIPTION
                "ingProf"
        ::= { uniportVlanEntry 6 }

        uniportVlanGemPort OBJECT-TYPE
        SYNTAX  INTEGER
        MAX-ACCESS  read-write
        STATUS  current
        DESCRIPTION
                "gemPort"
        ::= { uniportVlanEntry 7 }

        uniportVlanTr156 OBJECT-TYPE
        SYNTAX  INTEGER {
         		enable(1),
         		disable(2)
        }
        MAX-ACCESS  read-write
        STATUS  current
        DESCRIPTION
                "tr156"
        ::= { uniportVlanEntry 8 }

        uniportVlanTxTag OBJECT-TYPE
        SYNTAX  INTEGER {
         		untag(1),
         		tag(2),
         		pritag(3)
        }
        MAX-ACCESS  read-write
        STATUS  current
        DESCRIPTION
                "txtag"
        ::= { uniportVlanEntry 9 }

        uniportVlanPbitProf OBJECT-TYPE
        SYNTAX  DisplayString
        MAX-ACCESS  read-write
        STATUS  current
        DESCRIPTION
                "pbit profile"
        ::= { uniportVlanEntry 10 }

        uniportVlanDscpToPbit OBJECT-TYPE
        SYNTAX  INTEGER {
         		active(1),
         		inactive(2)
        }
        MAX-ACCESS  read-write
        STATUS  current
        DESCRIPTION
                "dscp to pbit active/inactive"
        ::= { uniportVlanEntry 11 }

        uniportVlanAesEncrypt OBJECT-TYPE
        SYNTAX  INTEGER {
         		enable(1),
         		disable(2)
        }
        MAX-ACCESS  read-write
        STATUS  current
        DESCRIPTION
                "AES encryption"
        ::= { uniportVlanEntry 12 }

    		uniportVlanRowStatus OBJECT-TYPE
        SYNTAX      RowStatus
        MAX-ACCESS  read-create
        STATUS      current
        DESCRIPTION
         ""
        ::= { uniportVlanEntry 13 }

        uniportVlanSharePriority OBJECT-TYPE
        SYNTAX  INTEGER {
        		priority0(0),
        		priority1(1),
        		priority2(2),
        		priority3(3),
        		priority4(4),
        		priority5(5),
        		priority6(6),
        		priority7(7),
        		off(8)
        }
        MAX-ACCESS  read-write
        STATUS  current
        DESCRIPTION
                "Share priority for macro meter"
        ::= { uniportVlanEntry 14 }

        uniportVlanMacNum OBJECT-TYPE
        SYNTAX  INTEGER
        MAX-ACCESS  read-write
        STATUS  current
        DESCRIPTION
                "Max mac number per flow can do rate limit"
        ::= { uniportVlanEntry 15 }

        uniportVlanRoute OBJECT-TYPE
        SYNTAX  INTEGER {
         		off(0),
         		on(1)
        }
        MAX-ACCESS  read-write
        STATUS  current
        DESCRIPTION
                "L3 route ds meter on/off"
        ::= { uniportVlanEntry 16 }

-- 		uniportVoipTable
        uniportVoipTable OBJECT-TYPE
        SYNTAX	SEQUENCE OF UniportVoipEntry
        MAX-ACCESS  not-accessible
        STATUS  current
        DESCRIPTION
                 	""
        ::= { ontuniportSetup 7 }

		uniportVoipEntry OBJECT-TYPE
        SYNTAX	UniportVoipEntry
        MAX-ACCESS	not-accessible
        STATUS	current
        DESCRIPTION    	"An entry in uniportVoipTable."
        INDEX          	{
        		dot1dBasePort,
        		ontNumber,
        		ontcard,
        		uniPort }
        ::= { uniportVoipTable 1 }

        UniportVoipEntry ::=
           SEQUENCE {
        	uniportVoipMode            INTEGER,
        	uniportVoipUniCvid         INTEGER,
        	uniportVoipCommProfName    DisplayString,
        	uniportVoipSipProfName     DisplayString,
        	uniportVoipUsername        DisplayString,
        	uniportVoipPassword        DisplayString,
        	uniportVoipDialPlanName    DisplayString,
        	uniportVoipAor             DisplayString,
        	uniportVoipDispName        DisplayString,
        	uniportVoipVmailUri        DisplayString,
        	uniportVoipVmailExtimer    INTEGER,
        	uniportVoipReleaseTimer    INTEGER,
        	uniportVoipRohTimer        INTEGER,
        	uniportVoipRowStatus       RowStatus
    }

        uniportVoipMode	 OBJECT-TYPE
        SYNTAX  INTEGER
        MAX-ACCESS  read-write
        STATUS  current
        DESCRIPTION
                "set ONT Voip mode."
        ::= { uniportVoipEntry 1 }

        uniportVoipUniCvid	 OBJECT-TYPE
        SYNTAX  INTEGER
        MAX-ACCESS  read-write
        STATUS  current
        DESCRIPTION
                "set ONT Voip vlan(1 ~ 4094)."
        ::= { uniportVoipEntry 2 }

        uniportVoipCommProfName OBJECT-TYPE
        SYNTAX  DisplayString
        MAX-ACCESS  read-write
        STATUS  current
        DESCRIPTION
                "set ONT Voip common profile name(1 ~ 15 characters)."
        ::= { uniportVoipEntry 3 }

        uniportVoipSipProfName OBJECT-TYPE
        SYNTAX  DisplayString
        MAX-ACCESS  read-write
        STATUS  current
        DESCRIPTION
                "set ONT Voip sip profile name(1 ~ 15 characters)."
        ::= { uniportVoipEntry 4 }

        uniportVoipUsername OBJECT-TYPE
        SYNTAX  DisplayString
        MAX-ACCESS  read-write
        STATUS  current
        DESCRIPTION
                "set ONT Voip user name(1 ~ 49 characters).
				- uniportVoipUsername is unique setting
				- modify unique setting in ONT will not influence refTemplate relation
				- modify unique setting in Template will not apply to existing reference ONT"
        ::= { uniportVoipEntry 5 }

        uniportVoipPassword OBJECT-TYPE
        SYNTAX  DisplayString
        MAX-ACCESS  read-write
        STATUS  current
        DESCRIPTION
                "set ONT Voip password(1 ~ 25 characters).
				- uniportVoipPassword is unique setting
				- modify unique setting in ONT will not influence refTemplate relation
				- modify unique setting in Template will not apply to existing reference ONT"
        ::= { uniportVoipEntry 6 }

        uniportVoipDialPlanName OBJECT-TYPE
        SYNTAX  DisplayString
        MAX-ACCESS  read-write
        STATUS  current
        DESCRIPTION
                "set ONT Voip network dial plan name(1 ~ 15 characters)"
        ::= { uniportVoipEntry 7 }

        uniportVoipAor OBJECT-TYPE
        SYNTAX  DisplayString
        MAX-ACCESS  read-write
        STATUS  current
        DESCRIPTION
                "set ONT Voip user part AOR(1 ~ 63 characters)."
        ::= { uniportVoipEntry 8 }

        uniportVoipDispName OBJECT-TYPE
        SYNTAX  DisplayString
        MAX-ACCESS  read-write
        STATUS  current
        DESCRIPTION
                "set ONT Voip sip display name(1 ~ 25 characters)."
        ::= { uniportVoipEntry 9 }

        uniportVoipVmailUri OBJECT-TYPE
        SYNTAX  DisplayString
        MAX-ACCESS  read-write
        STATUS  current
        DESCRIPTION
                "set ONT Voip voicemail server SIP URI(1 ~ 63 characters)"
        ::= { uniportVoipEntry 10 }

        uniportVoipVmailExtimer OBJECT-TYPE
        SYNTAX  INTEGER
        MAX-ACCESS  read-write
        STATUS  current
        DESCRIPTION
                "set ONT Voip voice subscription expiration time(0 ~ 3600)"
        ::= { uniportVoipEntry 11 }

        uniportVoipReleaseTimer OBJECT-TYPE
        SYNTAX  INTEGER
        MAX-ACCESS  read-write
        STATUS  current
        DESCRIPTION
                "set ONT Voip release timer( 0 ~ 30)"
        ::= { uniportVoipEntry 12 }

        uniportVoipRohTimer OBJECT-TYPE
        SYNTAX  INTEGER
        MAX-ACCESS  read-write
        STATUS  current
        DESCRIPTION
                "set ONT Voip ROH timer( 0 ~ 30)"
        ::= { uniportVoipEntry 13 }


    	uniportVoipRowStatus OBJECT-TYPE
        SYNTAX      RowStatus
        MAX-ACCESS  read-create
        STATUS      current
        DESCRIPTION
         ""
        ::= { uniportVoipEntry 14 }

--      uniportIpbindingTable
	uniportIpbindingTable OBJECT-TYPE
	SYNTAX  SEQUENCE OF UniportIpbindingEntry
	MAX-ACCESS  not-accessible
	STATUS  current
	DESCRIPTION
		""
	::= { ontuniportSetup 8 }

        uniportIpbindingEntry OBJECT-TYPE
        SYNTAX  UniportIpbindingEntry
        MAX-ACCESS  not-accessible
        STATUS  current
        DESCRIPTION
            "An entry in IpbindingTable."
        INDEX {
            dot1dBasePort,
            ontNumber,
            ontcard,
            uniPort,
            uniportIpbindingUniSvid,
            uniportIpbindingUniCvid,
			uniportIpbindingSubnet,
			uniportIpbindingMaskBits
        }
        ::= { uniportIpbindingTable 1 }

        UniportIpbindingEntry ::=
        SEQUENCE {
            uniportIpbindingUniSvid		INTEGER,
            uniportIpbindingUniCvid		INTEGER,
        	uniportIpbindingSubnet		IpAddress,
        	uniportIpbindingMaskBits	INTEGER,
			uniportIpbindingEnabled		EnabledStatus,
            uniportIpbindingRowStatus	RowStatus
        }

        uniportIpbindingUniSvid OBJECT-TYPE
        SYNTAX  INTEGER (1..4096)
        MAX-ACCESS  not-accessible
        STATUS  current
        DESCRIPTION
            "uni-svid"
        ::= { uniportIpbindingEntry 1 }

        uniportIpbindingUniCvid OBJECT-TYPE
        SYNTAX  INTEGER (1..4094)
        MAX-ACCESS  not-accessible
        STATUS  current
        DESCRIPTION
            "uni-cvid"
        ::= { uniportIpbindingEntry 2 }

        uniportIpbindingSubnet OBJECT-TYPE
        SYNTAX  IpAddress
        MAX-ACCESS  not-accessible
        STATUS  current
        DESCRIPTION
                     	"The ip subnet address of the ipbinding entry."
        ::= { uniportIpbindingEntry 3 }

        uniportIpbindingMaskBits OBJECT-TYPE
        SYNTAX  INTEGER
        MAX-ACCESS  not-accessible
        STATUS  current
        DESCRIPTION
                     	"The ip subnet mask bits(1-32) of the ipbinding entry."
        ::= { uniportIpbindingEntry 4 }

		uniportIpbindingEnabled OBJECT-TYPE
			SYNTAX  EnabledStatus
			MAX-ACCESS  read-only
			STATUS  current
			DESCRIPTION
				"show if ipbinding enabled with this ONT."
			::= { uniportIpbindingEntry 5 }
		
        uniportIpbindingRowStatus OBJECT-TYPE
        SYNTAX      RowStatus
        MAX-ACCESS  read-create
        STATUS      current
        DESCRIPTION
            ""
        ::= { uniportIpbindingEntry 6 }
		
	--  gpon remote ontuniportSetup uniportOntPoeTable
	uniportOntPoeTable OBJECT-TYPE
		SYNTAX SEQUENCE OF UniportOntPoeEntry
		MAX-ACCESS not-accessible
		STATUS current
		DESCRIPTION
				""
		::= { ontuniportSetup 9 }

	uniportOntPoeEntry OBJECT-TYPE
		SYNTAX UniportOntPoeEntry
		MAX-ACCESS not-accessible
		STATUS current
		DESCRIPTION "An entry in uniportOntPoeTable."
		INDEX {
				ifIndex,
				ontNumber,
				ontcard,
				uniPort }
		::= { uniportOntPoeTable 1 }

		UniportOntPoeEntry ::=
			SEQUENCE {
			uniportOntPoeActive							INTEGER,
			uniportOntPoePriority						INTEGER,
			uniportOntPoePowerClassControl				INTEGER,
			uniportOntPoePowerClassificationStatus		INTEGER,
			uniportOntPoePowerDetectStatus				INTEGER
		}

		uniportOntPoeActive OBJECT-TYPE
			SYNTAX  INTEGER {
				enable(1),
				disable(2)
			}
			MAX-ACCESS  read-write
			STATUS  current
			DESCRIPTION
			"enable/disable power over the Ethernet port"
			::= { uniportOntPoeEntry 1 }

		uniportOntPoePriority OBJECT-TYPE
			SYNTAX  INTEGER {
				low(1),
				high(2),
				critical(3)
			}
			MAX-ACCESS  read-write
			STATUS  current
			DESCRIPTION
			"power management priority"
			::= { uniportOntPoeEntry 2 }

		uniportOntPoePowerClassControl OBJECT-TYPE
			SYNTAX  INTEGER {
				null(0),
				class1(2),
				class2(3),
				class3(4),
				class4(5)
			}
			MAX-ACCESS  read-write
			STATUS  current
			DESCRIPTION
			""
			::= { uniportOntPoeEntry 3 }


		uniportOntPoePowerClassificationStatus OBJECT-TYPE
			SYNTAX  INTEGER {
				notsupport(0),
				class0(1),
				class1(2),
				class2(3),
				class3(4),
				class4(5)
			}
			MAX-ACCESS  read-only
			STATUS  current
			DESCRIPTION
			""
			::= { uniportOntPoeEntry 4 }

		uniportOntPoePowerDetectStatus OBJECT-TYPE
			SYNTAX  INTEGER {
				disable(0),
				searching(1),
				delivering(2),
				test(3),
				fault(4),
				implement_fault(5)
			}
			MAX-ACCESS  read-only
			STATUS  current
			DESCRIPTION
			""
			::= { uniportOntPoeEntry 5 }
		
-- *
-- * ontcfm Table
-- *

    	ontOmciCfmTable OBJECT IDENTIFIER ::= { remoteOnt 6 }

-- 		omciCfmMdTable
        omciCfmMdTable OBJECT-TYPE
        SYNTAX	SEQUENCE OF OmciCfmMdEntry
        MAX-ACCESS  not-accessible
        STATUS  current
        DESCRIPTION
                 	""
        ::= { ontOmciCfmTable 1 }

		omciCfmMdEntry OBJECT-TYPE
        SYNTAX	OmciCfmMdEntry
        MAX-ACCESS	not-accessible
        STATUS	current
        DESCRIPTION    	"An entry in omciCfmMdTable."
        INDEX {
        		ifIndex,
        		ontNumber
        }
        ::= { omciCfmMdTable 1 }

        OmciCfmMdEntry ::=
           SEQUENCE {
        	omciCfmMdIndex		     	      Unsigned32,
          omciCfmMdFormat                      INTEGER,
          omciCfmMdName                    OCTET STRING,
          omciCfmMdLevel                    INTEGER,
          omciCfmMdRowStatus              RowStatus
    }

        omciCfmMdIndex OBJECT-TYPE
        SYNTAX      Unsigned32 (1..4294967295)
        MAX-ACCESS  read-create
        STATUS      current
        DESCRIPTION
         " The index to the Maintenance Domain table."
    	::= { omciCfmMdEntry 1 }

    	  omciCfmMdFormat OBJECT-TYPE
        SYNTAX  INTEGER {
        	none(1),
        	dns(2),
        	mac(3),
        	string(4)
        }
        MAX-ACCESS  read-create
        STATUS      current
        DESCRIPTION
         " The type (and thereby format) of the Maintenance Domain Name."
    	::= { omciCfmMdEntry 2 }

    	  omciCfmMdName OBJECT-TYPE
        SYNTAX  OCTET STRING
        MAX-ACCESS  read-create
        STATUS      current
        DESCRIPTION
         " The Maintenance Domain name. The type/format of this object
           is determined by the value of the omciCfmMdFormat object."
    	::= { omciCfmMdEntry 3 }

    	  omciCfmMdLevel OBJECT-TYPE
        SYNTAX  INTEGER
        MAX-ACCESS  read-create
        STATUS      current
        DESCRIPTION
         " The Maintenance Domain Level."
    	::= { omciCfmMdEntry 4 }

				omciCfmMdRowStatus OBJECT-TYPE
        SYNTAX  RowStatus
        MAX-ACCESS  read-create
        STATUS  current
        DESCRIPTION
                      	""
      ::= {  omciCfmMdEntry 5 }

-- 		omciCfmMaTable
        omciCfmMaTable OBJECT-TYPE
        SYNTAX	SEQUENCE OF OmciCfmMaEntry
        MAX-ACCESS  not-accessible
        STATUS  current
        DESCRIPTION
                 	""
        ::= { ontOmciCfmTable 2 }

		omciCfmMaEntry OBJECT-TYPE
        SYNTAX	OmciCfmMaEntry
        MAX-ACCESS	not-accessible
        STATUS	current
        DESCRIPTION    	"An entry in omciCfmMaTable."
        INDEX {
        		ifIndex,
        		ontNumber
        }
        ::= { omciCfmMaTable 1 }

        OmciCfmMaEntry ::=
           SEQUENCE {
        	omciCfmMaIndex		     	      Unsigned32,
        	omciCfmMaMdIndex		     	      Unsigned32,
          omciCfmMaFormat                      INTEGER,
          omciCfmMaName                    OCTET STRING,
          omciCfmMaCcmInterval                    INTEGER,
          omciCfmMaRowStatus              RowStatus
    }

        omciCfmMaIndex OBJECT-TYPE
        SYNTAX      Unsigned32 (1..4294967295)
        MAX-ACCESS  read-create
        STATUS      current
        DESCRIPTION
         " Index of the MA table."
    	::= { omciCfmMaEntry 1 }

        omciCfmMaMdIndex OBJECT-TYPE
        SYNTAX      Unsigned32 (1..4294967295)
        MAX-ACCESS  read-create
        STATUS      current
        DESCRIPTION
         " The index specifies the MD with which this MA is associated."
    	::= { omciCfmMaEntry 2 }

    	  omciCfmMaFormat OBJECT-TYPE
        SYNTAX  INTEGER {
        	vid(1),
        	string(2),
        	integer(3),
        	vpnid(4)
        }
        MAX-ACCESS  read-create
        STATUS      current
        DESCRIPTION
         " The type (and thereby format) of the Maintenance Association Name."
    	::= { omciCfmMaEntry 3 }

    	  omciCfmMaName OBJECT-TYPE
        SYNTAX  OCTET STRING
        MAX-ACCESS  read-create
        STATUS      current
        DESCRIPTION
         " The Maintenance Association name. The type/format of this object
           is determined by the value of the omciCfmMaFormat object."
    	::= { omciCfmMaEntry 4 }

    	  omciCfmMaCcmInterval OBJECT-TYPE
        SYNTAX  INTEGER {
        		ccmDisable(0),
        		ccm3point33ms(1),
        		ccm10ms(2),
        		ccm100ms(3),
        		ccm1s(4),
        		ccm10s(5),
        		ccm1min(6),
        		ccm10min(7)
        }
        MAX-ACCESS  read-create
        STATUS      current
        DESCRIPTION
         " Interval between CCM transmissions to be used by all MEPs in the MA."
    	::= { omciCfmMaEntry 5 }

				omciCfmMaRowStatus OBJECT-TYPE
        SYNTAX  RowStatus
        MAX-ACCESS  read-create
        STATUS  current
        DESCRIPTION
                      	""
      ::= {  omciCfmMaEntry 6 }

-- *
-- * ontuniportOmciCfm Table
-- *

    	ontuniportOmciCfmTable OBJECT IDENTIFIER ::= { remoteOnt 7 }

-- 		omciCfmMepTable
        omciCfmMepTable OBJECT-TYPE
        SYNTAX	SEQUENCE OF OmciCfmMepEntry
        MAX-ACCESS  not-accessible
        STATUS  current
        DESCRIPTION
                 	""
        ::= { ontuniportOmciCfmTable 1 }

		omciCfmMepEntry OBJECT-TYPE
        SYNTAX	OmciCfmMepEntry
        MAX-ACCESS	not-accessible
        STATUS	current
        DESCRIPTION    	"An entry in omciCfmMepTable."
        INDEX          	{
        		dot1dBasePort,
        		ontNumber,
        		ontcard,
        		uniPort
        }
        ::= { omciCfmMepTable 1 }

        OmciCfmMepEntry ::=
           SEQUENCE {
          omciCfmMepIdentifier		     	      Unsigned32,
        	omciCfmMepMaIndex		     	      Unsigned32,
          omciCfmMepCcmLtmPriority       				INTEGER,
          omciCfmMepRowStatus       				RowStatus
    }

        omciCfmMepIdentifier OBJECT-TYPE
        SYNTAX      Unsigned32 (1..8191)
        MAX-ACCESS  read-create
        STATUS      current
        DESCRIPTION
         " Integer that is unique among all the MEPs in the same MA. MEP Identifier is also known as the MEPID"
    	::= { omciCfmMepEntry 1 }

    	  omciCfmMepMaIndex OBJECT-TYPE
        SYNTAX      Unsigned32 (1..4294967295)
        MAX-ACCESS  read-create
        STATUS      current
        DESCRIPTION
         " The index specifies the MA with which this MEP is associated.."
    	::= { omciCfmMepEntry 2 }

    	  omciCfmMepCcmLtmPriority OBJECT-TYPE
        SYNTAX  INTEGER {
        		priority0(0),
        		priority1(1),
        		priority2(2),
        		priority3(3),
        		priority4(4),
        		priority5(5),
        		priority6(6),
        		priority7(7)
        }
        MAX-ACCESS  read-create
        STATUS      current
        DESCRIPTION
         " The priority value for CCMs and LTMs transmitted by the MEP."
    	::= { omciCfmMepEntry 3 }

				omciCfmMepRowStatus OBJECT-TYPE
        SYNTAX  RowStatus
        MAX-ACCESS  read-create
        STATUS  current
        DESCRIPTION
                      	""
      ::= {  omciCfmMepEntry 4 }

--------------------------------------------------------------------
-- *
-- * ontQosProfile
-- *

    	ontQosProfile OBJECT IDENTIFIER ::= { remoteOnt 8 }

-- 		ingressProfileTable
        ingressProfileTable OBJECT-TYPE
        SYNTAX	SEQUENCE OF IngressProfileEntry
        MAX-ACCESS  not-accessible
        STATUS  current
        DESCRIPTION
                 	""
        ::= { ontQosProfile 1 }

		ingressProfileEntry OBJECT-TYPE
        SYNTAX	IngressProfileEntry
        MAX-ACCESS	not-accessible
        STATUS	current
        DESCRIPTION    	"An entry in ONT QoS ingress profile table."
        INDEX {
        		ingressProfileName
        }
        ::= { ingressProfileTable 1 }

        IngressProfileEntry ::=
        SEQUENCE {
          ingressProfileName     	    OCTET STRING,
          ingressProfileDot1p0tc        INTEGER,
          ingressProfileDot1p1tc        INTEGER,
          ingressProfileDot1p2tc        INTEGER,
          ingressProfileDot1p3tc        INTEGER,
          ingressProfileDot1p4tc        INTEGER,
          ingressProfileDot1p5tc        INTEGER,
          ingressProfileDot1p6tc        INTEGER,
          ingressProfileDot1p7tc        INTEGER,
          ingressProfileRowStatus       RowStatus
        }

    	ingressProfileName OBJECT-TYPE
        SYNTAX  OCTET STRING
        MAX-ACCESS  read-only
        STATUS      current
        DESCRIPTION
         "ONT QoS Ingress Profile Name."
    	::= { ingressProfileEntry 1 }

    	ingressProfileDot1p0tc OBJECT-TYPE
        SYNTAX  INTEGER {
        		tc0(0),
        		tc1(1),
        		tc2(2),
        		tc3(3),
        		tc4(4),
        		tc5(5),
        		tc6(6),
        		tc7(7),
        		tcNULL(8)
        }
        MAX-ACCESS  read-write
        STATUS      current
        DESCRIPTION
         "set traffic class mapping to 802.1P priority 0."
    	::= { ingressProfileEntry 2 }

    	ingressProfileDot1p1tc OBJECT-TYPE
        SYNTAX  INTEGER {
        		tc0(0),
        		tc1(1),
        		tc2(2),
        		tc3(3),
        		tc4(4),
        		tc5(5),
        		tc6(6),
        		tc7(7),
        		tcNULL(8)
        }
        MAX-ACCESS  read-write
        STATUS      current
        DESCRIPTION
         "set traffic class mapping to 802.1P priority 1."
    	::= { ingressProfileEntry 3 }

     	ingressProfileDot1p2tc OBJECT-TYPE
        SYNTAX  INTEGER {
        		tc0(0),
        		tc1(1),
        		tc2(2),
        		tc3(3),
        		tc4(4),
        		tc5(5),
        		tc6(6),
        		tc7(7),
        		tcNULL(8)
        }
        MAX-ACCESS  read-write
        STATUS      current
        DESCRIPTION
         "set traffic class mapping to 802.1P priority 2."
    	::= { ingressProfileEntry 4 }

    	ingressProfileDot1p3tc OBJECT-TYPE
        SYNTAX  INTEGER {
        		tc0(0),
        		tc1(1),
        		tc2(2),
        		tc3(3),
        		tc4(4),
        		tc5(5),
        		tc6(6),
        		tc7(7),
        		tcNULL(8)
        }
        MAX-ACCESS  read-write
        STATUS      current
        DESCRIPTION
         "set traffic class mapping to 802.1P priority 3."
    	::= { ingressProfileEntry 5 }

    	ingressProfileDot1p4tc OBJECT-TYPE
        SYNTAX  INTEGER {
        		tc0(0),
        		tc1(1),
        		tc2(2),
        		tc3(3),
        		tc4(4),
        		tc5(5),
        		tc6(6),
        		tc7(7),
        		tcNULL(8)
        }
        MAX-ACCESS  read-write
        STATUS      current
        DESCRIPTION
         "set traffic class mapping to 802.1P priority 4."
    	::= { ingressProfileEntry 6 }

    	ingressProfileDot1p5tc OBJECT-TYPE
        SYNTAX  INTEGER {
        		tc0(0),
        		tc1(1),
        		tc2(2),
        		tc3(3),
        		tc4(4),
        		tc5(5),
        		tc6(6),
        		tc7(7),
        		tcNULL(8)
        }
        MAX-ACCESS  read-write
        STATUS      current
        DESCRIPTION
         "set traffic class mapping to 802.1P priority 5."
    	::= { ingressProfileEntry 7 }

    	ingressProfileDot1p6tc OBJECT-TYPE
        SYNTAX  INTEGER {
        		tc0(0),
        		tc1(1),
        		tc2(2),
        		tc3(3),
        		tc4(4),
        		tc5(5),
        		tc6(6),
        		tc7(7),
        		tcNULL(8)
        }
        MAX-ACCESS  read-write
        STATUS      current
        DESCRIPTION
         "set traffic class mapping to 802.1P priority 6."
    	::= { ingressProfileEntry 8 }

    	ingressProfileDot1p7tc OBJECT-TYPE
        SYNTAX  INTEGER {
        		tc0(0),
        		tc1(1),
        		tc2(2),
        		tc3(3),
        		tc4(4),
        		tc5(5),
        		tc6(6),
        		tc7(7),
        		tcNULL(8)
        }
        MAX-ACCESS  read-write
        STATUS      current
        DESCRIPTION
         "set traffic class mapping to 802.1P priority 7."
    	::= { ingressProfileEntry 9 }

		ingressProfileRowStatus OBJECT-TYPE
        SYNTAX  RowStatus
        MAX-ACCESS  read-create
        STATUS  current
        DESCRIPTION
                      	""
      ::= {  ingressProfileEntry 10 }
 -- 		pbitProfileTable
        pbitProfileTable OBJECT-TYPE
        SYNTAX	SEQUENCE OF PbitProfileEntry
        MAX-ACCESS  not-accessible
        STATUS  current
        DESCRIPTION
                 	""
        ::= { ontQosProfile 2 }
		pbitProfileEntry OBJECT-TYPE
        SYNTAX	PbitProfileEntry
        MAX-ACCESS	not-accessible
        STATUS	current
        DESCRIPTION    	"An entry in ONT QoS pbit profile table."
        INDEX {
        		pbitProfileName
        }
        ::= { pbitProfileTable 1 }

        PbitProfileEntry ::=
        SEQUENCE {
          pbitProfileName     	    OCTET STRING,
          pbitProfileP0to        INTEGER,
          pbitProfileP1to        INTEGER,
          pbitProfileP2to        INTEGER,
          pbitProfileP3to        INTEGER,
          pbitProfileP4to        INTEGER,
          pbitProfileP5to        INTEGER,
          pbitProfileP6to        INTEGER,
          pbitProfileP7to        INTEGER,
          pbitProfileRowStatus       RowStatus
        }

    	pbitProfileName OBJECT-TYPE
        SYNTAX  OCTET STRING
        MAX-ACCESS  read-only
        STATUS      current
        DESCRIPTION
         "ONT QoS pbit Profile Name."
    	::= { pbitProfileEntry 1 }

    	pbitProfileP0to OBJECT-TYPE
        SYNTAX  INTEGER {
        		tc0(0),
        		tc1(1),
        		tc2(2),
        		tc3(3),
        		tc4(4),
        		tc5(5),
        		tc6(6),
        		tc7(7),
				tcDrop(8)
        }
        MAX-ACCESS  read-write
        STATUS      current
        DESCRIPTION
         "set traffic class mapping to 802.1P priority 0."
    	::= { pbitProfileEntry 2 }

    	pbitProfileP1to OBJECT-TYPE
        SYNTAX  INTEGER {
        		tc0(0),
        		tc1(1),
        		tc2(2),
        		tc3(3),
        		tc4(4),
        		tc5(5),
        		tc6(6),
        		tc7(7),
				tcDrop(8)
        }
        MAX-ACCESS  read-write
        STATUS      current
        DESCRIPTION
         "set traffic class mapping to 802.1P priority 1."
    	::= { pbitProfileEntry 3 }

     	pbitProfileP2to OBJECT-TYPE
        SYNTAX  INTEGER {
        		tc0(0),
        		tc1(1),
        		tc2(2),
        		tc3(3),
        		tc4(4),
        		tc5(5),
        		tc6(6),
        		tc7(7),
				tcDrop(8)
        }
        MAX-ACCESS  read-write
        STATUS      current
        DESCRIPTION
         "set traffic class mapping to 802.1P priority 2."
    	::= { pbitProfileEntry 4 }

    	pbitProfileP3to OBJECT-TYPE
        SYNTAX  INTEGER {
        		tc0(0),
        		tc1(1),
        		tc2(2),
        		tc3(3),
        		tc4(4),
        		tc5(5),
        		tc6(6),
        		tc7(7),
				tcDrop(8)
        }
        MAX-ACCESS  read-write
        STATUS      current
        DESCRIPTION
         "set traffic class mapping to 802.1P priority 3."
    	::= { pbitProfileEntry 5 }

    	pbitProfileP4to OBJECT-TYPE
        SYNTAX  INTEGER {
        		tc0(0),
        		tc1(1),
        		tc2(2),
        		tc3(3),
        		tc4(4),
        		tc5(5),
        		tc6(6),
        		tc7(7),
				tcDrop(8)
        }
        MAX-ACCESS  read-write
        STATUS      current
        DESCRIPTION
         "set traffic class mapping to 802.1P priority 4."
    	::= { pbitProfileEntry 6 }

    	pbitProfileP5to OBJECT-TYPE
        SYNTAX  INTEGER {
        		tc0(0),
        		tc1(1),
        		tc2(2),
        		tc3(3),
        		tc4(4),
        		tc5(5),
        		tc6(6),
        		tc7(7),
				tcDrop(8)
        }
        MAX-ACCESS  read-write
        STATUS      current
        DESCRIPTION
         "set traffic class mapping to 802.1P priority 5."
    	::= { pbitProfileEntry 7 }

    	pbitProfileP6to OBJECT-TYPE
        SYNTAX  INTEGER {
        		tc0(0),
        		tc1(1),
        		tc2(2),
        		tc3(3),
        		tc4(4),
        		tc5(5),
        		tc6(6),
        		tc7(7),
				tcDrop(8)
        }
        MAX-ACCESS  read-write
        STATUS      current
        DESCRIPTION
         "set traffic class mapping to 802.1P priority 6."
    	::= { pbitProfileEntry 8 }

    	pbitProfileP7to OBJECT-TYPE
        SYNTAX  INTEGER {
        		tc0(0),
        		tc1(1),
        		tc2(2),
        		tc3(3),
        		tc4(4),
        		tc5(5),
        		tc6(6),
        		tc7(7),
				tcDrop(8)
        }
        MAX-ACCESS  read-write
        STATUS      current
        DESCRIPTION
         "set traffic class mapping to 802.1P priority 7."
    	::= { pbitProfileEntry 9 }

		pbitProfileRowStatus OBJECT-TYPE
        SYNTAX  RowStatus
        MAX-ACCESS  read-create
        STATUS  current
        DESCRIPTION
                      	""
      ::= {  pbitProfileEntry 10 }

-- 		bwProfileTable
        bwProfileTable OBJECT-TYPE
        SYNTAX	SEQUENCE OF BwProfileEntry
        MAX-ACCESS  not-accessible
        STATUS  current
        DESCRIPTION
                 	""
        ::= { ontQosProfile 3 }

		bwProfileEntry OBJECT-TYPE
        SYNTAX	BwProfileEntry
        MAX-ACCESS	not-accessible
        STATUS	current
        DESCRIPTION    	"An entry in ONT QoS bandwidth profile table."
        INDEX {
        		bwProfileName
        }
        ::= { bwProfileTable 1 }

        BwProfileEntry ::=
        SEQUENCE {
          bwProfileName     	OCTET STRING,
          bwProfileSir        INTEGER,
          bwProfileAir        INTEGER,
          bwProfilePir        INTEGER,
          bwProfileRowStatus  RowStatus,
          bwProfileModify     	OCTET STRING,
          bwProfileUstype        INTEGER,
          bwProfileDescription        OCTET STRING
        }

    	bwProfileName OBJECT-TYPE
        SYNTAX  OCTET STRING
        MAX-ACCESS  read-only
        STATUS      current
        DESCRIPTION
         "ONT QoS Bandwidth Profile Name."
    	::= { bwProfileEntry 1 }

    	bwProfileSir OBJECT-TYPE
        SYNTAX  INTEGER
        MAX-ACCESS  read-write
        STATUS      current
        DESCRIPTION
         "set SIR value."
    	::= { bwProfileEntry 2 }

  	   	bwProfileAir OBJECT-TYPE
        SYNTAX  INTEGER
        MAX-ACCESS  read-write
        STATUS      current
        DESCRIPTION
         "set AIR value."
    	::= { bwProfileEntry 3 }

 	   	bwProfilePir OBJECT-TYPE
        SYNTAX  INTEGER
        MAX-ACCESS  read-write
        STATUS      current
        DESCRIPTION
         "set PIR value."
    	::= { bwProfileEntry 4 }

		bwProfileRowStatus OBJECT-TYPE
        SYNTAX  RowStatus
        MAX-ACCESS  read-create
        STATUS  current
        DESCRIPTION
                      	""
      ::= {  bwProfileEntry 5 }

    	bwProfileModify OBJECT-TYPE
        SYNTAX  OCTET STRING
        MAX-ACCESS  read-write
        STATUS      current
        DESCRIPTION
         "Modify a bandwidth profile that already exist and was used to ONT. The format is '<sir>,<air>,<pir>'"
    	::= { bwProfileEntry 6 }

    	bwProfileUstype OBJECT-TYPE
        SYNTAX  INTEGER
        MAX-ACCESS  read-write
        STATUS      current
        DESCRIPTION
         "Modify the upstream type.
			US TCONT Type
			+-----------------+---------+---------+---------+-------+--------------+
			|  Type0          |  Type1  |  Type2  | Type3   | Type4 | Type5        |
			|                 |         |         |         |       |              |
			+-----------------+---------+---------+---------+-------+--------------+
			|                 |   sir   |         |         |       | sir          |
			+ auto-correction +---------+---------+---------+-------+--------------+
			| when active the |         |   air   |   air   |       | air          |
			+ profile         +---------+---------+---------+-------+--------------+
			|                 | pir=sir | pir=air | pir>air | pir   | pir>=sir+air |
			+-----------------+-------------------+---------+-------+--------------+
			PS: If After auto-correction, the type still is 0,
			    then the profile can`t be used as a US profile."
    	::= { bwProfileEntry 7 }

    	bwProfileDescription OBJECT-TYPE
        SYNTAX  OCTET STRING (SIZE (0..32))
        MAX-ACCESS  read-write
        STATUS      current
        DESCRIPTION
         "ONT QoS Bandwidth Profile description."
    	::= { bwProfileEntry 8 }
        
-- 		ontAlarmProfileTable

			ontAlarmProfileTable OBJECT-TYPE
				SYNTAX	SEQUENCE OF OntAlarmProfileEntry
	      MAX-ACCESS  not-accessible
				STATUS      current
				DESCRIPTION
		            	""
	        ::= { remoteOnt 10 }

			ontAlarmProfileEntry OBJECT-TYPE
        SYNTAX	OntAlarmProfileEntry
        MAX-ACCESS	not-accessible
        STATUS	current
        DESCRIPTION    	"An entry in ONT Alarm profile table for DDMI threshold setting."
        INDEX {
        		ontAlarmProfileName
        }
        ::= { ontAlarmProfileTable 1 }

      	OntAlarmProfileEntry ::=
        SEQUENCE {
          ontAlarmProfileName     	OCTET STRING,
          ontAlarmProfileFeedVoltThreshLow        DisplayString,
          ontAlarmProfileFeedVoltThreshUp        DisplayString,
          ontAlarmProfileBiasCurrThreshLow        DisplayString,
          ontAlarmProfileBiasCurrThreshUp        DisplayString,
          ontAlarmProfileTemperatureThreshLow        DisplayString,
          ontAlarmProfileTemperatureThreshUp        DisplayString,
          ontAlarmProfileTxPowerThreshLow        DisplayString,
          ontAlarmProfileTxPowerThreshUp        DisplayString,
          ontAlarmProfileRowStatus  RowStatus,
          ontAlarmProfileRxPowerThreshLow        DisplayString,
          ontAlarmProfileRxPowerThreshUp        DisplayString
        }

    	ontAlarmProfileName OBJECT-TYPE
        SYNTAX  OCTET STRING
        MAX-ACCESS  read-only
        STATUS      current
        DESCRIPTION
         "ONT Alarm Profile Name."
    	::= { ontAlarmProfileEntry 1 }

    	ontAlarmProfileFeedVoltThreshLow OBJECT-TYPE
        SYNTAX  DisplayString
        MAX-ACCESS  read-write
        STATUS      current
        DESCRIPTION
         "set Lower Power Feed Voltage Threshold (unit V). The range of voltage is between 2.80 and 3.59 V."
    	::= { ontAlarmProfileEntry 2 }

  	  ontAlarmProfileFeedVoltThreshUp OBJECT-TYPE
        SYNTAX  DisplayString
        MAX-ACCESS  read-write
        STATUS      current
        DESCRIPTION
         "set Upper Power Feed Voltage Threshold (unit V). The range of voltage is between 2.80 and 3.59 V."
    	::= { ontAlarmProfileEntry 3 }

 	   	ontAlarmProfileBiasCurrThreshLow OBJECT-TYPE
        SYNTAX  DisplayString
        MAX-ACCESS  read-write
        STATUS      current
        DESCRIPTION
         "set Lower Laser Bias Current Threshold (unit mA). The range of current is between 0 and 79 mA."
    	::= { ontAlarmProfileEntry 4 }

  	  ontAlarmProfileBiasCurrThreshUp OBJECT-TYPE
        SYNTAX  DisplayString
        MAX-ACCESS  read-write
        STATUS      current
        DESCRIPTION
         "set Upper Laser Bias Current Threshold (unit mA). The range of current is between 0 and 79 mA."
    	::= { ontAlarmProfileEntry 5 }

      ontAlarmProfileTemperatureThreshLow OBJECT-TYPE
        SYNTAX  DisplayString
        MAX-ACCESS  read-write
        STATUS      current
        DESCRIPTION
         "set Lower Temperature Threshold (unit degree C). The range of temperature is between -40 and 100 degree C."
    	::= { ontAlarmProfileEntry 6 }

  	  ontAlarmProfileTemperatureThreshUp OBJECT-TYPE
        SYNTAX  DisplayString
        MAX-ACCESS  read-write
        STATUS      current
        DESCRIPTION
         "set Upper Temperature Threshold (unit degree C). The range of temperature is between -40 and 100 degree C."
    	::= { ontAlarmProfileEntry 7 }

    	ontAlarmProfileTxPowerThreshLow OBJECT-TYPE
        SYNTAX  DisplayString
        MAX-ACCESS  read-write
        STATUS      current
        DESCRIPTION
         "set Lower Transmit Power Threshold (unit dBm). The range of power is between -15.3 and 6.5 dBm."
    	::= { ontAlarmProfileEntry 8 }

  	  ontAlarmProfileTxPowerThreshUp OBJECT-TYPE
        SYNTAX  DisplayString
        MAX-ACCESS  read-write
        STATUS      current
        DESCRIPTION
         "set Upper Transmit Power Threshold (unit dBm). The range of power is between -15.3 and 6.5 dBm."
    	::= { ontAlarmProfileEntry 9 }


			ontAlarmProfileRowStatus OBJECT-TYPE
        SYNTAX  RowStatus
        MAX-ACCESS  read-create
        STATUS  current
        DESCRIPTION
                      	""
      ::= {  ontAlarmProfileEntry 10 }

    	ontAlarmProfileRxPowerThreshLow OBJECT-TYPE
        SYNTAX  DisplayString
        MAX-ACCESS  read-write
        STATUS      current
        DESCRIPTION
         "set Lower Receive Power Threshold (unit dBm). The range of power is between -127 and 0 dBm."
    	::= { ontAlarmProfileEntry 11 }

  	  ontAlarmProfileRxPowerThreshUp OBJECT-TYPE
        SYNTAX  DisplayString
        MAX-ACCESS  read-write
        STATUS      current
        DESCRIPTION
         "set Upper Receive Power Threshold (unit dBm). The range of power is between -127 and 0 dBm."
    	::= { ontAlarmProfileEntry 12 }

-- *
-- * ontvenet Table
-- *
  	ontvenetTable OBJECT-TYPE
		SYNTAX      SEQUENCE OF OntvenetEntry
        MAX-ACCESS  not-accessible
		STATUS      current
		DESCRIPTION
	            ""
        ::= { remoteOnt 11 }

	ontvenetEntry OBJECT-TYPE
        SYNTAX      OntvenetEntry
        MAX-ACCESS  not-accessible
        STATUS      current
        DESCRIPTION
        		"An entry in ontvenetTable"
        INDEX {
        		dot1dBasePort,
        		ontNumber,
        		ontcard,
        		ontvenetCardPort
        }
    	::= { ontvenetTable 1 }

	OntvenetEntry ::=
        SEQUENCE {
            ontvenetCardPort		     	      INTEGER,
            pmvenetEnable                      INTEGER,
            ontvenetRowStatus              RowStatus,
            ontvenetAction              INTEGER
   	}

	ontvenetCardPort OBJECT-TYPE
        SYNTAX      INTEGER
        MAX-ACCESS  not-accessible
        STATUS      current
        DESCRIPTION
         	" ontvenetCardPort."
    	::= { ontvenetEntry 1 }

	pmvenetEnable OBJECT-TYPE
        SYNTAX      INTEGER {
             disable(0),
             baseOnModelID(1),
			 bit64(2),
			 bit32(3)
         }
        MAX-ACCESS  read-write
        STATUS      current
        DESCRIPTION
         	" pmvenetEnable."
    	::= { ontvenetEntry 2 }

	ontvenetRowStatus OBJECT-TYPE
        SYNTAX      RowStatus
        MAX-ACCESS  read-create
        STATUS      current
        DESCRIPTION
         ""
        ::= { ontvenetEntry 3 }

     ontvenetAction OBJECT-TYPE
         SYNTAX  INTEGER {
             idle(0),
             delAllConfig(1)
         }
         MAX-ACCESS  read-write
         STATUS  current
         DESCRIPTION
                "Delete all configurations relating to ontvenet."
         ::= { ontvenetEntry 4 }
-- *
-- * ontpots Table
-- *
  	ontpotsTable OBJECT-TYPE
		SYNTAX      SEQUENCE OF OntpotsEntry
        MAX-ACCESS  not-accessible
		STATUS      current
		DESCRIPTION
	            ""
        ::= { remoteOnt 12 }

	ontpotsEntry OBJECT-TYPE
        SYNTAX      OntpotsEntry
        MAX-ACCESS  not-accessible
        STATUS      current
        DESCRIPTION
        		"An entry in ontpotsTable"
        INDEX {
        		dot1dBasePort,
        		ontNumber,
        		ontcard,
        		ontpotsCardPort
        }
    	::= { ontpotsTable 1 }

	OntpotsEntry ::=
        SEQUENCE {
            ontpotsCardPort		     	      INTEGER,
            ontpotsRowStatus              RowStatus,
            ontpotsAction              INTEGER
   	}

	ontpotsCardPort OBJECT-TYPE
        SYNTAX      INTEGER
        MAX-ACCESS  not-accessible
        STATUS      current
        DESCRIPTION
         	" ontpotsCardPort."
    	::= { ontpotsEntry 1 }

	ontpotsRowStatus OBJECT-TYPE
        SYNTAX      RowStatus
        MAX-ACCESS  read-create
        STATUS      current
        DESCRIPTION
         ""
        ::= { ontpotsEntry 2 }

     ontpotsAction OBJECT-TYPE
         SYNTAX  INTEGER {
             idle(0),
             delAllConfig(1)
         }
         MAX-ACCESS  read-write
         STATUS  current
         DESCRIPTION
                "Delete all configurations relating to ontpots."
         ::= { ontpotsEntry 3 }

--------------------------------------------------------------------
-- *
-- * ontVoipProfile
-- *

    	ontVoipProfile OBJECT IDENTIFIER ::= { remoteOnt 13 }

-- 		sipProfileTable
        sipProfileTable OBJECT-TYPE
        SYNTAX	SEQUENCE OF SipProfileEntry
        MAX-ACCESS  not-accessible
        STATUS  current
        DESCRIPTION
                 	""
        ::= { ontVoipProfile 1 }

		sipProfileEntry OBJECT-TYPE
        SYNTAX	SipProfileEntry
        MAX-ACCESS	not-accessible
        STATUS	current
        DESCRIPTION    	"An entry in ONT Voip sip profile table."
        INDEX {
        		sipProfileName
        }
        ::= { sipProfileTable 1 }

        SipProfileEntry ::=
        SEQUENCE {
          sipProfileName     	        DisplayString,
          sipProfileProxyServiceAddr    DisplayString,
          sipProfileOutProxyAddr        DisplayString,
          sipProfilePriDns              IpAddress,
          sipProfileSecDns              IpAddress,
          sipProfileRegExpTime          INTEGER,
          sipProfileReregHeadStartTime  INTEGER,
          sipProfileHostPartUri         DisplayString,
          sipProfileRegistrar           DisplayString,
          sipProfileSoftSwitch          DisplayString,
          sipProfileCid                 BITS,
          sipProfileCallWait            BITS,
          sipProfileCallProgTrans       BITS,
          sipProfileCallPresent         BITS,
          sipProfileDirectCon           BITS,
          sipProfileDirectConUri        DisplayString,
          sipProfileBridgeLineAgentUri  DisplayString,
          sipProfileConfFactoryUri      DisplayString,
          sipProfileRowStatus           RowStatus
        }

    	sipProfileName OBJECT-TYPE
        SYNTAX  DisplayString
        MAX-ACCESS  read-only
        STATUS      current
        DESCRIPTION
         "ONT Voip sip profile name(1 ~ 15 characters)."
    	::= { sipProfileEntry 1 }

    	sipProfileProxyServiceAddr OBJECT-TYPE
        SYNTAX  DisplayString
        MAX-ACCESS  read-write
        STATUS      current
        DESCRIPTION
         "set ONT Voip proxy service address(1 ~ 63 characters)."
    	::= { sipProfileEntry 2 }

     	sipProfileOutProxyAddr OBJECT-TYPE
        SYNTAX  DisplayString
        MAX-ACCESS  read-write
        STATUS      current
        DESCRIPTION
         "set ONT Voip out proxy address(1 ~ 15 characters)."
    	::= { sipProfileEntry 3 }

      	sipProfilePriDns OBJECT-TYPE
        SYNTAX  IpAddress
        MAX-ACCESS  read-write
        STATUS      current
        DESCRIPTION
         "set ONT Voip primary sip dns(ip format)."
    	::= { sipProfileEntry 4 }

       	sipProfileSecDns OBJECT-TYPE
        SYNTAX  IpAddress
        MAX-ACCESS  read-write
        STATUS      current
        DESCRIPTION
         "set ONT Voip secondary sip dns(ip format)."
    	::= { sipProfileEntry 5 }

        sipProfileRegExpTime OBJECT-TYPE
        SYNTAX  INTEGER
        MAX-ACCESS  read-write
        STATUS      current
        DESCRIPTION
         "set ONT Voip sip registration expiration time(0 ~ 25200 sec)."
    	::= { sipProfileEntry 6 }

        sipProfileReregHeadStartTime OBJECT-TYPE
        SYNTAX  INTEGER
        MAX-ACCESS  read-write
        STATUS      current
        DESCRIPTION
         "set ONT Voip sip re-registration head start time(0 ~ 720 sec)."
    	::= { sipProfileEntry 7 }

        sipProfileHostPartUri OBJECT-TYPE
        SYNTAX  DisplayString
        MAX-ACCESS  read-write
        STATUS      current
        DESCRIPTION
         "set ONT Voip host or domain part of the sip address(1 ~ 63 characters)."
    	::= { sipProfileEntry 8 }

        sipProfileRegistrar OBJECT-TYPE
        SYNTAX  DisplayString
        MAX-ACCESS  read-write
        STATUS      current
        DESCRIPTION
         "set ONT Voip sip registrar address(1 ~ 63 characters)."
    	::= { sipProfileEntry 9 }

        sipProfileSoftSwitch OBJECT-TYPE
        SYNTAX  DisplayString
        MAX-ACCESS  read-write
        STATUS      current
        DESCRIPTION
         "set ONT Voip sip gateway softswitch vendor.
         This format os four ASCII coded alphabetic characters[A..Z] as defined in ANSI T1.220(4 characters)."
    	::= { sipProfileEntry 10 }

        sipProfileCid OBJECT-TYPE
        SYNTAX	BITS {
			calNum(0),
			calNam(1),
			cidBlo(2),
			cidNum(3),
			cidNam(4),
			acr(5)
		}
        MAX-ACCESS  read-write
        STATUS      current
        DESCRIPTION
         "set ONT sip caller ID features."
    	::= { sipProfileEntry 11 }

        sipProfileCallWait OBJECT-TYPE
        SYNTAX	BITS {
			calWai(0),
			cidAnn(1)
		}
        MAX-ACCESS  read-write
        STATUS      current
        DESCRIPTION
         "set ONT sip call waiting feature."
    	::= { sipProfileEntry 12 }

        sipProfileCallProgTrans OBJECT-TYPE
        SYNTAX	BITS {
			threeWay(0),
			calTra(1),
			calHol(2),
			calPar(3),
			notDis(4),
			flash(5),
			origin(6),
			sixWay(7)
		}
        MAX-ACCESS  read-write
        STATUS      current
        DESCRIPTION
         "set ONT sip progress or transfer feature."
    	::= { sipProfileEntry 13 }

        sipProfileCallPresent OBJECT-TYPE
        SYNTAX	BITS {
			splRin(0),
			diaTon(1),
			visInd(2),
			calFor(3)
		}
        MAX-ACCESS  read-write
        STATUS      current
        DESCRIPTION
         "set ONT sip call presentation feature."
    	::= { sipProfileEntry 14 }

        sipProfileDirectCon OBJECT-TYPE
        SYNTAX	BITS {
			enable(0),
			disOpt(1)
		}
        MAX-ACCESS  read-write
        STATUS      current
        DESCRIPTION
         "set ONT sip direct connect feature."
    	::= { sipProfileEntry 15 }

        sipProfileDirectConUri OBJECT-TYPE
        SYNTAX  DisplayString
        MAX-ACCESS  read-write
        STATUS      current
        DESCRIPTION
         "set ONT direct connect URI(1 ~ 63 characters)."
    	::= { sipProfileEntry 16 }

        sipProfileBridgeLineAgentUri OBJECT-TYPE
        SYNTAX  DisplayString
        MAX-ACCESS  read-write
        STATUS      current
        DESCRIPTION
         "set ONT bridge line agent URI(1 ~ 63 characters)."
    	::= { sipProfileEntry 17 }


        sipProfileConfFactoryUri OBJECT-TYPE
        SYNTAX  DisplayString
        MAX-ACCESS  read-write
        STATUS      current
        DESCRIPTION
         "set ONT conference factory URI(1 ~ 63 characters)."
    	::= { sipProfileEntry 18 }


		sipProfileRowStatus OBJECT-TYPE
        SYNTAX  RowStatus
        MAX-ACCESS  read-create
        STATUS  current
        DESCRIPTION
                      	""
      ::= {  sipProfileEntry 19 }

 -- 		commonProfileTable
        commonProfileTable OBJECT-TYPE
        SYNTAX	SEQUENCE OF CommonProfileEntry
        MAX-ACCESS  not-accessible
        STATUS  current
        DESCRIPTION
                 	""
        ::= { ontVoipProfile 2 }
		commonProfileEntry OBJECT-TYPE
        SYNTAX	CommonProfileEntry
        MAX-ACCESS	not-accessible
        STATUS	current
        DESCRIPTION    	"An entry in ONT Voip common profile table."
        INDEX {
        		commonProfileName
        }
        ::= { commonProfileTable 1 }

        CommonProfileEntry ::=
        SEQUENCE {
          commonProfileName     	      DisplayString,
          commonProfileLocalPortMin       INTEGER,
          commonProfileLocalPortMax       INTEGER,
          commonProfileDscpMark           INTEGER,
          commonProfilePiggyback          INTEGER,
          commonProfileTone               INTEGER,
          commonProfileDtmf               INTEGER,
          commonProfileCas                INTEGER,
          commonProfileAnnounceType       INTEGER,
          commonProfileJitterTarget       INTEGER,
          commonProfileJitterBufMax       INTEGER,
          commonProfileEchoCancel         INTEGER,
          commonProfilePstnProtocol       INTEGER,
          commonProfileFaxMode            INTEGER,
          commonProfile1stCodec           INTEGER,
          commonProfile2ndCodec           INTEGER,
          commonProfile3rdCodec           INTEGER,
          commonProfile4thCodec           INTEGER,
          commonProfile1stPacketPeriod    INTEGER,
          commonProfile2ndPacketPeriod    INTEGER,
          commonProfile3rdPacketPeriod    INTEGER,
          commonProfile4thPacketPeriod    INTEGER,
          commonProfile1stSilence         INTEGER,
          commonProfile2ndSilence         INTEGER,
          commonProfile3rdSilence         INTEGER,
          commonProfile4thSilence         INTEGER,
          commonProfileOobDtmf            INTEGER,
          commonProfileRowStatus          RowStatus,
          commonProfileSignalCode         INTEGER
        }

    	commonProfileName OBJECT-TYPE
        SYNTAX  DisplayString
        MAX-ACCESS  read-only
        STATUS      current
        DESCRIPTION
         "ONT Voip common profile name(1 ~ 15 characters)."
    	::= { commonProfileEntry 1 }

        commonProfileLocalPortMin OBJECT-TYPE
        SYNTAX  INTEGER
        MAX-ACCESS  read-write
        STATUS      current
        DESCRIPTION
         "set ONT Voip base RTP port(1 ~ 65535, but must smaller than highest RTP port)."
    	::= { commonProfileEntry 2 }

        commonProfileLocalPortMax OBJECT-TYPE
        SYNTAX  INTEGER
        MAX-ACCESS  read-write
        STATUS      current
        DESCRIPTION
         "set ONT Voip highest RTP port(1 ~ 65535, but must bigger than highest RTP port)."
    	::= { commonProfileEntry 3 }

        commonProfileDscpMark OBJECT-TYPE
        SYNTAX  INTEGER
        MAX-ACCESS  read-write
        STATUS      current
        DESCRIPTION
         "set ONT Voip diffserv code point to be used for utgoing RTP packets for this profile(0 ~ 63)."
    	::= { commonProfileEntry 4 }

        commonProfilePiggyback OBJECT-TYPE
        SYNTAX  INTEGER {
			disable(0),
			enable(1)
		}
        MAX-ACCESS  read-write
        STATUS      current
        DESCRIPTION
         "set ONT Voip RTP piggyback events."
    	::= { commonProfileEntry 5 }

        commonProfileTone OBJECT-TYPE
        SYNTAX  INTEGER {
			disable(0),
			enable(1)
		}
        MAX-ACCESS  read-write
        STATUS      current
        DESCRIPTION
         "set ONT Voip handlin of tones via RTP tone events per RFC 4733."
    	::= { commonProfileEntry 6 }

        commonProfileDtmf OBJECT-TYPE
        SYNTAX  INTEGER {
			disable(0),
			enable(1)
		}
        MAX-ACCESS  read-write
        STATUS      current
        DESCRIPTION
         "set ONT Voip handling of DTMF via RTP DTMF events per RFC 4733."
    	::= { commonProfileEntry 7 }


        commonProfileCas OBJECT-TYPE
        SYNTAX  INTEGER {
			disable(0),
			enable(1)
		}
        MAX-ACCESS  read-write
        STATUS      current
        DESCRIPTION
         "set ONT Voip handling of CAS via RTP CAS events per RFC 4733."
    	::= { commonProfileEntry 8 }

        commonProfileAnnounceType OBJECT-TYPE
        SYNTAX  INTEGER {
			silence(0),
			reoTon(1),
			fasBus(2),
			voiAnn(3)
		}
        MAX-ACCESS  read-write
        STATUS      current
        DESCRIPTION
         "set ONT Voip treatment when a subscriber goes off hook but dose not attempt a call."
    	::= { commonProfileEntry 9 }

        commonProfileJitterTarget OBJECT-TYPE
        SYNTAX  INTEGER
        MAX-ACCESS  read-write
        STATUS      current
        DESCRIPTION
         "set ONT Voip target value of the jitter buffer in milliseconds(0 ~ 500 milliseconds)."
    	::= { commonProfileEntry 10 }

        commonProfileJitterBufMax OBJECT-TYPE
        SYNTAX  INTEGER
        MAX-ACCESS  read-write
        STATUS      current
        DESCRIPTION
         "set ONT Voip maximum depth of the jitter buffer associated with this service in milliseconds(0 ~ 5000 milliseconds)."
    	::= { commonProfileEntry 11 }

        commonProfileEchoCancel OBJECT-TYPE
        SYNTAX  INTEGER {
			disable(0),
			enable(1)
		}
        MAX-ACCESS  read-write
        STATUS      current
        DESCRIPTION
         "set ONT Voip echo cancellation."
    	::= { commonProfileEntry 12 }

        commonProfilePstnProtocol OBJECT-TYPE
        SYNTAX  INTEGER
        MAX-ACCESS  read-write
        STATUS      current
        DESCRIPTION
         "set ONT Voip pstn protocol the value is equal to the E.164 country code. ex: taiwan is 886."
    	::= { commonProfileEntry 13 }

        commonProfileFaxMode OBJECT-TYPE
        SYNTAX  INTEGER {
			passthru(0),
			t38(1)
		}
        MAX-ACCESS  read-write
        STATUS      current
        DESCRIPTION
         "set ONT Voip fax mode."
    	::= { commonProfileEntry 14 }

        commonProfile1stCodec OBJECT-TYPE
        SYNTAX  INTEGER {
			pcmu(0),
			gsm(3),
			g723(4),
			dvi48000(5),
			dvi416000(6),
			lpc(7),
			pcma(8),
			g722(9),
			l162(10),
			l161(11),
			qcelp(12),
			cn(13),
			mpa(14),
			g728(15),
			dvi411025(16),
			dvi422050(17),
			g729(18)
		}
        MAX-ACCESS  read-write
        STATUS      current
        DESCRIPTION
         "set ONT Voip codec selection as defined by RFC 3551."
    	::= { commonProfileEntry 15 }

        commonProfile2ndCodec OBJECT-TYPE
        SYNTAX  INTEGER {
			pcmu(0),
			gsm(3),
			g723(4),
			dvi48000(5),
			dvi416000(6),
			lpc(7),
			pcma(8),
			g722(9),
			l162(10),
			l161(11),
			qcelp(12),
			cn(13),
			mpa(14),
			g728(15),
			dvi411025(16),
			dvi422050(17),
			g729(18)
		}
        MAX-ACCESS  read-write
        STATUS      current
        DESCRIPTION
         "set ONT Voip codec selection as defined by RFC 3551."
    	::= { commonProfileEntry 16 }

        commonProfile3rdCodec OBJECT-TYPE
        SYNTAX  INTEGER {
			pcmu(0),
			gsm(3),
			g723(4),
			dvi48000(5),
			dvi416000(6),
			lpc(7),
			pcma(8),
			g722(9),
			l162(10),
			l161(11),
			qcelp(12),
			cn(13),
			mpa(14),
			g728(15),
			dvi411025(16),
			dvi422050(17),
			g729(18)
		}
        MAX-ACCESS  read-write
        STATUS      current
        DESCRIPTION
         "set ONT Voip codec selection as defined by RFC 3551."
    	::= { commonProfileEntry 17 }

        commonProfile4thCodec OBJECT-TYPE
        SYNTAX  INTEGER {
			pcmu(0),
			gsm(3),
			g723(4),
			dvi48000(5),
			dvi416000(6),
			lpc(7),
			pcma(8),
			g722(9),
			l162(10),
			l161(11),
			qcelp(12),
			cn(13),
			mpa(14),
			g728(15),
			dvi411025(16),
			dvi422050(17),
			g729(18)
		}
        MAX-ACCESS  read-write
        STATUS      current
        DESCRIPTION
         "set ONT Voip codec selection as defined by RFC 3551."
    	::= { commonProfileEntry 18 }

        commonProfile1stPacketPeriod OBJECT-TYPE
        SYNTAX  INTEGER
        MAX-ACCESS  read-write
        STATUS      current
        DESCRIPTION
         "set ONT Voip packet period selection interval in milliseconds(10 ~ 30 milliseconds)."
    	::= { commonProfileEntry 19 }

        commonProfile2ndPacketPeriod OBJECT-TYPE
        SYNTAX  INTEGER
        MAX-ACCESS  read-write
        STATUS      current
        DESCRIPTION
         "set ONT Voip packet period selection interval in milliseconds(10 ~ 30 milliseconds)."
    	::= { commonProfileEntry 20 }

        commonProfile3rdPacketPeriod OBJECT-TYPE
        SYNTAX  INTEGER
        MAX-ACCESS  read-write
        STATUS      current
        DESCRIPTION
         "set ONT Voip packet period selection interval in milliseconds(10 ~ 30 milliseconds)."
    	::= { commonProfileEntry 21 }

        commonProfile4thPacketPeriod OBJECT-TYPE
        SYNTAX  INTEGER
        MAX-ACCESS  read-write
        STATUS      current
        DESCRIPTION
         "set ONT Voip packet period selection interval in milliseconds(10 ~ 30 milliseconds)."
    	::= { commonProfileEntry 22 }

        commonProfile1stSilence OBJECT-TYPE
        SYNTAX  INTEGER {
			disable(0),
			enable(1)
		}
        MAX-ACCESS  read-write
        STATUS      current
        DESCRIPTION
         "set ONT Voip silence suppression."
    	::= { commonProfileEntry 23 }

        commonProfile2ndSilence OBJECT-TYPE
        SYNTAX  INTEGER {
			disable(0),
			enable(1)
		}
        MAX-ACCESS  read-write
        STATUS      current
        DESCRIPTION
         "set ONT Voip silence suppression."
    	::= { commonProfileEntry 24 }

        commonProfile3rdSilence OBJECT-TYPE
        SYNTAX  INTEGER {
			disable(0),
			enable(1)
		}
        MAX-ACCESS  read-write
        STATUS      current
        DESCRIPTION
         "set ONT Voip silence suppression."
    	::= { commonProfileEntry 25 }

        commonProfile4thSilence OBJECT-TYPE
        SYNTAX  INTEGER {
			disable(0),
			enable(1)
		}
        MAX-ACCESS  read-write
        STATUS      current
        DESCRIPTION
         "set ONT Voip silence suppression."
    	::= { commonProfileEntry 26 }

        commonProfileOobDtmf OBJECT-TYPE
        SYNTAX  INTEGER {
			disable(0),
			enable(1)
		}
        MAX-ACCESS  read-write
        STATUS      current
        DESCRIPTION
         "set ONT Voip out of band DTMF carriage."
    	::= { commonProfileEntry 27 }

		commonProfileRowStatus OBJECT-TYPE
        SYNTAX  RowStatus
        MAX-ACCESS  read-create
        STATUS  current
        DESCRIPTION
                      	""
      ::= {  commonProfileEntry 28 }


        commonProfileSignalCode OBJECT-TYPE
      SYNTAX  INTEGER {
			loopStart(0),
			groundStart(1),
			loopReverseBattery(2),
			coinFirst(3),
			dialToneFirst(4),
			multiparty(5)
		}
        MAX-ACCESS  read-write
        STATUS  current
        DESCRIPTION
         "set ONT Voip signal conde."
      ::= {  commonProfileEntry 29 }



-- 		dialPlanTable

        dialPlan OBJECT IDENTIFIER ::= { ontVoipProfile 3 }

        dialPlanCommTable OBJECT-TYPE
        SYNTAX	SEQUENCE OF DialPlanCommEntry
        MAX-ACCESS  not-accessible
        STATUS  current
        DESCRIPTION
                 	""
        ::= { dialPlan 1 }

		dialPlanCommEntry OBJECT-TYPE
        SYNTAX	DialPlanCommEntry
        MAX-ACCESS	not-accessible
        STATUS	current
        DESCRIPTION    	"An entry in ONT Voip network dial plan common table."
        INDEX {
        		dialPlanCommName
        }
        ::= { dialPlanCommTable 1 }

        DialPlanCommEntry ::=
        SEQUENCE {
          dialPlanCommName            DisplayString,
          dialPlanCommMaxSize         INTEGER,
          dialPlanCommCriticalTimeout INTEGER,
          dialPlanCommPartialTimeout  INTEGER,
          dialPlanCommFormat          INTEGER,
          dialPlanCommRowStatus       RowStatus
        }

    	dialPlanCommName OBJECT-TYPE
        SYNTAX  DisplayString
        MAX-ACCESS  read-only
        STATUS      current
        DESCRIPTION
         "ONT Voip network dial plan Name(1 ~ 15 characters)."
    	::= { dialPlanCommEntry 1 }

    	dialPlanCommMaxSize OBJECT-TYPE
        SYNTAX  INTEGER
        MAX-ACCESS  read-write
        STATUS      current
        DESCRIPTION
         "set ONT Voip maximum number of dial plans(1 ~ 256)."
    	::= { dialPlanCommEntry 2 }

  	   	dialPlanCommCriticalTimeout OBJECT-TYPE
        SYNTAX  INTEGER
        MAX-ACCESS  read-write
        STATUS      current
        DESCRIPTION
         "set ONT Voip critical dial timeout for digit map processing in milliseconds(0 ~ 8000 milliseconds)."
    	::= { dialPlanCommEntry 3 }

 	   	dialPlanCommPartialTimeout OBJECT-TYPE
        SYNTAX  INTEGER
        MAX-ACCESS  read-write
        STATUS      current
        DESCRIPTION
         "set ONT Voip partial dial timeout for digit map processing in milliseconds(0 ~ 32000 milliseconds)."
    	::= { dialPlanCommEntry 4 }

  	   	dialPlanCommFormat OBJECT-TYPE
        SYNTAX  INTEGER {
			notDefined(0),
			h248(1),
			nsc(2),
			vendorSpecific(3)
		}
        MAX-ACCESS  read-write
        STATUS      current
        DESCRIPTION
         "set ONT Voip dial plan format standard that is supported in the ONT for Voip."
    	::= { dialPlanCommEntry 5 }

		dialPlanCommRowStatus OBJECT-TYPE
        SYNTAX  RowStatus
        MAX-ACCESS  read-create
        STATUS  current
        DESCRIPTION
                      	""
      ::= {  dialPlanCommEntry 6 }


        dialPlanContTable OBJECT-TYPE
        SYNTAX	SEQUENCE OF DialPlanContEntry
        MAX-ACCESS  not-accessible
        STATUS  current
        DESCRIPTION
                 	""
        ::= { dialPlan 2 }

		dialPlanContEntry OBJECT-TYPE
        SYNTAX	DialPlanContEntry
        MAX-ACCESS	not-accessible
        STATUS	current
        DESCRIPTION    	"An entry in ONT Voip network dial plan content table."
        INDEX {
        		dialPlanContName,
        		dialPlanContId
        }
        ::= { dialPlanContTable 1 }

        DialPlanContEntry ::=
        SEQUENCE {
          dialPlanContName            OCTET STRING,
          dialPlanContId              INTEGER,
          dialPlanContToken           OCTET STRING,
          dialPlanContRowStatus       RowStatus
        }

    	dialPlanContName OBJECT-TYPE
        SYNTAX  OCTET STRING
        MAX-ACCESS  read-only
        STATUS      current
        DESCRIPTION
         "ONT Voip network dial plan Name."
    	::= { dialPlanContEntry 1 }

    	dialPlanContId OBJECT-TYPE
        SYNTAX  INTEGER
        MAX-ACCESS  read-write
        STATUS      current
        DESCRIPTION
         "set ONT Voip dial plans id(1 ~ 16)."
    	::= { dialPlanContEntry 2 }

    	dialPlanContToken OBJECT-TYPE
        SYNTAX  OCTET STRING
        MAX-ACCESS  read-write
        STATUS      current
        DESCRIPTION
         "set ONT Voip dial plan token(1 ~ 28 characters)."
    	::= { dialPlanContEntry 3 }

    	dialPlanContRowStatus OBJECT-TYPE
        SYNTAX  RowStatus
        MAX-ACCESS  read-create
        STATUS      current
        DESCRIPTION
         ""
    	::= { dialPlanContEntry 4 }

-- *
-- * ontvideo Table
-- *
  	ontvideoTable OBJECT-TYPE
		SYNTAX      SEQUENCE OF OntvideoEntry
        MAX-ACCESS  not-accessible
		STATUS      current
		DESCRIPTION
	            ""
        ::= { remoteOnt 14 }

	ontvideoEntry OBJECT-TYPE
        SYNTAX      OntvideoEntry
        MAX-ACCESS  not-accessible
        STATUS      current
        DESCRIPTION
        		"An entry in ontvideoTable"
        INDEX {
        		dot1dBasePort,
        		ontNumber,
        		ontcard,
        		ontvideoPort
        }
    	::= { ontvideoTable 1 }

	OntvideoEntry ::=
        SEQUENCE {
            ontvideoPort		INTEGER,
            ontvideoRowStatus           RowStatus,
            ontvideoAction              INTEGER
   	}

	ontvideoPort OBJECT-TYPE
        SYNTAX      INTEGER
        MAX-ACCESS  not-accessible
        STATUS      current
        DESCRIPTION
         	" ontvideoPort."
    	::= { ontvideoEntry 1 }

	ontvideoRowStatus OBJECT-TYPE
        SYNTAX      RowStatus
        MAX-ACCESS  read-create
        STATUS      current
        DESCRIPTION
         ""
        ::= { ontvideoEntry 2 }

     ontvideoAction OBJECT-TYPE
         SYNTAX  INTEGER {
             idle(0),
             delAllConfig(1)
         }
         MAX-ACCESS  read-write
         STATUS  current
         DESCRIPTION
                "Delete all configurations relating to ontvideo."
         ::= { ontvideoEntry 3 }

-- *
-- * onuVendorVersion
-- *

    	onuVendorVersion OBJECT IDENTIFIER ::= { remoteOnt 15 }

-- 		onuVendorVersionTable
        onuVendorVersionTable OBJECT-TYPE
        SYNTAX	SEQUENCE OF OnuVendorVersionEntry
        MAX-ACCESS  not-accessible
        STATUS  current
        DESCRIPTION
                 	""
        ::= { onuVendorVersion 1 }

		onuVendorVersionEntry OBJECT-TYPE
        SYNTAX	OnuVendorVersionEntry
        MAX-ACCESS	not-accessible
        STATUS	current
        DESCRIPTION    	"An entry in ONU Model table."
        INDEX {
          onuVendorVersionModelName
        }
        ::= { onuVendorVersionTable 1 }

        OnuVendorVersionEntry ::=
        SEQUENCE {
          onuVendorVersionName     	    OCTET STRING,
          onuVendorVersionSoftwareVer   OCTET STRING,
          onuVendorVersionModelName     OCTET STRING,
          onuVendorVersionModelID       INTEGER,
          onuVendorVersionCard1         INTEGER,
          onuVendorVersionCard2         INTEGER,
          onuVendorVersionCard3         INTEGER,
          onuVendorVersionCard4         INTEGER,
          onuVendorVersionCard5         INTEGER,
		  onuVendorVersionRowStatus	    RowStatus
        }

    	onuVendorVersionName OBJECT-TYPE
        SYNTAX  OCTET STRING
        MAX-ACCESS  read-write
        STATUS      current
        DESCRIPTION
         "ONU Vendor Version Name."
    	::= { onuVendorVersionEntry 1 }

		onuVendorVersionSoftwareVer OBJECT-TYPE
        SYNTAX  OCTET STRING
        MAX-ACCESS  read-write
        STATUS      current
        DESCRIPTION
         "ONU Vendor Version Software-version."
    	::= { onuVendorVersionEntry 2 }

		onuVendorVersionModelName OBJECT-TYPE
        SYNTAX  OCTET STRING
        MAX-ACCESS  read-only
        STATUS      current
        DESCRIPTION
         "ONU Vendor Version Model Name."
    	::= { onuVendorVersionEntry 3 }


		onuVendorVersionModelID OBJECT-TYPE
        SYNTAX  INTEGER (0..8)
        MAX-ACCESS  read-write
        STATUS      current
        DESCRIPTION
         "ONU Vendor Version Model ID."
    	::= { onuVendorVersionEntry 4 }

		onuVendorVersionCard1 OBJECT-TYPE
        SYNTAX  INTEGER (0..255)
        MAX-ACCESS  read-write
        STATUS      current
        DESCRIPTION
         "ONU Vendor Version GIGA Card entity ID. 0 means no this card"
    	::= { onuVendorVersionEntry 5 }

		onuVendorVersionCard2 OBJECT-TYPE
        SYNTAX  INTEGER (0..255)
        MAX-ACCESS  read-write
        STATUS      current
        DESCRIPTION
         "ONU Vendor Version VEIP Card entity ID. 0 means no this card"
    	::= { onuVendorVersionEntry 6 }

		onuVendorVersionCard3 OBJECT-TYPE
        SYNTAX  INTEGER (0..255)
        MAX-ACCESS  read-write
        STATUS      current
        DESCRIPTION
         "ONU Vendor Version POTS Card entity ID. 0 means no this card"
    	::= { onuVendorVersionEntry 7 }

		onuVendorVersionCard4 OBJECT-TYPE
        SYNTAX  INTEGER (0..255)
        MAX-ACCESS  read-write
        STATUS      current
        DESCRIPTION
         "ONU Vendor Version VIDEO Card entity ID. 0 means no this card"
    	::= { onuVendorVersionEntry 8 }

		onuVendorVersionCard5 OBJECT-TYPE
        SYNTAX  INTEGER (0..255)
        MAX-ACCESS  read-write
        STATUS      current
        DESCRIPTION
         "ONU Vendor Version 100M Card entity ID. 0 means no this card"
    	::= { onuVendorVersionEntry 9 }

		onuVendorVersionRowStatus OBJECT-TYPE
        SYNTAX  RowStatus
        MAX-ACCESS  read-create
        STATUS  current
        DESCRIPTION
         "The status of specified ONU Vendor Version entry."
    	::= { onuVendorVersionEntry 10 }

-- *
-- * ontPmRate Table
-- *

--	ontPmRateTable OBJECT IDENTIFIER ::= { remoteOnt 16}

    ontPmRateTable OBJECT-TYPE
        SYNTAX	SEQUENCE OF OntPmRateEntry
        MAX-ACCESS  not-accessible
        STATUS  current
        DESCRIPTION
                 	""
        ::= { remoteOnt 16 }

	ontPmRateEntry OBJECT-TYPE
        SYNTAX      OntPmRateEntry
        MAX-ACCESS  not-accessible
        STATUS      current
        DESCRIPTION
            "An entry in ontPmRateTable,
            ontPmRateDot1dBasePort and ontPmRateOnt need to be set via multiple variable binding."
        INDEX {
            ontPmRateIndex
        }
    	::= { ontPmRateTable 1 }

	OntPmRateEntry ::=
        SEQUENCE {
            ontPmRateDot1dBasePort      INTEGER,
            ontPmRateOnt                INTEGER,
            ontPmRateMonitor            INTEGER,
            ontPmRateIndex              INTEGER

        }

    ontPmRateDot1dBasePort OBJECT-TYPE
        SYNTAX      INTEGER
        MAX-ACCESS  read-write
        STATUS      current
        DESCRIPTION
         	"The dot1dBase port of the ONT that will be monitored."
    	::= { ontPmRateEntry 1}

    ontPmRateOnt OBJECT-TYPE
        SYNTAX      INTEGER
        MAX-ACCESS  read-write
        STATUS      current
        DESCRIPTION
         	"The ONT AID that will be monitored."
    	::= { ontPmRateEntry 2}

    ontPmRateMonitor OBJECT-TYPE
        SYNTAX  INTEGER {
            disable(0),
            enable(1)
        }
        MAX-ACCESS  read-write
        STATUS      current
        DESCRIPTION
         	"Enable or disable the motitored of the ONT."
    	::= { ontPmRateEntry 3}

    ontPmRateIndex OBJECT-TYPE
        SYNTAX      INTEGER
        MAX-ACCESS  not-accessible
        STATUS      current
        DESCRIPTION
         	"The index of the ONT PM rate table."
    	::= { ontPmRateEntry 4}

-- *
-- * ontAclProfile Table
-- *

--   ontAclProfileTable OBJECT IDENTIFIER ::= { remoteOnt 17 }

        ontAclProfileTable OBJECT-TYPE
        SYNTAX  SEQUENCE OF OntAclProfileEntry
        MAX-ACCESS  not-accessible
        STATUS      current
        DESCRIPTION
            ""
            ::= { remoteOnt 17 }

        ontAclProfileEntry OBJECT-TYPE
        SYNTAX  OntAclProfileEntry
        MAX-ACCESS  not-accessible
        STATUS  current
        DESCRIPTION  "An entry in ONT ACL profile table for service rule setting."
        INDEX {
                ontAclProfileName
        }
        ::= { ontAclProfileTable 1 }

        OntAclProfileEntry ::=
        SEQUENCE {
            ontAclProfileName                       OCTET STRING,
            ontAclProfileEnable                     INTEGER,
            ontAclProfilePolicy                     INTEGER,
            ontAclProfileInterface                  INTEGER,
            ontAclProfileIpProtocol                 INTEGER,
            ontAclProfileSourceL4Port               INTEGER,
            ontAclProfileDestinationL4Port          INTEGER,
            ontAclProfileSourceIpAddress            IpAddress,
            ontAclProfileSourceIpMask               INTEGER,
            ontAclProfileDestinationIpAddress       IpAddress,
            ontAclProfileDestinationIpMask          INTEGER,
            ontAclProfileSourceMacAddress           MacAddress,
            ontAclProfileDestinationMacAddress      MacAddress,
            ontAclProfileRowStatus                  RowStatus,
			ontAclProfileCounter					EnabledStatus,
			ontAclProfileLogging					EnabledStatus
        }

        ontAclProfileName OBJECT-TYPE
        SYNTAX  OCTET STRING
        MAX-ACCESS  read-only
        STATUS      current
        DESCRIPTION
            "ONT ACL Profile Name."
        ::= { ontAclProfileEntry 1 }

        ontAclProfileEnable OBJECT-TYPE
        SYNTAX INTEGER {
            disable(0),
            enable(1)
        }
        MAX-ACCESS  read-write
        STATUS      current
        DESCRIPTION
            "Enables or disables the ONT ACL profile."
        ::= { ontAclProfileEntry 2 }

        ontAclProfilePolicy OBJECT-TYPE
        SYNTAX INTEGER {
            drop(0),
            trust(1)
        }
        MAX-ACCESS  read-write
        STATUS      current
        DESCRIPTION
            "Selects specified policy for ONT ACL profile."
        ::= { ontAclProfileEntry 3 }

        ontAclProfileInterface OBJECT-TYPE
        SYNTAX INTEGER {
            lan(0),
            wan(1),
            both(2)
        }
        MAX-ACCESS  read-write
        STATUS      current
        DESCRIPTION
            "Selects specified interface for ONT ACL profile."
        ::= { ontAclProfileEntry 4 }

        ontAclProfileIpProtocol OBJECT-TYPE
        SYNTAX INTEGER  (0..255)
        MAX-ACCESS  read-write
        STATUS      current
        DESCRIPTION
            "Matches specified IP protocol for ONT ACL profile, 255 represents to remove match to IP protocol."
        ::= { ontAclProfileEntry 5 }

        ontAclProfileSourceL4Port OBJECT-TYPE
        SYNTAX INTEGER  (0..65535)
        MAX-ACCESS  read-write
        STATUS      current
        DESCRIPTION
            "Matches specified layer 4 source port for ONT ACL profile, 0 represents to remove match to layer 4 source port."
        ::= { ontAclProfileEntry 6 }

        ontAclProfileDestinationL4Port OBJECT-TYPE
        SYNTAX INTEGER  (0..65535)
        MAX-ACCESS  read-write
        STATUS      current
        DESCRIPTION
            "Matches specified layer 4 destination port for ONT ACL profile, 0 represents to remove match to layer 4 destination port."
        ::= { ontAclProfileEntry 7 }

        ontAclProfileSourceIpAddress OBJECT-TYPE
        SYNTAX  IpAddress
        MAX-ACCESS  read-write
        STATUS      current
        DESCRIPTION
            "Matches specified source IP address for ONT ACL profile, 0.0.0.0 represents to remove match to source IP address."
        ::= { ontAclProfileEntry 8 }

        ontAclProfileSourceIpMask OBJECT-TYPE
        SYNTAX  INTEGER  (0..32)
        MAX-ACCESS  read-write
        STATUS      current
        DESCRIPTION
            "Matches specified source IP range for ONT ACL profile, source IP mask can be 0 if and only if source IP address is 0.0.0.0."
        ::= { ontAclProfileEntry 9 }

        ontAclProfileDestinationIpAddress OBJECT-TYPE
        SYNTAX  IpAddress
        MAX-ACCESS  read-write
        STATUS      current
        DESCRIPTION
            "Matches specified destination IP address for ONT ACL profile, 0.0.0.0 represents to remove match to destination IP address."
        ::= { ontAclProfileEntry 10 }

        ontAclProfileDestinationIpMask OBJECT-TYPE
        SYNTAX  INTEGER  (0..32)
        MAX-ACCESS  read-write
        STATUS      current
        DESCRIPTION
            "Matches specified destination IP range for ONT ACL profile, destination IP mask can be 0 if and only if destination IP address is 0.0.0.0."
        ::= { ontAclProfileEntry 11 }

        ontAclProfileSourceMacAddress OBJECT-TYPE
        SYNTAX  MacAddress
        MAX-ACCESS  read-write
        STATUS  current
        DESCRIPTION
            "Matches specified source MAC address for ONT ACL profile, 00:00:00:00:00:00 represents to remove match to source IP address."
        ::= { ontAclProfileEntry 12 }

        ontAclProfileDestinationMacAddress OBJECT-TYPE
        SYNTAX  MacAddress
        MAX-ACCESS  read-write
        STATUS  current
        DESCRIPTION
            "Matches specified destination MAC address for ONT ACL profile, 00:00:00:00:00:00 represents to remove match to destination IP address."
        ::= { ontAclProfileEntry 13 }

        ontAclProfileRowStatus OBJECT-TYPE
        SYNTAX  RowStatus
        MAX-ACCESS  read-create
        STATUS  current
        DESCRIPTION
            "Row status for ONT ACL profile."
      ::= { ontAclProfileEntry 14 }

        ontAclProfileCounter OBJECT-TYPE
        SYNTAX  EnabledStatus
        MAX-ACCESS  read-write
        STATUS  current
        DESCRIPTION
            "Counter enabled/disabled for ONT ACL profile."
        ::= { ontAclProfileEntry 15 }

        ontAclProfileLogging OBJECT-TYPE
        SYNTAX  EnabledStatus
        MAX-ACCESS  read-write
        STATUS  current
        DESCRIPTION
            "Logging enabled/disabled for ONT ACL profile."
        ::= { ontAclProfileEntry 16 }

-- ******************************************************************
-- *
-- 136.remoteOntInfo mib
-- *
-- ******************************************************************
-- *
-- * ponStatus Table
-- *
	ponStatusTable OBJECT-TYPE
		SYNTAX      SEQUENCE OF PonStatusEntry
        MAX-ACCESS  not-accessible
		STATUS      current
		DESCRIPTION
	            ""
        ::= { remoteOntInfo 2 }

	ponStatusEntry OBJECT-TYPE
        SYNTAX      PonStatusEntry
        MAX-ACCESS  not-accessible
        STATUS      current
        DESCRIPTION
        		"An entry in ponStatusTable"
        INDEX {
        		dot1dBasePort
        }
    	::= { ponStatusTable 1 }

	PonStatusEntry ::=
        SEQUENCE {
            state                         INTEGER,
            oltKeyExchange				  INTEGER,
            snAcq                         INTEGER,
            rogueDectect                  INTEGER,
            rogueDestructState            INTEGER,
            procInterval 			      INTEGER,
            procIntervalSec               INTEGER,
            los                			  INTEGER,
            last                          INTEGER,
            endOfBurstOffset			  INTEGER
   }
 	state OBJECT-TYPE
        SYNTAX INTEGER {
            inactive(0),
            active(1)
        }
        MAX-ACCESS  read-only
        STATUS      current
        DESCRIPTION
         	" state."
    	::= { ponStatusEntry 1 }

   	oltKeyExchange OBJECT-TYPE
        SYNTAX INTEGER {
            disable(0),
            enable(1)
        }
        MAX-ACCESS  read-only
        STATUS      current
        DESCRIPTION
         	" pon keyExchange."
    	::= { ponStatusEntry 2 }

   	snAcq OBJECT-TYPE
        SYNTAX      INTEGER {
            disable(0),
            enable(1)
        }
        MAX-ACCESS  read-only
        STATUS      current
        DESCRIPTION
         	" SNAcq."
    	::= { ponStatusEntry 3 }

    rogueDectect OBJECT-TYPE
        SYNTAX      INTEGER {
            disable(0),
            enable(1)
        }
        MAX-ACCESS  read-only
        STATUS      current
        DESCRIPTION
         	" rogueDectect."
    	::= { ponStatusEntry 4 }

    rogueDestructState OBJECT-TYPE
        SYNTAX      INTEGER {
            disable(0),
            enable(1)
        }
        MAX-ACCESS  read-only
        STATUS      current
        DESCRIPTION
         	" rogueDestructState."
    	::= { ponStatusEntry 5 }

    procInterval OBJECT-TYPE
        SYNTAX      INTEGER
        MAX-ACCESS  read-only
        STATUS      current
        DESCRIPTION
         	" procInterval."
    	::= { ponStatusEntry 6 }

    procIntervalSec OBJECT-TYPE
        SYNTAX      INTEGER
        MAX-ACCESS  read-only
        STATUS      current
        DESCRIPTION
         	" procIntervalSec."
    	::= { ponStatusEntry 7 }

    los OBJECT-TYPE
        SYNTAX      INTEGER {
            off(0),
            on(1)
        }
        MAX-ACCESS  read-only
        STATUS      current
        DESCRIPTION
         	" LOS."
    	::= { ponStatusEntry 8 }


    last OBJECT-TYPE
        SYNTAX      INTEGER
        MAX-ACCESS  read-only
        STATUS      current
        DESCRIPTION
         	" Last."
    	::= { ponStatusEntry 9 }

    endOfBurstOffset OBJECT-TYPE
        SYNTAX      INTEGER
        MAX-ACCESS  read-only
        STATUS      current
        DESCRIPTION
         	" EndofBurstOffset."
    	::= { ponStatusEntry 10 }

-- *
-- * ontStatus Table
-- *
RemoteOnuStatus ::= TEXTUAL-CONVENTION
   STATUS      current
   DESCRIPTION
      "Objects with this syntax are status parameters that reflects the status for a given
       provision entity of an ONU. Each provision entity has different error checking list,
       system reports the first failure when it goes through the list. And therefore when
       it shows a specific OOS type OOS-XX, doesn't mean the OOS-XX is the only failure
       of this entity, but the first failure that user should solve before checking next
       checking item of the list. Status can only be IS when it passes all items in the
       checking list.

       Specified as an INTEGER, the values are:
        OOS(0)     -- Out Of Service - Obsoleted status.
        IS(1)      -- In Service. This entity passes all error checking.
        OOS-LO(2)  -- Out Of Service - Line card Oos. (The related line card is OOS)
        OOS-NR(3)  -- Out Of Service - Not Registered. (ONU is not registered)
        OOS-CD(4)  -- Out Of Service - omcC Down. (The OMCC is blocked)
        OOS-NP(5)  -- Out Of Service - Not Provisioned. (This entity is not ever provisioned)
        OOS-PF(6)  -- Out Of Service - Provision Failed. (ONU replies error during provision)
        OOS-AD(7)  -- Out Of Service - Admin Down. (The entity is down administratively)
        OOS-OD(8)  -- Out Of Service - Oper Down. (ONU reports it can't perform its function)
        OOS-OO(9)  -- Out Of Service - Onu Oos. (The related ONU is OOS)
        OOS-TM(10)  -- Out Of Service - Type Mismatch. (The actual type mismatches with config
                                       type)
        OOS-CO(11) -- Out Of Service - onu Card Oos. (The related onu card is OOS)
        OOS-UO(12) -- Out Of Service - Uni Oos. (The related UNI is OOS)
        OOS-NO(13) -- Out Of Service - Nni Oos. (The related NNI is OOS)
        OOS-GS(14) -- Out Of Service - Gem Suspended. (One or many of the related GEM ports
                                       are temporarily closed)
        OOS-GF(15) -- Out Of Service - Gem Failure. (One or many of the related GEM ports
                                       fails during creation)
        OOS-AF(16) -- Out Of Service - Allocid Failure. (One or many of the related allocation
                                       ID fails during creation)
        OOS-VO(17) -- Out Of Service - Vlan Oos. (The related VLAN service is OOS)
        OOS-DG(18) -- Out Of Service - Dying Gasp. (ONU was ever registered, after that, it was
                                       deregistered due to loss of power)
        OOS-LS(19) -- Out Of Service - Loss of Signal. (ONU was ever registered, after that, it was
                                       deregistered due to loss of signal)
        OOS-SB(20) -- Out Of Service - StandBy. (ONU is in standby mode in a protection group)"
   SYNTAX      INTEGER {
                  oos(0),
                  is(1),
                  oosLO(2),
                  oosNR(3),
                  oosCD(4),
                  oosNP(5),
                  oosPF(6),
                  oosAD(7),
                  oosOD(8),
                  oosOO(9),
                  oosTM(10),
                  oosCO(11),
                  oosUO(12),
                  oosNO(13),
                  oosGS(14),
                  oosGF(15),
                  oosAF(16),
                  oosVO(17),
                  oosDG(18),
                  oosLS(19),
                  oosSB(20)
               }

	ontStatusTable OBJECT IDENTIFIER ::= { remoteOntInfo 3 }

-- 	ontCurrentStatusTable
    ontCurrentStatusTable OBJECT-TYPE
        SYNTAX	SEQUENCE OF OntCurrentStatusEntry
        MAX-ACCESS  not-accessible
        STATUS  current
        DESCRIPTION
                 	""
        ::= { ontStatusTable 1 }

	ontCurrentStatusEntry OBJECT-TYPE
        SYNTAX      OntCurrentStatusEntry
        MAX-ACCESS  not-accessible
        STATUS      current
       DESCRIPTION
        		"An entry in ontCurrentStatusTable"
        INDEX {
        		dot1dBasePort,
        		ontNumber
        }
    	::= { ontCurrentStatusTable 1 }

	OntCurrentStatusEntry ::=
        SEQUENCE {
            serialNumber                  DisplayString,
            passwordOnt                   DisplayString,
            ontStatus                     INTEGER,
            versionA                      DisplayString,
            versionB                      DisplayString,
            actVersion                    INTEGER,
            estimatedDistance             Unsigned32,
            pppoeStatus                   INTEGER,
            onuVersion                    DisplayString,
            wanIp                         IpAddress,
            ontStatusElapsedTime          Unsigned32,
            onuModelName                  DisplayString,
            onuModelId                    INTEGER,
            upgradeStatus                 INTEGER,
            wanConfigurable               TruthValue,
            ontWanControlable		  BITS,
            ontLanControlable		  BITS,
            ontWifiControlable		  BITS,
            ontAcsControlable		  BITS,
            ontServiceControlable	  BITS,
            ontUpnpControlable		  BITS,
            ontDmzControlable		  BITS,
            ontFirewallControlable	  BITS
        }


    serialNumber OBJECT-TYPE
        SYNTAX      DisplayString
        MAX-ACCESS  read-only
        STATUS      current
        DESCRIPTION
         	" Serial Number."
    	::= { ontCurrentStatusEntry 1}

    passwordOnt OBJECT-TYPE
        SYNTAX      DisplayString
        MAX-ACCESS  read-only
        STATUS      current
        DESCRIPTION
         	" Ont password."
    	::= { ontCurrentStatusEntry 2}

    ontStatus OBJECT-TYPE
        SYNTAX      RemoteOnuStatus
        MAX-ACCESS  read-only
        STATUS      current
        DESCRIPTION
         	" ONT status."
    	::= { ontCurrentStatusEntry 3}

	versionA OBJECT-TYPE
        SYNTAX  DisplayString
        MAX-ACCESS  read-only
        STATUS  current
        DESCRIPTION
                "versionA"
        ::= { ontCurrentStatusEntry 4 }

	versionB OBJECT-TYPE
        SYNTAX  DisplayString
        MAX-ACCESS  read-only
        STATUS  current
        DESCRIPTION
                "versionB"
        ::= { ontCurrentStatusEntry 5 }

    actVersion OBJECT-TYPE
        SYNTAX      INTEGER {
            none(0),
            versionA(1),
            versionB(2)
        }
        MAX-ACCESS  read-only
        STATUS      current
        DESCRIPTION
         	" actVersion."
    	::= { ontCurrentStatusEntry 6}

    estimatedDistance  OBJECT-TYPE
        SYNTAX      Unsigned32
        UNITS       "meter"
        MAX-ACCESS  read-only
        STATUS      current
        DESCRIPTION
            "The estimated distance to the ONT."
        ::= { ontCurrentStatusEntry 7 }

    pppoeStatus OBJECT-TYPE
        SYNTAX      INTEGER {
            down(0),
            up(1),
            notAvailable(2)
        }
        MAX-ACCESS  read-only
        STATUS      current
        DESCRIPTION
         	"This item reports the PPPoE session status of the ONT."
    	::= { ontCurrentStatusEntry 8}

     onuVersion OBJECT-TYPE
        SYNTAX      DisplayString
        MAX-ACCESS  read-only
        STATUS      current
        DESCRIPTION
               "This item indicates the ONU version defined by the vendor."
    	::= { ontCurrentStatusEntry 9}

     wanIp OBJECT-TYPE
        SYNTAX  IpAddress
        MAX-ACCESS  read-only
        STATUS  current
        DESCRIPTION
               "WAN IP address of this ONU."
        ::= { ontCurrentStatusEntry 10 }

     ontStatusElapsedTime OBJECT-TYPE
        SYNTAX  Unsigned32
        MAX-ACCESS  read-only
        STATUS  current
        DESCRIPTION
               "The elapsed time since the ont status changed. (in seconds)."
        ::= { ontCurrentStatusEntry 11 }

     onuModelName OBJECT-TYPE
        SYNTAX      DisplayString
        MAX-ACCESS  read-only
        STATUS      current
        DESCRIPTION
               "This item indicates the model name of the entry in the ONU vendor table that matches this ONU."
    	::= { ontCurrentStatusEntry 12}

     onuModelId OBJECT-TYPE
        SYNTAX  INTEGER {
            default(0),
            pmg1006ORpmg2006ORpmg1005ORpmg2005(1),
            pmg5318b20a(2),
            pmg3000b20a(3),
            na1(4),
            gpt2542gnaucORpmg5318b20bORpmg5318b20cORpmg5317ORpmg5323(5),
            o00xx0vpq(6),
            na2(7),
            gpt2820gnORgpt2840gnORgpt2841hntORgpt2840hnt(8)
        }
        MAX-ACCESS  read-only
        STATUS  current
        DESCRIPTION
               "This item indicates the model ID of the entry in the ONU vendor table that matches this ONU."
        ::= { ontCurrentStatusEntry 13 }

     upgradeStatus OBJECT-TYPE
        SYNTAX      INTEGER {
            idle(0),
            matched(1),
            downloading(2),
            successful(3),
            failed(4),
            failedWhtiOntDown(5),
            notFoundTheMatchImage(6),
            noPlannedVer(7),
            timeout(8),
            ontNotReady(9),
            swdlQueueFull(10),
            inDownloadingQueue(11),
            inWaitingQueue(12),
            mismatched(13),
            changeToImage1(14),
            changeToImage2(15),
            noImage(16),
            alreadySuccess(17),
            alreadyChangeToImage1(18),
            alreadyChangeToImage2(19),
            ontProcessing(20)
        }
        MAX-ACCESS  read-only
        STATUS  current
        DESCRIPTION
               "The upgrade status of this ONU.
               0. The upgrade status is idle.
               1. The planned version of the ont and the action version of the ONT match.
               2. The ONT start to download the FW.
               3. The ONT upgraded FW successesful.
               4. The ONT upgraded FW failed.
               5. The ONT upgraded FW failed because ONT down.
               6. Not found the matching image with the planned version.
               7. The ONT does not set the planned version.
               8. The ONT upgraded FW failed because timeout.
               9. The ONT status is not ready.
               10. The FW upgrading waiting queue is full.
               11. The ONT is in downloading queue.
               12. The ONT is in waiting queue.
               13. The ONT action version and the planned version mismatch.
               14. Change to Image(1).
               15. Change to Image(2).
               16. No ONT image on OLT.
               17. Already successeful.
               18. Already changed to image(1) successefully.
               19. Already chagned to image(2) successefully.
               20. ONT processing."
        ::= { ontCurrentStatusEntry 14 }

        wanConfigurable OBJECT-TYPE
        SYNTAX  TruthValue
        MAX-ACCESS  read-only
        STATUS  current
        DESCRIPTION
               "This item indicates that if the wan interface of this ONU is configurable by OLT"
        ::= { ontCurrentStatusEntry 15 }

		ontWanControlable OBJECT-TYPE
		SYNTAX	BITS {
			support(0),
			supportBinding(1),
			supportMvlan(2)
		}
		MAX-ACCESS  read-only
		STATUS  current
		DESCRIPTION
			"support:		support partial WAN config; 
			supportBinding:	support WAN port/wifi binding config; 
			supportMvlan:	support MVLAN setting"
		::= { ontCurrentStatusEntry 16 }

		ontLanControlable OBJECT-TYPE
		SYNTAX	BITS {
			support(0),
			supportDns(1)
		}
		MAX-ACCESS  read-only
		STATUS  current
		DESCRIPTION
			"support:	support LAN config; 
			supportDns:	support LAN DNS config"
		::= { ontCurrentStatusEntry 17 }

		ontWifiControlable OBJECT-TYPE
		SYNTAX	BITS {
			support(0)
		}
		MAX-ACCESS  read-only
		STATUS  current
		DESCRIPTION
			"support:	support Wi-Fi config"
		::= { ontCurrentStatusEntry 18 }

		ontAcsControlable OBJECT-TYPE
		SYNTAX	BITS {
			support(0)
		}
		MAX-ACCESS  read-only
		STATUS  current
		DESCRIPTION
			"support:	support ACS config"
		::= { ontCurrentStatusEntry 19 }
		
		ontServiceControlable OBJECT-TYPE
		SYNTAX	BITS {
			support(0)
		}
		MAX-ACCESS  read-only
		STATUS  current
		DESCRIPTION
			"support:	support service config(ftp,http,snmp,...)"
		::= { ontCurrentStatusEntry 20 }

		ontUpnpControlable OBJECT-TYPE
		SYNTAX	BITS {
			support(0)
		}
		MAX-ACCESS  read-only
		STATUS  current
		DESCRIPTION
			"support:	support UPnP config"
		::= { ontCurrentStatusEntry 21 }

		ontDmzControlable OBJECT-TYPE
		SYNTAX	BITS {
			support(0)
		}
		MAX-ACCESS  read-only
		STATUS  current
		DESCRIPTION
			"support:	support DMZ config"
		::= { ontCurrentStatusEntry 22 }

		ontFirewallControlable OBJECT-TYPE
		SYNTAX	BITS {
			support(0)
		}
		MAX-ACCESS  read-only
		STATUS  current
		DESCRIPTION
			"support:	support DMZ config"
		::= { ontCurrentStatusEntry 23 }

-- 	ontCountersTable

    ontCountersTable OBJECT-TYPE
        SYNTAX	SEQUENCE OF OntCountersEntry
        MAX-ACCESS  not-accessible
        STATUS  current
        DESCRIPTION
                 	" ontCountersTable"
      ::= { ontStatusTable 4 }

		ontCountersEntry OBJECT-TYPE
        SYNTAX      OntCountersEntry
        MAX-ACCESS  not-accessible
        STATUS      current
       	DESCRIPTION
        		"An entry in ontCountersTable"
        INDEX {
        		dot1dBasePort,
        		ontNumber
        }
    	::= { ontCountersTable 1 }

		OntCountersEntry ::=
        SEQUENCE {
            ontCountersUnreceivedBursts          Counter32,
            ontCountersPositiveDriftBits         Counter32,
            ontCountersNegativeDriftBits         Counter32,
						ontCountersBip8Errors            		Counter32,
            ontCountersCorrectedBytes            Counter32,
            ontCountersCorrectedCodewords        Counter32,
            ontCountersUncorrctableCodewords     Counter32,
						ontCountersTotalReceivedCodewords	  Counter32,
						ontCountersDsBer        							Counter32
   	}

    ontCountersUnreceivedBursts OBJECT-TYPE
        SYNTAX      Counter32
        MAX-ACCESS  read-only
        STATUS      current
        DESCRIPTION
         	" Unreceived bursts."
    	::= { ontCountersEntry 1}

    ontCountersPositiveDriftBits OBJECT-TYPE
        SYNTAX      Counter32
        MAX-ACCESS  read-only
        STATUS      current
        DESCRIPTION
         	" Positive drift (bits)."
    	::= { ontCountersEntry 2}

    ontCountersNegativeDriftBits OBJECT-TYPE
        SYNTAX      Counter32
        MAX-ACCESS  read-only
        STATUS      current
        DESCRIPTION
         	" Negative drift (bits)."
    	::= { ontCountersEntry 3}

    ontCountersBip8Errors OBJECT-TYPE
        SYNTAX      Counter32
        MAX-ACCESS  read-only
        STATUS      current
        DESCRIPTION
         	" Bip8 errors."
    	::= { ontCountersEntry 4}

    ontCountersCorrectedBytes OBJECT-TYPE
        SYNTAX      Counter32
        MAX-ACCESS  read-only
        STATUS      current
        DESCRIPTION
         	" Corrected Bytes."
    	::= { ontCountersEntry 5}

    ontCountersCorrectedCodewords OBJECT-TYPE
        SYNTAX      Counter32
        MAX-ACCESS  read-only
        STATUS      current
        DESCRIPTION
         	" Corrected Codewords."
    	::= { ontCountersEntry 6}

    ontCountersUncorrctableCodewords OBJECT-TYPE
        SYNTAX      Counter32
        MAX-ACCESS  read-only
        STATUS      current
        DESCRIPTION
         	" Uncorrctable Codewords."
    	::= { ontCountersEntry 7}

		ontCountersTotalReceivedCodewords OBJECT-TYPE
        SYNTAX      Counter32
        MAX-ACCESS  read-only
        STATUS      current
        DESCRIPTION
         	" Total received Codewords."
    	::= { ontCountersEntry 8}

    ontCountersDsBer OBJECT-TYPE
        SYNTAX      Counter32
        MAX-ACCESS  read-only
        STATUS      current
        DESCRIPTION
         	" DS BER (REI)."
    	::= { ontCountersEntry 9}

--  ontBwGroupStatusTable

    ontBwGroupStatusTable OBJECT-TYPE
        SYNTAX      SEQUENCE OF OntBwGroupStatusEntry
        MAX-ACCESS  not-accessible
        STATUS  current
        DESCRIPTION
        ""
        ::= { ontStatusTable 5 }

    ontBwGroupStatusEntry OBJECT-TYPE
        SYNTAX      OntBwGroupStatusEntry
        MAX-ACCESS  not-accessible
        STATUS	current
        DESCRIPTION
            "An entry in ontBwGroupStatusTable"
        INDEX {
            dot1dBasePort,
            ontNumber,
            ontBwGroupId
        }
        ::= { ontBwGroupStatusTable 1 }

    OntBwGroupStatusEntry ::=
    SEQUENCE {
        ontBwGroupStatusAllocId        INTEGER,
        ontBwGroupStatusCurrUsDataRate   INTEGER
    }

    ontBwGroupStatusAllocId OBJECT-TYPE
    SYNTAX  INTEGER
    MAX-ACCESS  read-only
    STATUS  current
    DESCRIPTION
        "This MIB reports the allocation ID assigned to this bandwidth group."
    ::= { ontBwGroupStatusEntry 1 }

    ontBwGroupStatusCurrUsDataRate OBJECT-TYPE
    SYNTAX  INTEGER
    MAX-ACCESS  read-only
    STATUS  current
    DESCRIPTION
        "This MIB reports the actual upstream data rate calculated by OLT in bps."
    ::= { ontBwGroupStatusEntry 2 }

--  ontWanStatusTable

    ontWanStatusTable OBJECT-TYPE
        SYNTAX      SEQUENCE OF OntWanStatusEntry
        MAX-ACCESS  not-accessible
        STATUS  current
        DESCRIPTION
        ""
        ::= { ontStatusTable 6 }

    ontWanStatusEntry OBJECT-TYPE
        SYNTAX      OntWanStatusEntry
        MAX-ACCESS  not-accessible
        STATUS	current
        DESCRIPTION
            "An entry in ontWanStatusTable"
        INDEX {
            dot1dBasePort,
            ontNumber,
            ontWanId
        }
        ::= { ontWanStatusTable 1 }

    OntWanStatusEntry ::=
    SEQUENCE {
		ontWanId                   INTEGER,
        ontWanStatusEnable         INTEGER,
        ontWanStatusType           INTEGER,
        ontWanStatusLinkStatus     INTEGER,
		ontWanStatusServiceType    BITS,
		ontWanStatusVlan           INTEGER,
		ontWanStatusPriority       INTEGER,
		ontWanStatusIpMode         INTEGER,
		ontWanStatusIp             IpAddress,
		ontWanStatusMask           IpAddress,
		ontWanStatusGateway        IpAddress,
		ontWanStatusPrimaryDns     IpAddress,
		ontWanStatusSecondDns      IpAddress,
		ontWanStatusNat            INTEGER,
        ontWanStatusGetState       INTEGER,

        ontWanStatusUsername                DisplayString,
        ontWanStatusPassword                DisplayString,
        ontWanStatusConnectionDefault       TruthValue,
        ontWanStatusBridgePortBinding       BITS,
        ontWanStatusWifiSSIDBinding         BITS,
        ontWanStatusWifi5GSSIDBinding       BITS,
		ontWanStatusMvlan           		INTEGER
    }

    ontWanId OBJECT-TYPE
    SYNTAX  INTEGER (1..8)
    MAX-ACCESS  not-accessible
    STATUS  current
    DESCRIPTION
        " ont wan Id"
    ::= { ontWanStatusEntry 1 }

    ontWanStatusEnable OBJECT-TYPE
	SYNTAX      INTEGER {
		disable(0),
		enable(1)
	}
    MAX-ACCESS  read-only
    STATUS  current
    DESCRIPTION
        "This MIB reports the wan status type."
    ::= { ontWanStatusEntry 2 }

    ontWanStatusType OBJECT-TYPE
	SYNTAX      INTEGER {
		ipoe(0),
		pppoe(1),
		bridging(2)
	}
    MAX-ACCESS  read-only
    STATUS  current
    DESCRIPTION
        "This MIB reports the wan status type."
    ::= { ontWanStatusEntry 3 }

    ontWanStatusLinkStatus OBJECT-TYPE
	SYNTAX      INTEGER {
		down(0),
		up(1)
	}
    MAX-ACCESS  read-only
    STATUS  current
    DESCRIPTION
        "This MIB reports the wan status."
    ::= { ontWanStatusEntry 4 }

    ontWanStatusServiceType OBJECT-TYPE
	SYNTAX	BITS {
		data(0),
		voip(1),
        tr069(2),
		iptv(3)
	}
    MAX-ACCESS  read-only
    STATUS  current
    DESCRIPTION
        "This MIB reports the wan status."
    ::= { ontWanStatusEntry 5 }

    ontWanStatusVlan OBJECT-TYPE
	SYNTAX      INTEGER
    MAX-ACCESS  read-only
    STATUS  current
    DESCRIPTION
        "This MIB reports the wan vlan."
    ::= { ontWanStatusEntry 6 }

    ontWanStatusPriority OBJECT-TYPE
	SYNTAX      INTEGER
    MAX-ACCESS  read-only
    STATUS  current
    DESCRIPTION
        "This MIB reports the wan proirity."
    ::= { ontWanStatusEntry 7 }

    ontWanStatusIpMode OBJECT-TYPE
	SYNTAX      INTEGER {
		disable(0),
		enable(1)
	}
    MAX-ACCESS  read-only
    STATUS  current
    DESCRIPTION
        "This MIB reports the wan ip mode."
    ::= { ontWanStatusEntry 8 }

    ontWanStatusIp OBJECT-TYPE
	SYNTAX      IpAddress
    MAX-ACCESS  read-only
    STATUS  current
    DESCRIPTION
        "This MIB reports the wan IP."
    ::= { ontWanStatusEntry 9 }

    ontWanStatusMask OBJECT-TYPE
	SYNTAX      IpAddress
    MAX-ACCESS  read-only
    STATUS  current
    DESCRIPTION
        "This MIB reports the wan IP mask."
    ::= { ontWanStatusEntry 10 }

    ontWanStatusGateway  OBJECT-TYPE
	SYNTAX      IpAddress
    MAX-ACCESS  read-only
    STATUS  current
    DESCRIPTION
        "This MIB reports the wan IP gateway."
    ::= { ontWanStatusEntry 11 }

    ontWanStatusPrimaryDns  OBJECT-TYPE
	SYNTAX      IpAddress
    MAX-ACCESS  read-only
    STATUS  current
    DESCRIPTION
        "This MIB reports the wan primary dns."
    ::= { ontWanStatusEntry 12 }

    ontWanStatusSecondDns  OBJECT-TYPE
	SYNTAX      IpAddress
    MAX-ACCESS  read-only
    STATUS  current
    DESCRIPTION
        "This MIB reports the wan second dns."
    ::= { ontWanStatusEntry 13 }

    ontWanStatusNat OBJECT-TYPE
	SYNTAX      INTEGER {
		disable(0),
		enable(1)
	}
    MAX-ACCESS  read-only
    STATUS  current
    DESCRIPTION
        "This MIB reports the wan nat status."
    ::= { ontWanStatusEntry 14 }

    ontWanStatusGetState OBJECT-TYPE
	SYNTAX      INTEGER {
		idle(0),
		processing(1)
	}
    MAX-ACCESS  read-write
    STATUS  current
    DESCRIPTION
        "This MIB reports get wan status state."
    ::= { ontWanStatusEntry 15 }

    ontWanStatusUsername OBJECT-TYPE
    SYNTAX   DisplayString
    MAX-ACCESS  read-only
    STATUS  current
    DESCRIPTION
        "This MIB reports the PPPoE username."
    ::= { ontWanStatusEntry 16 }

    ontWanStatusPassword OBJECT-TYPE
    SYNTAX   DisplayString
    MAX-ACCESS  read-only
    STATUS  current
    DESCRIPTION
        "This MIB reports the PPPoE password."
    ::= { ontWanStatusEntry 17 }

    ontWanStatusConnectionDefault OBJECT-TYPE
    SYNTAX   TruthValue
    MAX-ACCESS  read-only
    STATUS  current
    DESCRIPTION
        "This MIB reports if this wan is the default gateway."
    ::= { ontWanStatusEntry 18 }

    ontWanStatusBridgePortBinding OBJECT-TYPE
    SYNTAX   BITS
    MAX-ACCESS  read-only
    STATUS  current
    DESCRIPTION
        "This MIB reports the lan port binding of this wan."
    ::= { ontWanStatusEntry 19 }

    ontWanStatusWifiSSIDBinding OBJECT-TYPE
    SYNTAX   BITS
    MAX-ACCESS  read-only
    STATUS  current
    DESCRIPTION
        "This MIB reports the wifi(2.4G) bindind of this wan."
    ::= { ontWanStatusEntry 20 }

    ontWanStatusWifi5GSSIDBinding OBJECT-TYPE
    SYNTAX   BITS
    MAX-ACCESS  read-only
    STATUS  current
    DESCRIPTION
        "This MIB reports the wifi(5G) binding of this wan."
    ::= { ontWanStatusEntry 21 }

	ontWanStatusMvlan OBJECT-TYPE
		SYNTAX      INTEGER
		MAX-ACCESS  read-only
		STATUS  current
		DESCRIPTION
			"This MIB reports the wan Mvlan."
		::= { ontWanStatusEntry 22 }

--  ontStatusHistTable

    ontStatusHistTable OBJECT-TYPE
        SYNTAX      SEQUENCE OF OntStatusHistEntry
        MAX-ACCESS  not-accessible
        STATUS  current
        DESCRIPTION
        "This table stores the most recent 16 records of the ONU status,
         each entry contains status and the time when it changes to the status."
        ::= { ontStatusTable 7 }

    ontStatusHistEntry OBJECT-TYPE
        SYNTAX      OntStatusHistEntry
        MAX-ACCESS  not-accessible
        STATUS	current
        DESCRIPTION
            "An entry of the ontStatusHistTable"
        INDEX {
            dot1dBasePort,
            ontNumber,
            ontStatusHistIdx
        }
        ::= { ontStatusHistTable 1 }

    OntStatusHistEntry ::=
    SEQUENCE {
		ontStatusHistIdx           INTEGER,
        	ontStatusHistStatus        INTEGER,
        	ontStatusHistYear          INTEGER,
        	ontStatusHistMonth         INTEGER,
        	ontStatusHistDay           INTEGER,
        	ontStatusHistHour          INTEGER,
        	ontStatusHistMin           INTEGER,
        	ontStatusHistSec           INTEGER
    }

    ontStatusHistIdx OBJECT-TYPE
    SYNTAX  INTEGER (1..16)
    MAX-ACCESS  not-accessible
    STATUS  current
    DESCRIPTION
        "The entry index of the ONU status history. 1 indicates the newest status record,
        while 16 indicates the oldest. Therefore the entry content will shift when the
        table is full and new status is being updated."
    ::= { ontStatusHistEntry 1 }

    ontStatusHistStatus OBJECT-TYPE
    SYNTAX  RemoteOnuStatus
    MAX-ACCESS  read-only
    STATUS  current
    DESCRIPTION
        "The ONU status for this entry."
    ::= { ontStatusHistEntry 2 }

    ontStatusHistYear OBJECT-TYPE
    SYNTAX  INTEGER
    MAX-ACCESS  read-only
    STATUS  current
    DESCRIPTION
        "The year of the time when the ONU changed to the status."
    ::= { ontStatusHistEntry 3 }

    ontStatusHistMonth OBJECT-TYPE
    SYNTAX  INTEGER
    MAX-ACCESS  read-only
    STATUS  current
    DESCRIPTION
        "The month of the time when the ONU changed to the status."
    ::= { ontStatusHistEntry 4 }

    ontStatusHistDay OBJECT-TYPE
    SYNTAX  INTEGER
    MAX-ACCESS  read-only
    STATUS  current
    DESCRIPTION
        "The day of the time when the ONU changed to the status."
    ::= { ontStatusHistEntry 5 }

    ontStatusHistHour OBJECT-TYPE
    SYNTAX  INTEGER
    MAX-ACCESS  read-only
    STATUS  current
    DESCRIPTION
        "The hour of the time when the ONU changed to the status."
    ::= { ontStatusHistEntry 6 }

    ontStatusHistMin OBJECT-TYPE
    SYNTAX  INTEGER
    MAX-ACCESS  read-only
    STATUS  current
    DESCRIPTION
        "The minute of the time when the ONU changed to the status."
    ::= { ontStatusHistEntry 7 }

    ontStatusHistSec OBJECT-TYPE
    SYNTAX  INTEGER
    MAX-ACCESS  read-only
    STATUS  current
    DESCRIPTION
        "The second of the time when the ONU changed to the status."
    ::= { ontStatusHistEntry 8 }

--  ontStormingStatusTable

    ontStormingStatusTable OBJECT-TYPE
        SYNTAX      SEQUENCE OF OntStormingStatusEntry
        MAX-ACCESS  not-accessible
        STATUS  current
        DESCRIPTION
        "This table can display the status of ONT storm, loopguard, and DDoS."
        ::= { ontStatusTable 8 }

    ontStormingStatusEntry OBJECT-TYPE
        SYNTAX      OntStormingStatusEntry
        MAX-ACCESS  not-accessible
        STATUS	current
        DESCRIPTION
            "An entry of the ontStormingTable"
        INDEX {
            dot1dBasePort,
            ontNumber
        }
        ::= { ontStormingStatusTable 1 }

    OntStormingStatusEntry ::=
    SEQUENCE {
        	ontStormingBcastOverThr         INTEGER,
        	ontStormingMcastOverThr         INTEGER,
        	ontStormingUnknowOverThr        INTEGER,
        	ontStormingDdosArpDetect        INTEGER,
        	ontStormingDdosTcpDetect        INTEGER,
        	ontStormingDdosUdpDetect        INTEGER,
        	ontStormingLoopguardDetect      INTEGER
    }

    ontStormingBcastOverThr OBJECT-TYPE
    SYNTAX  INTEGER{
           na(0),
           no(1),
           yes(2)
    }
    MAX-ACCESS  read-only
    STATUS  current
    DESCRIPTION
        "The status of ONT broadcast control over threshold."
    ::= { ontStormingStatusEntry 1 }

    ontStormingMcastOverThr OBJECT-TYPE
    SYNTAX  INTEGER{
           na(0),
           no(1),
           yes(2)
    }
    MAX-ACCESS  read-only
    STATUS  current
    DESCRIPTION
        "The status of ONT multicast control over threshold."
    ::= { ontStormingStatusEntry 2 }

    ontStormingUnknowOverThr OBJECT-TYPE
    SYNTAX  INTEGER{
           na(0),
           no(1),
           yes(2)
    }
    MAX-ACCESS  read-only
    STATUS  current
    DESCRIPTION
        "The entry display the status of ONT unknown unicast control over threshold."
    ::= { ontStormingStatusEntry 3 }

    ontStormingDdosArpDetect OBJECT-TYPE
    SYNTAX  INTEGER{
           na(0),
           no(1),
           yes(2)
    }
    MAX-ACCESS  read-only
    STATUS  current
    DESCRIPTION
        "The status of ONT DDoS ARP detected."
    ::= { ontStormingStatusEntry 4 }

    ontStormingDdosTcpDetect OBJECT-TYPE
    SYNTAX  INTEGER{
           na(0),
           no(1),
           yes(2)
    }
    MAX-ACCESS  read-only
    STATUS  current
    DESCRIPTION
        "The status of ONT DDoS TCP detected."
    ::= { ontStormingStatusEntry 5 }

    ontStormingDdosUdpDetect OBJECT-TYPE
    SYNTAX  INTEGER{
           na(0),
           no(1),
           yes(2)
    }
    MAX-ACCESS  read-only
    STATUS  current
    DESCRIPTION
        "The status of ONT DDoS UDP detected."
    ::= { ontStormingStatusEntry 6 }

    ontStormingLoopguardDetect OBJECT-TYPE
    SYNTAX  INTEGER{
           na(0),
           no(1),
           yes(2)
    }
    MAX-ACCESS  read-only
    STATUS  current
    DESCRIPTION
        "The status of ONT loopguard detected."
    ::= { ontStormingStatusEntry 7 }

--  ontAclServiceStatusTable

    ontAclServiceStatusTable OBJECT-TYPE
        SYNTAX      SEQUENCE OF OntAclServiceStatusEntry
        MAX-ACCESS  not-accessible
        STATUS  current
        DESCRIPTION
        ""
        ::= { ontStatusTable 9 }

    ontAclServiceStatusEntry OBJECT-TYPE
        SYNTAX      OntAclServiceStatusEntry
        MAX-ACCESS  not-accessible
        STATUS	current
        DESCRIPTION
            "An entry in ontAclServiceStatusTable"
        INDEX {
            dot1dBasePort,
            ontNumber,
            ontAclRuleId
        }
        ::= { ontAclServiceStatusTable 1 }

    OntAclServiceStatusEntry ::=
    SEQUENCE {
        ontAclServiceStatusState         DisplayString,
        ontAclServiceStatusProfileName	DisplayString,
		ontAclServiceCounter			Counter32
    }

    ontAclServiceStatusState OBJECT-TYPE
    SYNTAX  DisplayString
    MAX-ACCESS  read-only
    STATUS  current
    DESCRIPTION
        "This MIB reports the state assigned to this ACL service rule ID."
    ::= { ontAclServiceStatusEntry 1 }

    ontAclServiceStatusProfileName OBJECT-TYPE
    SYNTAX  DisplayString
    MAX-ACCESS  read-only
    STATUS  current
    DESCRIPTION
        "This MIB reports the ONT profile name assigned to this ACL service rule ID."
    ::= { ontAclServiceStatusEntry 2 }

	ontAclServiceCounter OBJECT-TYPE
	SYNTAX  Counter32
	MAX-ACCESS  read-only
	STATUS  current
	DESCRIPTION
		"Counter for the ONT profile name assigned to this ACL service rule."
	::= { ontAclServiceStatusEntry 3 }

--  ontLanportStatusTable
    ontLanportStatusTable OBJECT-TYPE
        SYNTAX      SEQUENCE OF OntLanportStatusEntry
        MAX-ACCESS  not-accessible
        STATUS  current
        DESCRIPTION
        ""
        ::= { ontStatusTable 10 }

    ontLanportStatusEntry OBJECT-TYPE
        SYNTAX      OntLanportStatusEntry
        MAX-ACCESS  not-accessible
        STATUS	current
        DESCRIPTION
            "An entry in ontLanportStatusTable"
        INDEX {
            dot1dBasePort,
            ontNumber,
            ontLanportIndex
        }
        ::= { ontLanportStatusTable 1 }

    OntLanportStatusEntry ::=
    SEQUENCE {
        ontLanportIndex         INTEGER,
        ontLanportOperationState	INTEGER,
		ontLanportSpeedDuplex			INTEGER
    }

    ontLanportIndex OBJECT-TYPE
    SYNTAX  INTEGER (1..6)
    MAX-ACCESS  read-only
    STATUS  current
    DESCRIPTION
        "Ethernet port index."
    ::= { ontLanportStatusEntry 1 }

    ontLanportOperationState OBJECT-TYPE
    SYNTAX  INTEGER{
           disable(0),
           linkdown(1),
           linkup(2)
    }
    MAX-ACCESS  read-only
    STATUS  current
    DESCRIPTION
        "Link state of Ethernet port."
    ::= { ontLanportStatusEntry 2 }

	ontLanportSpeedDuplex OBJECT-TYPE
    SYNTAX  INTEGER {
        unknown(0),
        speed10baseFull(1),
        speed100baseFull(2),
        speed1GbaseFull(3),
        speed10GbaseFull(4),
        speed10baseHalf(5),
        speed100baseHalf(6),
        speed1GbaseHalf(7)
    }
	MAX-ACCESS  read-only
	STATUS  current
	DESCRIPTION
		"Link speed and duplex of Ethernet port."
	::= { ontLanportStatusEntry 3 }

--  ontVoipStatusTable
    ontVoipStatusTable OBJECT-TYPE
        SYNTAX      SEQUENCE OF OntVoipStatusEntry
        MAX-ACCESS  not-accessible
        STATUS  current
        DESCRIPTION
        ""
        ::= { ontStatusTable 11 }

    ontVoipStatusEntry OBJECT-TYPE
        SYNTAX      OntVoipStatusEntry
        MAX-ACCESS  not-accessible
        STATUS	current
        DESCRIPTION
            "An entry in ontVoipStatusTable"
        INDEX {
            dot1dBasePort,
            ontNumber,
            ontVoipIndex
        }
        ::= { ontVoipStatusTable 1 }

    OntVoipStatusEntry ::=
    SEQUENCE {
        ontVoipIndex         INTEGER,
        voipLineStatus	INTEGER,
		registrationStatus			INTEGER
    }

    ontVoipIndex OBJECT-TYPE
    SYNTAX  INTEGER (1..6)
    MAX-ACCESS  read-only
    STATUS  current
    DESCRIPTION
        "POTS/VOIP index."
    ::= { ontVoipStatusEntry 1 }

    voipLineStatus OBJECT-TYPE
    SYNTAX  INTEGER{
           disable(255),
           on_hook(0),
           off_hook(1),
           dialing(2),
           ringing(3),
           ringback(4),
           connecting(5),
           connected(6),
           disconnecting(7),
           receiver_off_hook_no_tone(8),
           receiver_off_hook_with_tone(9),
           unknown(10)
    }
    MAX-ACCESS  read-only
    STATUS  current
    DESCRIPTION
        "Link state of subscriber line."
    ::= { ontVoipStatusEntry 2 }

	registrationStatus OBJECT-TYPE
    SYNTAX  INTEGER{
           initial(0),
           registered(1),
           in_session(2),
           reg_fail_icmp(3),
           reg_fail_tcp(4),
           reg_fail_auth(5),
           reg_fail_timeout(6),
           reg_fail_code(7),
           invite_fail_icmp(8),
           invite_fail_tcp(9),
           invite_fail_auth(10),
           invite_fail_timeout(11),
           invite_fail_code(12),
           port_not_configured(13),
           config_done(14),
           disabled_by_switch(15),
           unknown(16)
    }
	MAX-ACCESS  read-only
	STATUS  current
	DESCRIPTION
		"Registration status of POTS/VOIP."
	::= { ontVoipStatusEntry 3 }
    
--  ontVideoPortStatusTable
    ontVideoPortStatusTable OBJECT-TYPE
        SYNTAX      SEQUENCE OF OntVideoPortStatusEntry
        MAX-ACCESS  not-accessible
        STATUS  current
        DESCRIPTION
        ""
        ::= { ontStatusTable 12 }

    ontVideoPortStatusEntry OBJECT-TYPE
        SYNTAX      OntVideoPortStatusEntry
        MAX-ACCESS  not-accessible
        STATUS	current
        DESCRIPTION
            "An entry in ontVideoPortStatusTable"
        INDEX {
            dot1dBasePort,
            ontNumber,
            ontVideoIndex
        }
        ::= { ontVideoPortStatusTable 1 }

    OntVideoPortStatusEntry ::=
    SEQUENCE {
        ontVideoPortIndex			INTEGER,
        ontVideoPortAdminState		INTEGER,
        ontVideoPortOperationState	INTEGER
    }

    ontVideoPortIndex OBJECT-TYPE
    SYNTAX  INTEGER (1..6)
    MAX-ACCESS  read-only
    STATUS  current
    DESCRIPTION
        "Video port index."
    ::= { ontVideoPortStatusEntry 1 }

    ontVideoPortAdminState OBJECT-TYPE
    SYNTAX  INTEGER{
           locks(1),
           unlocks(2)
    }
    MAX-ACCESS  read-only
    STATUS  current
    DESCRIPTION
        "Administrative state of video port."
    ::= { ontVideoPortStatusEntry 2 }

    ontVideoPortOperationState OBJECT-TYPE
    SYNTAX  INTEGER{
           disabled(1),
           enabled(2)
    }
    MAX-ACCESS  read-only
    STATUS  current
    DESCRIPTION
        "Operational state of video port."
    ::= { ontVideoPortStatusEntry 3 }
	
-- *
-- * ontCard Status Table
-- *
	ontCardStatusTable OBJECT-TYPE
		SYNTAX      SEQUENCE OF OntCardStatusEntry
        MAX-ACCESS  not-accessible
		STATUS      current
		DESCRIPTION
	            ""
        ::= { remoteOntInfo 4 }

	ontCardStatusEntry OBJECT-TYPE
        SYNTAX      OntCardStatusEntry
        MAX-ACCESS  not-accessible
        STATUS      current
        DESCRIPTION
        		"An entry in ontCardStatusTable"
        INDEX {
        		ifIndex,
        		ontNumber,
        		ontcard
        }
    	::= { ontCardStatusTable 1 }

	OntCardStatusEntry ::=
        SEQUENCE {
            status                        INTEGER,
            adminState				  	  INTEGER,
--            opState                       INTEGER,
            expectType                    INTEGER,
            actualType            	   	  INTEGER,
            expectedPort 			      INTEGER,
            actualPort               	  INTEGER
   }

	status OBJECT-TYPE
        SYNTAX RemoteOnuStatus
        MAX-ACCESS  read-only
        STATUS      current
        DESCRIPTION
         	" ONT card status."
    	::= { ontCardStatusEntry 1 }

	adminState OBJECT-TYPE
        SYNTAX      INTEGER {
        	unlocked(0),
            locked(1)
        }

        MAX-ACCESS  read-only
        STATUS      current
        DESCRIPTION
         	" adminState."
    	::= { ontCardStatusEntry 2 }

--	opState OBJECT-TYPE
--        SYNTAX      INTEGER {
--        	enabled(0),
--            disabled(1)
--        }
--        MAX-ACCESS  read-only
--        STATUS      current
--        DESCRIPTION
--         	" OpState."
--    	::= { ontCardStatusEntry 3 }

	expectType OBJECT-TYPE
        SYNTAX      INTEGER {
        	ether(0),
            veip(1),
            pots(2),
            xdsl(3),
            giga(4),
            video(5),
            unknow(6)
        }
        MAX-ACCESS  read-only
        STATUS      current
        DESCRIPTION
         	" expectType."
    	::= { ontCardStatusEntry 4 }

	actualType OBJECT-TYPE
        SYNTAX      INTEGER {
        	ether(0),
            veip(1),
            pots(2),
            xdsl(3),
            giga(4),
            video(5),
            unknow(6)
        }
        MAX-ACCESS  read-only
        STATUS      current
        DESCRIPTION
         	" actualType."
    	::= { ontCardStatusEntry 5 }

	expectedPort OBJECT-TYPE
        SYNTAX      INTEGER
        MAX-ACCESS  read-only
        STATUS      current
        DESCRIPTION
         	" expectedPort."
    	::= { ontCardStatusEntry 6 }

	actualPort OBJECT-TYPE
        SYNTAX      INTEGER
        MAX-ACCESS  read-only
        STATUS      current
        DESCRIPTION
         	" actualPort."
    	::= { ontCardStatusEntry 7 }



-- *
-- * ontDdmiStatus Table
-- *

--	ontDdmiStatusTable OBJECT IDENTIFIER ::= { remoteOntInfo 5}

    ontDdmiStatusTable OBJECT-TYPE
        SYNTAX	SEQUENCE OF OntDdmiStatusEntry
        MAX-ACCESS  not-accessible
        STATUS  current
        DESCRIPTION
                 	""
        ::= { remoteOntInfo 5 }

	ontDdmiStatusEntry OBJECT-TYPE
        SYNTAX      OntDdmiStatusEntry
        MAX-ACCESS  not-accessible
        STATUS      current
       DESCRIPTION
        		"An entry in ontDdmiStatusTable"
        INDEX {
        		dot1dBasePort,
        		ontNumber
        }
    	::= { ontDdmiStatusTable 1 }

	OntDdmiStatusEntry ::=
        SEQUENCE {
            voltage                  DisplayString,
            rxPower                  DisplayString,
            txPower                  DisplayString,
			laserCurrent	         DisplayString,
			ontTemperature           DisplayString,
			ontDdmiRowStatus         EnabledStatus,
			ontDdmiStatus         INTEGER

   }


    voltage OBJECT-TYPE
        SYNTAX      DisplayString
        MAX-ACCESS  read-only
        STATUS      current
        DESCRIPTION
         	" ONT Voltage (V)."
    	::= { ontDdmiStatusEntry 1}

    rxPower OBJECT-TYPE
        SYNTAX      DisplayString
        MAX-ACCESS  read-only
        STATUS      current
        DESCRIPTION
         	" ONT Rx power (dbm)."
    	::= { ontDdmiStatusEntry 2}

	txPower OBJECT-TYPE
        SYNTAX      DisplayString
        MAX-ACCESS  read-only
        STATUS      current
        DESCRIPTION
         	" ONT Tx power (dbm)."
    	::= { ontDdmiStatusEntry 3}

    laserCurrent OBJECT-TYPE
        SYNTAX      DisplayString
        MAX-ACCESS  read-only
        STATUS      current
        DESCRIPTION
         	" ONT Laser Bias current (mA)."
    	::= { ontDdmiStatusEntry 4}

	ontTemperature OBJECT-TYPE
        SYNTAX      DisplayString
        MAX-ACCESS  read-only
        STATUS      current
        DESCRIPTION
         	" ONT Temperature (C)."
    	::= { ontDdmiStatusEntry 5}

	ontDdmiRowStatus OBJECT-TYPE
        SYNTAX      EnabledStatus
        MAX-ACCESS  read-write
        STATUS      current
        DESCRIPTION
         ""
        ::= { ontDdmiStatusEntry 6 }

	ontDdmiStatus OBJECT-TYPE
        SYNTAX      INTEGER {
        	none(0),
          waiting(1),
          processing(2),
          done(3)
        }
        MAX-ACCESS  read-only
        STATUS      current
        DESCRIPTION
         	" ontDdmiStatus."
        ::= { ontDdmiStatusEntry 7 }

-- *
-- * ontEnetPmCounters Table
-- *

	ontEnetPmCounters OBJECT IDENTIFIER ::= { remoteOntInfo 6}

    ontEnetCurrentPmCountersTable OBJECT-TYPE
        SYNTAX	SEQUENCE OF OntEnetCurrentPmCountersEntry
        MAX-ACCESS  not-accessible
        STATUS  current
        DESCRIPTION
                 	""
        ::= { ontEnetPmCounters 1 }

	ontEnetCurrentPmCountersEntry OBJECT-TYPE
        SYNTAX      OntEnetCurrentPmCountersEntry
        MAX-ACCESS  not-accessible
        STATUS      current
       DESCRIPTION
        		"An entry in ontEnetPmCounters"
        INDEX {
        		dot1dBasePort,
        		ontNumber,
        		ontcard,
        		ontenetCardPort
        }
    	::= { ontEnetCurrentPmCountersTable 1 }

	OntEnetCurrentPmCountersEntry ::=
        SEQUENCE {
            ontEnetCurrentPmUsOctets                  Counter64,
            ontEnetCurrentPmUsPackets                 Counter64,
            ontEnetCurrentPmUsMcastPackets            Counter64,
            ontEnetCurrentPmUsBcastPackets            Counter64,
            ontEnetCurrentPmDsOctets                  Counter64,
            ontEnetCurrentPmDsPackets                 Counter64,
            ontEnetCurrentPmDsMcastPackets            Counter64,
            ontEnetCurrentPmDsBcastPackets            Counter64,
            ontEnetPmCountersGetCurrent           EnabledStatus,
            ontEnetPmCountersCheckGetCurrent            INTEGER,
   }


    ontEnetCurrentPmUsOctets OBJECT-TYPE
        SYNTAX      Counter64
        MAX-ACCESS  read-only
        STATUS      current
        DESCRIPTION
         	" ONT enet PM counters up stream octets."
    	::= { ontEnetCurrentPmCountersEntry 1}

    ontEnetCurrentPmUsPackets OBJECT-TYPE
        SYNTAX      Counter64
        MAX-ACCESS  read-only
        STATUS      current
        DESCRIPTION
         	" ONT enet PM counters up stream packets."
    	::= { ontEnetCurrentPmCountersEntry 2}

	ontEnetCurrentPmUsMcastPackets OBJECT-TYPE
        SYNTAX      Counter64
        MAX-ACCESS  read-only
        STATUS      current
        DESCRIPTION
         	" ONT enet PM counters up stream mcast packets."
    	::= { ontEnetCurrentPmCountersEntry 3}

    ontEnetCurrentPmUsBcastPackets OBJECT-TYPE
        SYNTAX      Counter64
        MAX-ACCESS  read-only
        STATUS      current
        DESCRIPTION
         	" ONT enet PM counters up stream bcast packets."
    	::= { ontEnetCurrentPmCountersEntry 4}

    ontEnetCurrentPmDsOctets OBJECT-TYPE
        SYNTAX      Counter64
        MAX-ACCESS  read-only
        STATUS      current
        DESCRIPTION
         	" ONT enet PM counters ds stream octets."
    	::= { ontEnetCurrentPmCountersEntry 5}

    ontEnetCurrentPmDsPackets OBJECT-TYPE
        SYNTAX      Counter64
        MAX-ACCESS  read-only
        STATUS      current
        DESCRIPTION
         	" ONT enet PM counters ds stream packets."
    	::= { ontEnetCurrentPmCountersEntry 6}

	ontEnetCurrentPmDsMcastPackets OBJECT-TYPE
        SYNTAX      Counter64
        MAX-ACCESS  read-only
        STATUS      current
        DESCRIPTION
         	" ONT enet PM counters ds stream mcast packets."
    	::= { ontEnetCurrentPmCountersEntry 7}

    ontEnetCurrentPmDsBcastPackets OBJECT-TYPE
        SYNTAX      Counter64
        MAX-ACCESS  read-only
        STATUS      current
        DESCRIPTION
         	" ONT enet PM counters ds stream bcast packets."
    	::= { ontEnetCurrentPmCountersEntry 8}

	ontEnetPmCountersGetCurrent OBJECT-TYPE
        SYNTAX      EnabledStatus
        MAX-ACCESS  read-write
        STATUS      current
        DESCRIPTION
         ""
        ::= { ontEnetCurrentPmCountersEntry 9 }

	ontEnetPmCountersCheckGetCurrent OBJECT-TYPE
       SYNTAX      INTEGER {
        standby(0),
        processing(1)
        }
        MAX-ACCESS  read-only
        STATUS      current
        DESCRIPTION
         ""
        ::= { ontEnetCurrentPmCountersEntry 10 }

--  ontEnetLast15PmCountersEntry
    ontEnetLast15PmCountersTable OBJECT-TYPE
        SYNTAX	SEQUENCE OF OntEnetLast15PmCountersEntry
        MAX-ACCESS  not-accessible
        STATUS  current
        DESCRIPTION
                 	""
        ::= { ontEnetPmCounters 2 }

	ontEnetLast15PmCountersEntry OBJECT-TYPE
        SYNTAX      OntEnetLast15PmCountersEntry
        MAX-ACCESS  not-accessible
        STATUS      current
       DESCRIPTION
        		"An entry in ontEnetPmCounters"
        INDEX {
        		dot1dBasePort,
        		ontNumber,
        		ontcard,
        		ontenetCardPort
        }
    	::= { ontEnetLast15PmCountersTable 1 }

	OntEnetLast15PmCountersEntry ::=
        SEQUENCE {
            ontEnetLast15PmUsOctets                  Counter64,
            ontEnetLast15PmUsPackets                 Counter64,
            ontEnetLast15PmUsMcastPackets            Counter64,
            ontEnetLast15PmUsBcastPackets            Counter64,
            ontEnetLast15PmDsOctets                  Counter64,
            ontEnetLast15PmDsPackets                 Counter64,
            ontEnetLast15PmDsMcastPackets            Counter64,
            ontEnetLast15PmDsBcastPackets	         Counter64,
            ontEnetLast15PmInterval     	         Counter32
   }

    ontEnetLast15PmUsOctets OBJECT-TYPE
        SYNTAX      Counter64
        MAX-ACCESS  read-only
        STATUS      current
        DESCRIPTION
         	" ONT enet PM counters up stream octets."
    	::= { ontEnetLast15PmCountersEntry 1}

    ontEnetLast15PmUsPackets OBJECT-TYPE
        SYNTAX      Counter64
        MAX-ACCESS  read-only
        STATUS      current
        DESCRIPTION
         	" ONT enet PM counters up stream packets."
    	::= { ontEnetLast15PmCountersEntry 2}

	ontEnetLast15PmUsMcastPackets OBJECT-TYPE
        SYNTAX      Counter64
        MAX-ACCESS  read-only
        STATUS      current
        DESCRIPTION
         	" ONT enet PM counters up stream mcast packets."
    	::= { ontEnetLast15PmCountersEntry 3}

    ontEnetLast15PmUsBcastPackets OBJECT-TYPE
        SYNTAX      Counter64
        MAX-ACCESS  read-only
        STATUS      current
        DESCRIPTION
         	" ONT enet PM counters up stream bcast packets."
    	::= { ontEnetLast15PmCountersEntry 4}

    ontEnetLast15PmDsOctets OBJECT-TYPE
        SYNTAX      Counter64
        MAX-ACCESS  read-only
        STATUS      current
        DESCRIPTION
         	" ONT enet PM counters ds stream octets."
    	::= { ontEnetLast15PmCountersEntry 5}

    ontEnetLast15PmDsPackets OBJECT-TYPE
        SYNTAX      Counter64
        MAX-ACCESS  read-only
        STATUS      current
        DESCRIPTION
         	" ONT enet PM counters ds stream packets."
    	::= { ontEnetLast15PmCountersEntry 6}

	ontEnetLast15PmDsMcastPackets OBJECT-TYPE
        SYNTAX      Counter64
        MAX-ACCESS  read-only
        STATUS      current
        DESCRIPTION
         	" ONT enet PM counters ds stream mcast packets."
    	::= { ontEnetLast15PmCountersEntry 7}

    ontEnetLast15PmDsBcastPackets OBJECT-TYPE
        SYNTAX      Counter64
        MAX-ACCESS  read-only
        STATUS      current
        DESCRIPTION
         	" ONT enet PM counters ds stream bcast packets."
    	::= { ontEnetLast15PmCountersEntry 8}

    ontEnetLast15PmInterval OBJECT-TYPE
        SYNTAX      Counter32
        MAX-ACCESS  read-only
        STATUS      current
        DESCRIPTION
         	" ONT enet PM counters Interval."
    	::= { ontEnetLast15PmCountersEntry 9}

    ontEnetStatus OBJECT IDENTIFIER ::= { remoteOntInfo 7}

    ontEnetStatusTable OBJECT-TYPE
        SYNTAX	SEQUENCE OF OntEnetStatusEntry
        MAX-ACCESS  not-accessible
        STATUS  current
        DESCRIPTION
                 	""
        ::= { ontEnetStatus 1 }

	ontEnetStatusEntry OBJECT-TYPE
        SYNTAX      OntEnetStatusEntry
        MAX-ACCESS  not-accessible
        STATUS      current
       DESCRIPTION
        		"An entry in ontEnetStatus"
        INDEX {
        		dot1dBasePort,
        		ontNumber,
        		ontcard,
        		ontenetCardPort
        }
    	::= { ontEnetStatusTable 1 }

	OntEnetStatusEntry ::=
        SEQUENCE {
            ontEnetPortStatus                  INTEGER
               }


    ontEnetPortStatus OBJECT-TYPE
        SYNTAX      RemoteOnuStatus
        MAX-ACCESS  read-only
        STATUS      current
        DESCRIPTION
         	" ONT enet ME provision status."
    	::= { ontEnetStatusEntry 1}

-- *
-- * ontVenetPmCounters Table
-- *

	ontVenetPmCounters OBJECT IDENTIFIER ::= { remoteOntInfo 8}

    ontVenetCurrentPmCountersTable OBJECT-TYPE
        SYNTAX	SEQUENCE OF OntVenetCurrentPmCountersEntry
        MAX-ACCESS  not-accessible
        STATUS  current
        DESCRIPTION
                 	""
        ::= { ontVenetPmCounters 1 }

	ontVenetCurrentPmCountersEntry OBJECT-TYPE
        SYNTAX      OntVenetCurrentPmCountersEntry
        MAX-ACCESS  not-accessible
        STATUS      current
       DESCRIPTION
        		"An entry in ontVenetPmCounters"
        INDEX {
        		dot1dBasePort,
        		ontNumber,
        		ontcard,
        		ontenetCardPort
        }
    	::= { ontVenetCurrentPmCountersTable 1 }

	OntVenetCurrentPmCountersEntry ::=
        SEQUENCE {
            ontVenetCurrentPmUsOctets                  Counter64,
            ontVenetCurrentPmUsPackets                 Counter64,
            ontVenetCurrentPmUsMcastPackets            Counter64,
            ontVenetCurrentPmUsBcastPackets            Counter64,
            ontVenetCurrentPmDsOctets                  Counter64,
            ontVenetCurrentPmDsPackets                 Counter64,
            ontVenetCurrentPmDsMcastPackets            Counter64,
            ontVenetCurrentPmDsBcastPackets            Counter64,
            ontVenetPmCountersGetCurrent           EnabledStatus,
            ontVenetPmCountersCheckGetCurrent            INTEGER
		}

    ontVenetCurrentPmUsOctets OBJECT-TYPE
        SYNTAX      Counter64
        MAX-ACCESS  read-only
        STATUS      current
        DESCRIPTION
         	" ONT venet PM counters Upstream Octets Cont."
    	::= { ontVenetCurrentPmCountersEntry 1}

    ontVenetCurrentPmUsPackets OBJECT-TYPE
        SYNTAX      Counter64
        MAX-ACCESS  read-only
        STATUS      current
        DESCRIPTION
         	" ONT venet PM counters Upstream Packets Count."
    	::= { ontVenetCurrentPmCountersEntry 2}

	ontVenetCurrentPmUsMcastPackets OBJECT-TYPE
        SYNTAX      Counter64
        MAX-ACCESS  read-only
        STATUS      current
        DESCRIPTION
         	" ONT venet PM counters Upstream Multicast Packets Count."
    	::= { ontVenetCurrentPmCountersEntry 3}

    ontVenetCurrentPmUsBcastPackets OBJECT-TYPE
        SYNTAX      Counter64
        MAX-ACCESS  read-only
        STATUS      current
        DESCRIPTION
         	" ONT venet PM counters Upstream Broadcast Packets Count."
    	::= { ontVenetCurrentPmCountersEntry 4}

    ontVenetCurrentPmDsOctets OBJECT-TYPE
        SYNTAX      Counter64
        MAX-ACCESS  read-only
        STATUS      current
        DESCRIPTION
         	" ONT venet PM counters Downstream Octets Cont."
    	::= { ontVenetCurrentPmCountersEntry 5}

    ontVenetCurrentPmDsPackets OBJECT-TYPE
        SYNTAX      Counter64
        MAX-ACCESS  read-only
        STATUS      current
        DESCRIPTION
         	" ONT venet PM counters Downstream Packets Count."
    	::= { ontVenetCurrentPmCountersEntry 6}

	ontVenetCurrentPmDsMcastPackets OBJECT-TYPE
        SYNTAX      Counter64
        MAX-ACCESS  read-only
        STATUS      current
        DESCRIPTION
         	" ONT venet PM counters Downstream Multicast Packets Count."
    	::= { ontVenetCurrentPmCountersEntry 7}

    ontVenetCurrentPmDsBcastPackets OBJECT-TYPE
        SYNTAX      Counter64
        MAX-ACCESS  read-only
        STATUS      current
        DESCRIPTION
         	" ONT venet PM counters Downstream Broadcast Packets Count."
    	::= { ontVenetCurrentPmCountersEntry 8}

	ontVenetPmCountersGetCurrent OBJECT-TYPE
        SYNTAX      EnabledStatus
        MAX-ACCESS  read-write
        STATUS      current
        DESCRIPTION
         ""
        ::= { ontVenetCurrentPmCountersEntry 9 }

	ontVenetPmCountersCheckGetCurrent OBJECT-TYPE
       SYNTAX      INTEGER {
        standby(0),
        processing(1)
        }
        MAX-ACCESS  read-only
        STATUS      current
        DESCRIPTION
         ""
        ::= { ontVenetCurrentPmCountersEntry 10 }

--  ontVenetLast15PmCountersEntry
    ontVenetLast15PmCountersTable OBJECT-TYPE
        SYNTAX	SEQUENCE OF OntVenetLast15PmCountersEntry
        MAX-ACCESS  not-accessible
        STATUS  current
        DESCRIPTION
                 	""
        ::= { ontVenetPmCounters 2 }

	ontVenetLast15PmCountersEntry OBJECT-TYPE
        SYNTAX      OntVenetLast15PmCountersEntry
        MAX-ACCESS  not-accessible
        STATUS      current
       DESCRIPTION
        		"An entry in ontVenetPmCounters"
        INDEX {
        		dot1dBasePort,
        		ontNumber,
        		ontcard,
        		ontenetCardPort
        }
    	::= { ontVenetLast15PmCountersTable 1 }

	OntVenetLast15PmCountersEntry ::=
        SEQUENCE {
            ontVenetLast15PmUsOctets                  Counter64,
            ontVenetLast15PmUsPackets                 Counter64,
            ontVenetLast15PmUsMcastPackets            Counter64,
            ontVenetLast15PmUsBcastPackets            Counter64,
            ontVenetLast15PmDsOctets                  Counter64,
            ontVenetLast15PmDsPackets                 Counter64,
            ontVenetLast15PmDsMcastPackets            Counter64,
            ontVenetLast15PmDsBcastPackets            Counter64,
            ontVenetLast15PmInterval                  Counter32
   }

    ontVenetLast15PmUsOctets OBJECT-TYPE
        SYNTAX      Counter64
        MAX-ACCESS  read-only
        STATUS      current
        DESCRIPTION
         	" ONT venet PM counters Upstream Octets Count."
    	::= { ontVenetLast15PmCountersEntry 1}

	ontVenetLast15PmUsPackets OBJECT-TYPE
        SYNTAX      Counter64
        MAX-ACCESS  read-only
        STATUS      current
        DESCRIPTION
         	" ONT venet PM counters Upstream Packets Count."
    	::= { ontVenetLast15PmCountersEntry 2}

    ontVenetLast15PmUsMcastPackets OBJECT-TYPE
        SYNTAX      Counter64
        MAX-ACCESS  read-only
        STATUS      current
        DESCRIPTION
         	" ONT venet PM counters Upstream Multicast Packets Count."
    	::= { ontVenetLast15PmCountersEntry 3}

    ontVenetLast15PmUsBcastPackets OBJECT-TYPE
        SYNTAX      Counter64
        MAX-ACCESS  read-only
        STATUS      current
        DESCRIPTION
         	" ONT venet PM counters Upstream Broadcast Packets Count."
    	::= { ontVenetLast15PmCountersEntry 4}

    ontVenetLast15PmDsOctets OBJECT-TYPE
        SYNTAX      Counter64
        MAX-ACCESS  read-only
        STATUS      current
        DESCRIPTION
         	" ONT venet PM counters Downstream Octets Count."
    	::= { ontVenetLast15PmCountersEntry 5}

	ontVenetLast15PmDsPackets OBJECT-TYPE
        SYNTAX      Counter64
        MAX-ACCESS  read-only
        STATUS      current
        DESCRIPTION
         	" ONT venet PM counters Downstream Packets Count."
    	::= { ontVenetLast15PmCountersEntry 6}

    ontVenetLast15PmDsMcastPackets OBJECT-TYPE
        SYNTAX      Counter64
        MAX-ACCESS  read-only
        STATUS      current
        DESCRIPTION
         	" ONT venet PM counters Downstream Multicast Packets Count."
    	::= { ontVenetLast15PmCountersEntry 7}

    ontVenetLast15PmDsBcastPackets OBJECT-TYPE
        SYNTAX      Counter64
        MAX-ACCESS  read-only
        STATUS      current
        DESCRIPTION
         	" ONT venet PM counters Downstream Broadcast Packets Count."
    	::= { ontVenetLast15PmCountersEntry 8}

    ontVenetLast15PmInterval OBJECT-TYPE
        SYNTAX      Counter32
        MAX-ACCESS  read-only
        STATUS      current
        DESCRIPTION
         	" ONT venet PM counters Interval."
    	::= { ontVenetLast15PmCountersEntry 9}

-- *
-- * ontVenetStatusInfo Table
-- *
	 ontVenetStatusInfo OBJECT IDENTIFIER ::= { remoteOntInfo 9}

    ontVenetStatusTable OBJECT-TYPE
        SYNTAX	SEQUENCE OF OntVenetStatusEntry
        MAX-ACCESS  not-accessible
        STATUS  current
        DESCRIPTION
                 	""
        ::= { ontVenetStatusInfo 1 }

	ontVenetStatusEntry OBJECT-TYPE
        SYNTAX      OntVenetStatusEntry
        MAX-ACCESS  not-accessible
        STATUS      current
       DESCRIPTION
        		"An entry in ontVenetStatusInfo"
        INDEX {
        		dot1dBasePort,
        		ontNumber,
        		ontcard,
        		ontvenetCardPort
        }
    	::= { ontVenetStatusTable 1 }

	OntVenetStatusEntry ::=
        SEQUENCE {
            ontVenetStatus                  INTEGER
               }


    ontVenetStatus OBJECT-TYPE
        SYNTAX      RemoteOnuStatus
        MAX-ACCESS  read-only
        STATUS      current
        DESCRIPTION
         	" ONT Venet ME provision status."
    	::= { ontVenetStatusEntry 1}

-- *
-- * ontPotsStatusInfo Table
-- *
	 ontPotsStatusInfo OBJECT IDENTIFIER ::= { remoteOntInfo 10}

    ontPotsStatusTable OBJECT-TYPE
        SYNTAX	SEQUENCE OF OntPotsStatusEntry
        MAX-ACCESS  not-accessible
        STATUS  current
        DESCRIPTION
                 	""
        ::= { ontPotsStatusInfo 1 }

	ontPotsStatusEntry OBJECT-TYPE
        SYNTAX      OntPotsStatusEntry
        MAX-ACCESS  not-accessible
        STATUS      current
       DESCRIPTION
        		"An entry in ontPotsStatusInfo"
        INDEX {
        		dot1dBasePort,
        		ontNumber,
        		ontcard,
        		ontpotsCardPort
        }
    	::= { ontPotsStatusTable 1 }

	OntPotsStatusEntry ::=
        SEQUENCE {
            ontPotsStatus                  INTEGER
               }


    ontPotsStatus OBJECT-TYPE
        SYNTAX      RemoteOnuStatus
        MAX-ACCESS  read-only
        STATUS      current
        DESCRIPTION
         	" ONT Pots ME provision status."
    	::= { ontPotsStatusEntry 1}

-- *
-- * ontUniportStatusInfo Table
-- *
	 ontUniportStatusInfo OBJECT IDENTIFIER ::= { remoteOntInfo 11}

--	uniportVlanStatusTable
        uniportVlanStatusTable OBJECT-TYPE
        SYNTAX	SEQUENCE OF UniportVlanStatusEntry
        MAX-ACCESS  not-accessible
        STATUS  current
        DESCRIPTION
                 	""
        ::= { ontUniportStatusInfo 1 }

	uniportVlanStatusEntry OBJECT-TYPE
        SYNTAX      UniportVlanStatusEntry
        MAX-ACCESS  not-accessible
        STATUS      current
       DESCRIPTION
        		"An entry in uniportVlanStatusInfo"
        INDEX {
        		dot1dBasePort,
        		ontNumber,
        		ontcard,
        		uniPort,
				uniportVlanUniSvid,
				uniportVlanUniCvid
        }
    	::= { uniportVlanStatusTable 1 }

	UniportVlanStatusEntry ::=
        SEQUENCE {
            uniportVlanStatus                  INTEGER
               }


        uniportVlanStatus OBJECT-TYPE
        SYNTAX      RemoteOnuStatus
        MAX-ACCESS  read-only
        STATUS      current
        DESCRIPTION
         	" uniport VLAN ME provision status."
    	::= { uniportVlanStatusEntry 1}

    ontVideoStatus OBJECT IDENTIFIER ::= { remoteOntInfo 12}

    ontVideoStatusTable OBJECT-TYPE
        SYNTAX	SEQUENCE OF OntVideoStatusEntry
        MAX-ACCESS  not-accessible
        STATUS  current
        DESCRIPTION
                 	""
        ::= { ontVideoStatus 1 }

	ontVideoStatusEntry OBJECT-TYPE
        SYNTAX      OntVideoStatusEntry
        MAX-ACCESS  not-accessible
        STATUS      current
       DESCRIPTION
        		"An entry in ontVideoStatus"
        INDEX {
        		dot1dBasePort,
        		ontNumber,
        		ontcard,
        		ontvideoPort
        }
    	::= { ontVideoStatusTable 1 }

	OntVideoStatusEntry ::=
        SEQUENCE {
            ontVideoPortStatus                  INTEGER
               }


    ontVideoPortStatus OBJECT-TYPE
        SYNTAX      RemoteOnuStatus
        MAX-ACCESS  read-only
        STATUS      current
        DESCRIPTION
         	"ontVideo provision status."
    	::= { ontVideoStatusEntry 1}

-- *
-- * ontDdmiHistory Table
-- *

--	ontDdmiHistoryTable OBJECT IDENTIFIER ::= { remoteOntInfo 13}

    ontDdmiHistoryTable OBJECT-TYPE
        SYNTAX	SEQUENCE OF OntDdmiHistoryEntry
        MAX-ACCESS  not-accessible
        STATUS  current
        DESCRIPTION
                 	""
        ::= { remoteOntInfo 13 }

	ontDdmiHistoryEntry OBJECT-TYPE
        SYNTAX      OntDdmiHistoryEntry
        MAX-ACCESS  not-accessible
        STATUS      current
       DESCRIPTION
        		"An entry in ontDdmiHistoryTable"
        INDEX {
        		dot1dBasePort,
        		ontNumber,
        		timeSlot
        }
    	::= { ontDdmiHistoryTable 1 }

	OntDdmiHistoryEntry ::=
        SEQUENCE {
            ontDdmiHistoryVoltage15M                  DisplayString,
            ontDdmiHistoryRxPower15M                  DisplayString,
            ontDdmiHistoryTxPower15M                  DisplayString,
						ontDdmiHistoryLaserCurrent15M	         DisplayString,
						ontDdmiHistoryTemperature15M           DisplayString,
						ontDdmiHistoryUpdateTime15M           DisplayString
   }


   ontDdmiHistoryVoltage15M OBJECT-TYPE
        SYNTAX      DisplayString
        MAX-ACCESS  read-only
        STATUS      current
        DESCRIPTION
         	" update ONT Voltage (V) every 15 minutes."
    	::= { ontDdmiHistoryEntry 1}

    ontDdmiHistoryRxPower15M OBJECT-TYPE
        SYNTAX      DisplayString
        MAX-ACCESS  read-only
        STATUS      current
        DESCRIPTION
         	" update ONT Rx power (dbm) every 15 minutes."
    	::= { ontDdmiHistoryEntry 2}

		ontDdmiHistoryTxPower15M OBJECT-TYPE
        SYNTAX      DisplayString
        MAX-ACCESS  read-only
        STATUS      current
        DESCRIPTION
         	" update ONT Tx power (dbm) every 15 minutes."
    	::= { ontDdmiHistoryEntry 3}

    ontDdmiHistoryLaserCurrent15M OBJECT-TYPE
        SYNTAX      DisplayString
        MAX-ACCESS  read-only
        STATUS      current
        DESCRIPTION
         	" update ONT Laser Bias current (mA) every 15 minutes."
    	::= { ontDdmiHistoryEntry 4}

		ontDdmiHistoryTemperature15M OBJECT-TYPE
        SYNTAX      DisplayString
        MAX-ACCESS  read-only
        STATUS      current
        DESCRIPTION
         	" update ONT Temperature (C) every 15 minutes."
    	::= { ontDdmiHistoryEntry 5}

		ontDdmiHistoryUpdateTime15M OBJECT-TYPE
        SYNTAX      DisplayString
        MAX-ACCESS  read-only
        STATUS      current
        DESCRIPTION
         	" record update time of each ONT ddmi history entry."
    	::= { ontDdmiHistoryEntry 6}

-- *
-- * ontDdmiLatest15Min Table
-- *

--	ontDdmiLatest15MTable OBJECT IDENTIFIER ::= { remoteOntInfo 14}

    ontDdmiLatest15MTable OBJECT-TYPE
        SYNTAX	SEQUENCE OF OntDdmiLatest15MEntry
        MAX-ACCESS  not-accessible
        STATUS  current
        DESCRIPTION
                 	""
        ::= { remoteOntInfo 14 }

	ontDdmiLatest15MEntry OBJECT-TYPE
        SYNTAX      OntDdmiLatest15MEntry
        MAX-ACCESS  not-accessible
        STATUS      current
       DESCRIPTION
        		"An entry in ontDdmiLatest15MTable"
        INDEX {
        		dot1dBasePort,
        		ontNumber
        }
    	::= { ontDdmiLatest15MTable 1 }

	OntDdmiLatest15MEntry ::=
        SEQUENCE {
            ontDdmiLatest15MVoltage                  DisplayString,
            ontDdmiLatest15MRxPower                  DisplayString,
            ontDdmiLatest15MTxPower                  DisplayString,
						ontDdmiLatest15MLaserCurrent	         DisplayString,
						ontDdmiLatest15MTemperature           DisplayString
   }

    ontDdmiLatest15MVoltage OBJECT-TYPE
        SYNTAX      DisplayString
        MAX-ACCESS  read-only
        STATUS      current
        DESCRIPTION
         	" get ONT Voltage (V) within latest 15 minutes."
    	::= { ontDdmiLatest15MEntry 1}

    ontDdmiLatest15MRxPower OBJECT-TYPE
        SYNTAX      DisplayString
        MAX-ACCESS  read-only
        STATUS      current
        DESCRIPTION
         	" get ONT Rx power (dbm) within latest 15 minutes."
    	::= { ontDdmiLatest15MEntry 2}

		ontDdmiLatest15MTxPower OBJECT-TYPE
        SYNTAX      DisplayString
        MAX-ACCESS  read-only
        STATUS      current
        DESCRIPTION
         	" get ONT Tx power (dbm) within latest 15 minutes."
    	::= { ontDdmiLatest15MEntry 3}

    ontDdmiLatest15MLaserCurrent OBJECT-TYPE
        SYNTAX      DisplayString
        MAX-ACCESS  read-only
        STATUS      current
        DESCRIPTION
         	" get ONT Laser Bias current (mA) within latest 15 minutes."
    	::= { ontDdmiLatest15MEntry 4}

		ontDdmiLatest15MTemperature OBJECT-TYPE
        SYNTAX      DisplayString
        MAX-ACCESS  read-only
        STATUS      current
        DESCRIPTION
         	" get ONT Temperature (C) within latest 15 minutes."
    	::= { ontDdmiLatest15MEntry 5}

-- *
-- * ontPmRateInterval Table
-- *

--	ontPmRateIntervalTable OBJECT IDENTIFIER ::= { remoteOntInfo 15}

    ontPmRateIntervalTable OBJECT-TYPE
        SYNTAX	SEQUENCE OF OntPmRateIntervalEntry
        MAX-ACCESS  not-accessible
        STATUS  current
        DESCRIPTION
                 	""
        ::= { remoteOntInfo 15 }

	ontPmRateIntervalEntry OBJECT-TYPE
        SYNTAX      OntPmRateIntervalEntry
        MAX-ACCESS  not-accessible
        STATUS      current
        DESCRIPTION
            "An entry in ontPmRateIntervalTable"
        INDEX {
            dot1dBasePort,
            ontNumber,
            ontcard,
            uniPort
        }
    	::= { ontPmRateIntervalTable 1 }

	OntPmRateIntervalEntry ::=
        SEQUENCE {
            ontPmRateIntervalTime      DisplayString,
            ontPmRateIntervalUsRate      INTEGER,
            ontPmRateIntervalDsRate      INTEGER
        }

    ontPmRateIntervalTime OBJECT-TYPE
        SYNTAX      DisplayString
        MAX-ACCESS  read-only
        STATUS      current
        DESCRIPTION
         	"The time of the ONT PM rate that get from the ONT."
    	::= { ontPmRateIntervalEntry 1}

    ontPmRateIntervalUsRate OBJECT-TYPE
        SYNTAX      INTEGER
        MAX-ACCESS  read-only
        STATUS      current
        DESCRIPTION
         	"The PM upstream rate of the ONT.
         	PS: The unit is Kbps"
    	::= { ontPmRateIntervalEntry 2}

     ontPmRateIntervalDsRate OBJECT-TYPE
        SYNTAX      INTEGER
        MAX-ACCESS  read-only
        STATUS      current
        DESCRIPTION
         	"The PM downstream rate of the ONT.
         	PS: The unit is Kbps"
    	::= { ontPmRateIntervalEntry 3}
-- *
-- * ontSummary Table
-- *

	ontSummary OBJECT IDENTIFIER ::= { remoteOntInfo 16 }

	ontSummaryTable OBJECT-TYPE
		SYNTAX      SEQUENCE OF OntSummaryEntry
        MAX-ACCESS  not-accessible
		STATUS      current
		DESCRIPTION
	            ""
        ::= { ontSummary 1 }

	ontSummaryEntry OBJECT-TYPE
        SYNTAX      OntSummaryEntry
        MAX-ACCESS  not-accessible
        STATUS      current
        DESCRIPTION
        		"An entry in ontSummaryTable"
        INDEX {
        		dot1dBasePort
        }
    	::= { ontSummaryTable 1 }

	OntSummaryEntry ::=
        SEQUENCE {
            unRegistered		INTEGER,
            o7State				INTEGER,
            isState				INTEGER,
            oosLoState			INTEGER,
            oosSbState			INTEGER,
            oosDgState			INTEGER,
            oosLsState			INTEGER,
            oosNrState			INTEGER,
            oosCdState			INTEGER,
            oosTmState			INTEGER,
            oosNpState			INTEGER,
            oosPfState			INTEGER
   }
 	unRegistered OBJECT-TYPE
        SYNTAX INTEGER
        MAX-ACCESS  read-only
        STATUS      current
        DESCRIPTION
         	"The total number of ONTs that connecting in this pon port without assigning AID for them."
    	::= { ontSummaryEntry 1 }

 	o7State OBJECT-TYPE
        SYNTAX INTEGER
        MAX-ACCESS  read-only
        STATUS      current
        DESCRIPTION
         	"The total number of ONTs in O7 (Emergency Stop state) state"
    	::= { ontSummaryEntry 2 }

 	isState OBJECT-TYPE
        SYNTAX INTEGER
        MAX-ACCESS  read-only
        STATUS      current
        DESCRIPTION
         	"The total number of ONTs in IS (In Service) state"
    	::= { ontSummaryEntry 3 }

 	oosLoState OBJECT-TYPE
        SYNTAX INTEGER
        MAX-ACCESS  read-only
        STATUS      current
        DESCRIPTION
         	"The total number of ONTs in OOS-LO (Line Card Out Of Service) state"
    	::= { ontSummaryEntry 4 }

 	oosSbState OBJECT-TYPE
        SYNTAX INTEGER
        MAX-ACCESS  read-only
        STATUS      current
        DESCRIPTION
         	"The total number of ONTs in OOS-SB (Standby Out Of Service) state"
    	::= { ontSummaryEntry 5 }

 	oosDgState OBJECT-TYPE
        SYNTAX INTEGER
        MAX-ACCESS  read-only
        STATUS      current
        DESCRIPTION
         	"The total number of ONTs in OOS-DG (Dying Gasp, the ONU power-off in a normal operation) state"
    	::= { ontSummaryEntry 6 }

 	oosLsState OBJECT-TYPE
        SYNTAX INTEGER
        MAX-ACCESS  read-only
        STATUS      current
        DESCRIPTION
         	"The total number of ONTs in OOS-LS (Loss of Service) state"
    	::= { ontSummaryEntry 7 }

 	oosNrState OBJECT-TYPE
        SYNTAX INTEGER
        MAX-ACCESS  read-only
        STATUS      current
        DESCRIPTION
         	"The total number of ONTs in OOS-NR (Not Registered) state"
    	::= { ontSummaryEntry 8 }

 	oosCdState OBJECT-TYPE
        SYNTAX INTEGER
        MAX-ACCESS  read-only
        STATUS      current
        DESCRIPTION
         	"The total number of ONTs in OOS-CD (OMCC Down) state"
    	::= { ontSummaryEntry 9 }

 	oosTmState OBJECT-TYPE
        SYNTAX INTEGER
        MAX-ACCESS  read-only
        STATUS      current
        DESCRIPTION
         	"The total number of ONTs in OOS-TM (Type Mismatch) state"
    	::= { ontSummaryEntry 10 }

  	oosNpState OBJECT-TYPE
        SYNTAX INTEGER
        MAX-ACCESS  read-only
        STATUS      current
        DESCRIPTION
         	"The total number of ONTs in OOS-NP (Not Provisioned) state"
    	::= { ontSummaryEntry 11 }

  	oosPfState OBJECT-TYPE
        SYNTAX INTEGER
        MAX-ACCESS  read-only
        STATUS      current
        DESCRIPTION
         	"The total number of ONTs in OOS-PF (Provision Failed) state"
    	::= { ontSummaryEntry 12 }


	ontSummaryTotal OBJECT IDENTIFIER ::= { ontSummary 2 }

 	unRegisteredTotal OBJECT-TYPE
        SYNTAX INTEGER
        MAX-ACCESS  read-only
        STATUS      current
        DESCRIPTION
         	"The total number of ONTs that connecting in this pon port without assigning AID for them."
    	::= { ontSummaryTotal 1 }

 	o7StateTotal OBJECT-TYPE
        SYNTAX INTEGER
        MAX-ACCESS  read-only
        STATUS      current
        DESCRIPTION
         	"The total number of ONTs in O7 (Emergency Stop state) state"
    	::= { ontSummaryTotal 2 }

 	isStateTotal OBJECT-TYPE
        SYNTAX INTEGER
        MAX-ACCESS  read-only
        STATUS      current
        DESCRIPTION
         	"The total number of ONTs in IS (In Service) state"
    	::= { ontSummaryTotal 3 }

 	oosLoStateTotal OBJECT-TYPE
        SYNTAX INTEGER
        MAX-ACCESS  read-only
        STATUS      current
        DESCRIPTION
         	"The total number of ONTs in OOS-LO (Line Card Out Of Service) state"
    	::= { ontSummaryTotal 4 }

 	oosSBStateTotal OBJECT-TYPE
        SYNTAX INTEGER
        MAX-ACCESS  read-only
        STATUS      current
        DESCRIPTION
         	"The total number of ONTs in OOS-SB (Standby Out Of Service) state"
    	::= { ontSummaryTotal 5 }

 	oosDgStateTotal OBJECT-TYPE
        SYNTAX INTEGER
        MAX-ACCESS  read-only
        STATUS      current
        DESCRIPTION
         	"The total number of ONTs in OOS-DG (Dying Gasp, the ONU power-off in a normal operation) state"
    	::= { ontSummaryTotal 6 }

 	oosLsStateTotal OBJECT-TYPE
        SYNTAX INTEGER
        MAX-ACCESS  read-only
        STATUS      current
        DESCRIPTION
         	"The total number of ONTs in OOS-LS (Loss of Service) state"
    	::= { ontSummaryTotal 7 }

 	oosNrStateTotal OBJECT-TYPE
        SYNTAX INTEGER
        MAX-ACCESS  read-only
        STATUS      current
        DESCRIPTION
         	"The total number of ONTs in OOS-NR (Not Registered) state"
    	::= { ontSummaryTotal 8 }

 	oosCdStateTotal OBJECT-TYPE
        SYNTAX INTEGER
        MAX-ACCESS  read-only
        STATUS      current
        DESCRIPTION
         	"The total number of ONTs in OOS-CD (OMCC Down) state"
    	::= { ontSummaryTotal 9 }

 	oosTmStateTotal OBJECT-TYPE
        SYNTAX INTEGER
        MAX-ACCESS  read-only
        STATUS      current
        DESCRIPTION
         	"The total number of ONTs in OOS-TM (Type Mismatch) state"
    	::= { ontSummaryTotal 10 }

  	oosNpStateTotal OBJECT-TYPE
        SYNTAX INTEGER
        MAX-ACCESS  read-only
        STATUS      current
        DESCRIPTION
         	"The total number of ONTs in OOS-NP (Not Provisioned) state"
    	::= { ontSummaryTotal 11 }

  	oosPfStateTotal OBJECT-TYPE
        SYNTAX INTEGER
        MAX-ACCESS  read-only
        STATUS      current
        DESCRIPTION
         	"The total number of ONTs in OOS-PF (Provision Failed) state"
    	::= { ontSummaryTotal 12 }

--   ontAclProfileStatus OBJECT IDENTIFIER ::= { remoteOntInfo 17 }
	ontAclProfileStatus OBJECT IDENTIFIER ::= { remoteOntInfo 17 }

	ontAclProfileClearCounterAll OBJECT-TYPE
	SYNTAX  EnabledStatus
	MAX-ACCESS  read-write
	STATUS  current
	DESCRIPTION
			"Clear ONT ACL profile all counter, always return disable"
	::= { ontAclProfileStatus 1 }

	ontAclProfileClearTable OBJECT-TYPE
		SYNTAX      SEQUENCE OF OntAclProfileClearEntry
        MAX-ACCESS  not-accessible
		STATUS      current
		DESCRIPTION
	            ""
        ::= { ontAclProfileStatus 2 }

		ontAclProfileClearEntry OBJECT-TYPE
	        SYNTAX      OntAclProfileClearEntry
	        MAX-ACCESS  not-accessible
	        STATUS      current
	        DESCRIPTION
	        		"An entry in ontAclProfileClearTable"
	        INDEX {
	        	ontAclProfileName
	        }
	    	::= { ontAclProfileClearTable 1 }

		OntAclProfileClearEntry ::=
	        SEQUENCE {
				ontAclProfileClearCounter		EnabledStatus
			}

		ontAclProfileClearCounter OBJECT-TYPE
		SYNTAX  EnabledStatus
		MAX-ACCESS  read-write
		STATUS  current
		DESCRIPTION
				"Clear ONT ACL profile counter, always return disable"
		::= { ontAclProfileClearEntry 1 }

  ontAclProfileCounterTable	OBJECT-TYPE
  SYNTAX	SEQUENCE OF OntAclProfileCounterEntry
  MAX-ACCESS  not-accessible
  STATUS  current
  DESCRIPTION
           	""
  ::= { ontAclProfileStatus 3 }

 		ontAclProfileCounterEntry OBJECT-TYPE
        SYNTAX	OntAclProfileCounterEntry
        MAX-ACCESS	not-accessible
        STATUS	current
        DESCRIPTION    	"An entry in ontAclProfileCounterTable."
        INDEX          	{ontAclProfileName, dot1dBasePort, ontNumber, ontAclRuleId}
        ::= { ontAclProfileCounterTable 1 }

      	OntAclProfileCounterEntry ::=
				SEQUENCE {
        	ontAclProfilePacketCount			Counter32
        }

				ontAclProfilePacketCount OBJECT-TYPE
				SYNTAX  Counter32
				MAX-ACCESS  read-only
				STATUS  current
				DESCRIPTION
					"Counter for the ont Acl Profile, 65535 means counter disabled."
				::= { ontAclProfileCounterEntry 1 }


-- ******************************************************************
-- *
-- 138.antispoof mib
-- *
-- ******************************************************************

	antiSpoofState OBJECT-TYPE
	SYNTAX  EnabledStatus
	MAX-ACCESS  read-write
	STATUS  current
	DESCRIPTION
	"antiSpoof enabled/disabled for the switch."
	::= { antiSpoofSetup 1 }

--
--  	antiSpoofing port table
--

	antiSpoofPortTable	OBJECT-TYPE
	SYNTAX	SEQUENCE OF AntiSpoofPortEntry
	MAX-ACCESS  not-accessible
	STATUS  current
	DESCRIPTION
				""
	::= { antiSpoofSetup 2 }

	antiSpoofPortEntry OBJECT-TYPE
	SYNTAX	AntiSpoofPortEntry
	MAX-ACCESS	not-accessible
	STATUS	current
	DESCRIPTION    	""
	INDEX          	{ antiSpoofActiveByPort }
	::= { antiSpoofPortTable 1 }

	AntiSpoofPortEntry ::=
	SEQUENCE {
		antiSpoofActiveByPort		EnabledStatus
	}

	antiSpoofActiveByPort OBJECT-TYPE
	SYNTAX  EnabledStatus
	MAX-ACCESS  read-write
	STATUS  current
	DESCRIPTION
					""
	::= { antiSpoofPortEntry 1 }

--
--  	antiSpoofing setup table
--

	antiSpoofTable	OBJECT-TYPE
	SYNTAX	SEQUENCE OF AntiSpoofEntry
	MAX-ACCESS  not-accessible
	STATUS  current
	DESCRIPTION
				""
	::= { antiSpoofSetup 3 }

	antiSpoofEntry OBJECT-TYPE
	SYNTAX	AntiSpoofEntry
	MAX-ACCESS	not-accessible
	STATUS	current
	DESCRIPTION    	""
	INDEX          	{ antiSpoofPort, antiSpoofMode,  antiSpoofSetting}
	::= { antiSpoofTable 1 }

	AntiSpoofEntry ::=
	SEQUENCE {
		antiSpoofPort			INTEGER,
		antiSpoofMode                   INTEGER,
		antiSpoofSetting    		DisplayString,
		antiSpoofRowStatus	        RowStatus
	}

	antiSpoofPort OBJECT-TYPE
	SYNTAX  INTEGER
	MAX-ACCESS  read-only
	STATUS  current
	DESCRIPTION
					""
	::= { antiSpoofEntry 1 }

	antiSpoofMode OBJECT-TYPE
	SYNTAX  INTEGER {
		inclusiveIp(1),
		inclusiveMac(2),
		inclusiveIpMac(3),
		exclusiveIp(5),
		exclusiveMac(6),
		exclusiveIpMac(7),
		inclusiveOuimac(8)
	}
	MAX-ACCESS	read-only
	STATUS	current
	DESCRIPTION
					"Show the entry is inclusive/exclusive for IP/MAC/OUIMAC"
	::= { antiSpoofEntry 2 }

	antiSpoofSetting OBJECT-TYPE
	SYNTAX	DisplayString
	MAX-ACCESS	read-only
	STATUS	current
	DESCRIPTION
					"IP/MAC/IP&MAC/OUI-MAC setting"
	::= { antiSpoofEntry 3 }

	antiSpoofRowStatus OBJECT-TYPE
	SYNTAX  RowStatus
	MAX-ACCESS  read-create
	STATUS  current
	DESCRIPTION
					""
	::= { antiSpoofEntry 4 }

--  	multicastChannelSetup table

        multicastChannelTable OBJECT-TYPE
        SYNTAX  SEQUENCE OF MulticastChannelEntry
        MAX-ACCESS  not-accessible
        STATUS  current
        DESCRIPTION    	""

        ::= { multicastChannelSetup 1 }

        multicastChannelEntry OBJECT-TYPE
        SYNTAX  MulticastChannelEntry
        MAX-ACCESS  not-accessible
        STATUS  current
        DESCRIPTION    ""
        INDEX {
            multicastChannelStartIp,
            multicastChannelEndIp,
            multicastChannelSvid,
            multicastChannelCvid
        }
        ::= { multicastChannelTable 1 }

        MulticastChannelEntry ::=
        SEQUENCE {
            multicastChannelStartIp         IpAddress,
            multicastChannelEndIp           IpAddress,
            multicastChannelSvid            INTEGER,
            multicastChannelCvid            INTEGER,
            multicastChannelPbit            INTEGER,
            multicastChannelSrcIp           IpAddress,
            multicastChannelPkgMember       INTEGER,
            multicastChannelPreviewDuration INTEGER,
            multicastChannelPreviewCount    INTEGER,
            multicastChannelPreviewBlackout INTEGER,
            multicastChannelRowStatus       RowStatus,
            multicastChannelCacProf         DisplayString
        }

        multicastChannelStartIp OBJECT-TYPE
        SYNTAX  IpAddress
        MAX-ACCESS  read-only
        STATUS  current
        DESCRIPTION
            "start ip address of a group range"
        ::= { multicastChannelEntry 1 }

        multicastChannelEndIp OBJECT-TYPE
        SYNTAX  IpAddress
        MAX-ACCESS  read-only
        STATUS  current
        DESCRIPTION
            "end ip address of a group range"
        ::= { multicastChannelEntry 2 }

        multicastChannelSvid OBJECT-TYPE
        SYNTAX  INTEGER (1..4096)
        MAX-ACCESS  read-only
        STATUS  current
        DESCRIPTION
            "multicast vlan (svid)"
        ::= { multicastChannelEntry 3 }

        multicastChannelCvid OBJECT-TYPE
        SYNTAX  INTEGER (1..4094)
        MAX-ACCESS  read-only
        STATUS  current
        DESCRIPTION
            "multicast vlan (cvid)"
        ::= { multicastChannelEntry 4 }

        multicastChannelPbit OBJECT-TYPE
        SYNTAX  INTEGER (0..7)
        MAX-ACCESS  read-write
        STATUS  current
        DESCRIPTION
            "802.1p priority"
        ::= { multicastChannelEntry 5 }

        multicastChannelSrcIp OBJECT-TYPE
        SYNTAX  IpAddress
        MAX-ACCESS  read-write
        STATUS  current
        DESCRIPTION
            "source ip address"
        ::= { multicastChannelEntry 6 }

        multicastChannelPkgMember OBJECT-TYPE
        SYNTAX  INTEGER (0..32)
        MAX-ACCESS  read-write
        STATUS  current
        DESCRIPTION
            "package member"
        ::= { multicastChannelEntry 7 }

        multicastChannelPreviewDuration OBJECT-TYPE
        SYNTAX  INTEGER (1..6000)
        MAX-ACCESS  read-write
        STATUS  current
        DESCRIPTION
            "preview duration which is used when this package member is applied to an IGMP channel with preview privilege"
        ::= { multicastChannelEntry 8 }

        multicastChannelPreviewCount OBJECT-TYPE
        SYNTAX  INTEGER (1..100)
        MAX-ACCESS  read-write
        STATUS  current
        DESCRIPTION
            "preview count which is used when this package member is applied to an IGMP channel with preview privilege"
        ::= { multicastChannelEntry 9 }

        multicastChannelPreviewBlackout OBJECT-TYPE
        SYNTAX  INTEGER (0..7200)
        MAX-ACCESS  read-write
        STATUS  current
        DESCRIPTION
            "preview blackout which is used when this package member is applied to an IGMP channel with preview privilege"
        ::= { multicastChannelEntry 10 }

        multicastChannelRowStatus OBJECT-TYPE
        SYNTAX      RowStatus
        MAX-ACCESS  read-create
        STATUS      current
        DESCRIPTION
            ""
        ::= { multicastChannelEntry 11 }

        multicastChannelCacProf OBJECT-TYPE
        SYNTAX  DisplayString
        MAX-ACCESS  read-write
        STATUS  current
        DESCRIPTION
            "The multicast bandwidth for this package member"
        ::= { multicastChannelEntry 12 }

-- ******************************************************************
-- *
-- 142.ponSetup mib
-- *
-- ******************************************************************
-- *
-- * pon Table
-- *

  ponTable OBJECT IDENTIFIER ::= { ponSetup 1 }

	ponSetupTable OBJECT-TYPE
		SYNTAX      SEQUENCE OF PonSetupEntry
        MAX-ACCESS  not-accessible
        STATUS  current
        DESCRIPTION
                 	""
        ::= { ponTable 1 }

	ponSetupEntry OBJECT-TYPE
        SYNTAX      PonSetupEntry
        MAX-ACCESS  not-accessible
        STATUS	current
        DESCRIPTION
        		"An entry in ponSetupTable"
        INDEX {
        		dot1dBasePort
        }
    	::= { ponSetupTable 1 }

	PonSetupEntry ::=
           SEQUENCE {
            transceiverTxDisable		     	  EnabledStatus,
            inO7State                  DisplayString,
            outO7State                  DisplayString,
            linkState                  INTEGER,
            availableBandwidth                  INTEGER,
			delimiterDetected          INTEGER
           }

  transceiverTxDisable OBJECT-TYPE
        SYNTAX  EnabledStatus
        MAX-ACCESS  read-write
        STATUS  current
        DESCRIPTION
                              	"transceiver tx disable"
        ::= { ponSetupEntry 1 }

  inO7State OBJECT-TYPE
        SYNTAX  DisplayString
        MAX-ACCESS  read-write
        STATUS  current
        DESCRIPTION
                              	"ONT Enter Emergency Stop State(07), input serial number"
        ::= { ponSetupEntry 2 }

  outO7State OBJECT-TYPE
        SYNTAX  DisplayString
        MAX-ACCESS  read-write
        STATUS  current
        DESCRIPTION
                              	"ONT Leave Emergency Stop State(07), input serial number"
        ::= { ponSetupEntry 3 }

  linkState OBJECT-TYPE
        SYNTAX	INTEGER {
            off(0),
            on(1)
        }
        MAX-ACCESS	read-only
        STATUS	current
        DESCRIPTION     "Show PON link state"
        ::= { ponSetupEntry 4 }

  availableBandwidth OBJECT-TYPE
        SYNTAX	INTEGER
        MAX-ACCESS	read-only
        STATUS	current
        DESCRIPTION     "Show PON port available upstream bandwidth(kbps)"
        ::= { ponSetupEntry 5 }

  delimiterDetected OBJECT-TYPE
        SYNTAX  INTEGER {
           off(0),
           on(1)
        }
        MAX-ACCESS	read-only
        STATUS	current
        DESCRIPTION     "Show PON port delimiter detected"
        ::= { ponSetupEntry 6 }

	ponConfigTable OBJECT-TYPE
		SYNTAX      SEQUENCE OF PonConfigEntry
        MAX-ACCESS  not-accessible
        STATUS  current
        DESCRIPTION
                 	""
        ::= { ponTable 2 }

	ponConfigEntry OBJECT-TYPE
        SYNTAX      PonConfigEntry
        MAX-ACCESS  not-accessible
        STATUS	current
        DESCRIPTION
        		"An entry in ponConfigTable"
        INDEX {
        		dot1dBasePort
        }
    	::= { ponConfigTable 1 }

	PonConfigEntry ::=
           SEQUENCE {
            transceiverType               INTEGER,
            registerMethod                INTEGER,
            ponConfigRowStatus            RowStatus,
            templateOption                INTEGER,
            ontTemplate                   EnabledStatus,
            fecMode                       EnabledStatus,
            rangingDistance               INTEGER,
            bipErrThres                   Unsigned32,
            fecCorrByteThres              Unsigned32,
            fecCorrCodeWordThres          Unsigned32,
            fecUncorrCodeWordThres        Unsigned32,
            reiCounterThres               Unsigned32,
            tcaStatus                     EnabledStatus,
            fecCodeWordErrThres           Unsigned32,
            bipByteThres                  Unsigned32,
            rxPloamCrcErrThres            Unsigned32,
            rxPloamNonIdleThres           Unsigned32,
            positiveDriftThres            Unsigned32,
            negativeDriftThres            Unsigned32,
            rxOmciPacketThres             Unsigned32,
            rxOmciPacketCrcErrThres       Unsigned32,
            unrecievedBurstThres          Unsigned32,
            lcdgiErrThres                 Unsigned32,
            rdiErrThres                   Unsigned32
           }

    transceiverType OBJECT-TYPE
        SYNTAX      INTEGER {
            ligent(0),
            luminent(1),
            fiberxon(2),
            fujitsu(3),
            ligentA(4),
            ligentB(5),
            luminentA(6),
            luminentB(7),
            fiberxonA(8),
            fujitsuA(9),
            nec(10),
            neoptec(11),
            ligentC(12),
            fiberxonB(13),
            fujitsu30537(14),
            neophotonicsA(15),
            neophotonicsB(16),
            neophotonicsC(17),
            superxon(18),
            wtd(19),
            delta(20),
            no1(21),
            no2(22),
            none(23)
        }
        MAX-ACCESS  read-write
        STATUS  current
        DESCRIPTION
         	" transceiver Type"
    	::= { ponConfigEntry 1 }

    registerMethod OBJECT-TYPE
        SYNTAX      INTEGER {
            methodA(0),          -- Match serial number, and password
            methodC(1),          -- Match PLOAM password
            methodCAutolock(2),  -- Match serial number
            methodD(3),          -- Volatile auto provision by template
            methodE(4)           -- Non-volatile auto provision by template
        }
        MAX-ACCESS  read-write
        STATUS      current
        DESCRIPTION
         "register Method"
        ::= { ponConfigEntry 2 }

    ponConfigRowStatus OBJECT-TYPE
        SYNTAX  RowStatus
        MAX-ACCESS  read-create
        STATUS      current
        DESCRIPTION
         ""
        ::= { ponConfigEntry 3 }

	templateOption OBJECT-TYPE
        SYNTAX      INTEGER {
            template121(1),          -- Template 121
            template122(2),          -- Template 122
            template123(3),          -- Template 123
            template124(4),          -- Template 124
            template125(5),          -- Template 125
            template126(6),          -- Template 126
            template127(7),          -- Template 127
            template128(8)           -- Template 128
        }
        MAX-ACCESS  read-write
        STATUS      current
        DESCRIPTION
         "template Option"
        ::= { ponConfigEntry 4 }

    ontTemplate OBJECT-TYPE
        SYNTAX  EnabledStatus
        MAX-ACCESS  read-write
        STATUS  current
        DESCRIPTION
         "Enable/Disable ont template on pon port."
        ::= { ponConfigEntry 5 }

	fecMode OBJECT-TYPE
        SYNTAX  EnabledStatus
        MAX-ACCESS  read-write
        STATUS  current
        DESCRIPTION
         "Enable/Disable fec on pon port."
        ::= { ponConfigEntry 6 }

    rangingDistance OBJECT-TYPE
        SYNTAX  INTEGER (20..60)
        MAX-ACCESS  read-write
        STATUS  current
        DESCRIPTION
            "Maximum ranging distance between 20km to 60km."
        ::= { ponConfigEntry 7 }

    bipErrThres OBJECT-TYPE
        SYNTAX  Unsigned32
        MAX-ACCESS  read-write
        STATUS  current
        DESCRIPTION
            "BIP error threshold."
        ::= { ponConfigEntry 8 }

    fecCorrByteThres OBJECT-TYPE
        SYNTAX  Unsigned32
        MAX-ACCESS  read-write
        STATUS  current
        DESCRIPTION
            "FEC corrected byte threshold."
        ::= { ponConfigEntry 9 }

    fecCorrCodeWordThres OBJECT-TYPE
        SYNTAX  Unsigned32
        MAX-ACCESS  read-write
        STATUS  current
        DESCRIPTION
            "FEC corrected code word threshold."
        ::= { ponConfigEntry 10 }

    fecUncorrCodeWordThres OBJECT-TYPE
        SYNTAX  Unsigned32
        MAX-ACCESS  read-write
        STATUS  current
        DESCRIPTION
            "FEC uncorrected code word threshold."
        ::= { ponConfigEntry 11 }

    reiCounterThres OBJECT-TYPE
        SYNTAX  Unsigned32
        MAX-ACCESS  read-write
        STATUS  current
        DESCRIPTION
            "REI counter threshold."
        ::= { ponConfigEntry 12 }

    tcaStatus OBJECT-TYPE
        SYNTAX  EnabledStatus
        MAX-ACCESS  read-write
        STATUS  current
        DESCRIPTION
            "Enable/Disable tca status."
        ::= { ponConfigEntry 13 }

    fecCodeWordErrThres OBJECT-TYPE
        SYNTAX  Unsigned32
        MAX-ACCESS  read-write
        STATUS  current
        DESCRIPTION
            "FEC code word threshold."
        ::= { ponConfigEntry 14 }

    bipByteThres OBJECT-TYPE
        SYNTAX  Unsigned32
        MAX-ACCESS  read-write
        STATUS  current
        DESCRIPTION
            "BIP byte threshold."
        ::= { ponConfigEntry 15 }

    rxPloamCrcErrThres OBJECT-TYPE
        SYNTAX  Unsigned32
        MAX-ACCESS  read-write
        STATUS  current
        DESCRIPTION
            "Rx PLOAM CRC error threshold."
        ::= { ponConfigEntry 16 }

    rxPloamNonIdleThres OBJECT-TYPE
        SYNTAX  Unsigned32
        MAX-ACCESS  read-write
        STATUS  current
        DESCRIPTION
            "Rx PLOAM non idle threshold."
        ::= { ponConfigEntry 17 }

    positiveDriftThres OBJECT-TYPE
        SYNTAX  Unsigned32
        MAX-ACCESS  read-write
        STATUS  current
        DESCRIPTION
            "Positive drift threshold."
        ::= { ponConfigEntry 18 }
    negativeDriftThres OBJECT-TYPE
        SYNTAX  Unsigned32
        MAX-ACCESS  read-write
        STATUS  current
        DESCRIPTION
            "Negative drift threshold."
        ::= { ponConfigEntry 19 }

    rxOmciPacketThres OBJECT-TYPE
        SYNTAX  Unsigned32
        MAX-ACCESS  read-write
        STATUS  current
        DESCRIPTION
            "Rx OMCI packet threshold."
        ::= { ponConfigEntry 20 }

    rxOmciPacketCrcErrThres OBJECT-TYPE
        SYNTAX  Unsigned32
        MAX-ACCESS  read-write
        STATUS  current
        DESCRIPTION
            "Rx OMCI packet CRC error threshold."
        ::= { ponConfigEntry 21 }

    unrecievedBurstThres OBJECT-TYPE
        SYNTAX  Unsigned32
        MAX-ACCESS  read-write
        STATUS  current
        DESCRIPTION
            "Unreceived burst threshold."
        ::= { ponConfigEntry 22 }
    lcdgiErrThres OBJECT-TYPE
        SYNTAX  Unsigned32
        MAX-ACCESS  read-write
        STATUS  current
        DESCRIPTION
            "LCDGI (Loss of GEM channel delineation) error threshold."
        ::= { ponConfigEntry 23 }

    rdiErrThres OBJECT-TYPE
        SYNTAX  Unsigned32
        MAX-ACCESS  read-write
        STATUS  current
        DESCRIPTION
            "RDI (Remote defect indication) error threshold."
        ::= { ponConfigEntry 24 }

	unregisterOntTable OBJECT-TYPE
		SYNTAX      SEQUENCE OF UnregisterOntEntry
        MAX-ACCESS  not-accessible
        STATUS  current
        DESCRIPTION
                 	""
        ::= { ponTable 3 }

	unregisterOntEntry OBJECT-TYPE
        SYNTAX      UnregisterOntEntry
        MAX-ACCESS  not-accessible
        STATUS	current
        DESCRIPTION
        		"An entry in unregisterOntTable"
        INDEX {
        		dot1dBasePort,
				unregisterOntIndex
        }
    	::= { unregisterOntTable 1 }

	UnregisterOntEntry ::=
           SEQUENCE {
            unregisterOntSerialNumber   DisplayString,
            unregisterOntPassword		DisplayString,
            unregisterOntStatus         INTEGER,
			unregisterOntIndex          INTEGER
           }

    unregisterOntSerialNumber OBJECT-TYPE
        SYNTAX      DisplayString
        MAX-ACCESS  read-only
        STATUS  current
        DESCRIPTION
         	" unregisterOnt Serial Number"
    	::= { unregisterOntEntry 1 }

   unregisterOntPassword OBJECT-TYPE
        SYNTAX      DisplayString
        MAX-ACCESS  read-only
        STATUS  current
        DESCRIPTION
         	" unregisterOnt password"
    	::= { unregisterOntEntry 2 }

   unregisterOntStatus OBJECT-TYPE
        SYNTAX       INTEGER {
            disable(0),
            active(1),
			disable_rogue(2)
        }
        MAX-ACCESS  read-only
        STATUS  current
        DESCRIPTION
         	" unregisterOnt Status"
    	::= { unregisterOntEntry 3 }

   unregisterOntIndex OBJECT-TYPE
        SYNTAX      INTEGER
        MAX-ACCESS  read-only
        STATUS  current
        DESCRIPTION
         	" unregisterOnt Ont Index"
    	::= { unregisterOntEntry 4 }


	ponRogueOnuTable OBJECT-TYPE
		SYNTAX      SEQUENCE OF PonRogueOnuEntry
        MAX-ACCESS  not-accessible
        STATUS  current
        DESCRIPTION
                 	""
        ::= { ponTable 5 }

	ponRogueOnuEntry OBJECT-TYPE
        SYNTAX      PonRogueOnuEntry
        MAX-ACCESS  not-accessible
        STATUS	current
        DESCRIPTION
        		"An entry in ponRogueOnuTable"
        INDEX {
        		dot1dBasePort
        }
    	::= { ponRogueOnuTable 1 }

	PonRogueOnuEntry ::=
           SEQUENCE {
            rogueDetect                  INTEGER
           }

  rogueDetect OBJECT-TYPE
        SYNTAX	INTEGER {
            off(0),
            on(1)
        }
        MAX-ACCESS	read-write
        STATUS	current
        DESCRIPTION     "Start or Stop rogue onu detect"
        ::= { ponRogueOnuEntry 1 }

-- ******************************************************************
-- *
-- ponProtection mib
-- *
-- ******************************************************************
-- *

	ponProtectionTable OBJECT-TYPE
	SYNTAX      SEQUENCE OF PonProtectionEntry
        MAX-ACCESS  not-accessible
        STATUS  current
        DESCRIPTION
                 	""
        ::= { ponTable 4 }

	ponProtectionEntry OBJECT-TYPE
        SYNTAX      PonProtectionEntry
        MAX-ACCESS  not-accessible
        STATUS	current
        DESCRIPTION
        		"An entry in ponProtectionTable"
        INDEX {
        		dot1dBasePort
        }
    	::= { ponProtectionTable 1 }

	PonProtectionEntry ::=
           SEQUENCE {
            protectionPort		     	  INTEGER,
            ponProtectConfigRowStatus        RowStatus
          }

    protectionPort OBJECT-TYPE
        SYNTAX      INTEGER
        MAX-ACCESS  read-write
        STATUS  current
        DESCRIPTION
         	" transceiver Type"
    	::= { ponProtectionEntry 1 }

    ponProtectConfigRowStatus OBJECT-TYPE
        SYNTAX  RowStatus
        MAX-ACCESS  read-create
        STATUS      current
        DESCRIPTION
         ""
        ::= { ponProtectionEntry 2 }





-- ******************************************************************
-- *
-- 143.firmwareUpgrade mib
-- *
-- ******************************************************************
-- *
-- * firmwareUpgrade Table
-- *

  ontFwUpgradeSetup OBJECT IDENTIFIER ::= { ontFwUpgrade 1 }

  ontImageVersion OBJECT-TYPE
        SYNTAX  DisplayString
        MAX-ACCESS  read-write
        STATUS  current
        DESCRIPTION
             "ONT image version name on OLT."
        ::= { ontFwUpgradeSetup 1 }

  releaseOntImage OBJECT-TYPE
        SYNTAX  INTEGER{
			notRelease(0),
			release(1)
		}
        MAX-ACCESS  read-write
        STATUS  current
        DESCRIPTION
              "release ONT image from OLT."
        ::= { ontFwUpgradeSetup 3 }

  autoReboot OBJECT-TYPE
        SYNTAX  INTEGER{
			disable(0),
			enable(1)
		}
        MAX-ACCESS  read-write
        STATUS  current
        DESCRIPTION
              "change auto-reboot to enable or disable."
        ::= { ontFwUpgradeSetup 4 }

  ontFwUpgradeAction OBJECT IDENTIFIER ::= { ontFwUpgrade 2 }

  checkOntFwPerPon OBJECT-TYPE
        SYNTAX	BITS {
			pon1(0),
			pon2(1),
			pon3(2),
			pon4(3),
			pon5(4),
			pon6(5),
			pon7(6),
			pon8(7)
		}
       MAX-ACCESS  read-write
        STATUS  current
        DESCRIPTION
              "Do all ont FW upgrade of a pon."
        ::= { ontFwUpgradeAction 1 }

   ontFwUpgradeClearStatusPerPon OBJECT-TYPE
        SYNTAX	BITS {
			pon1(0),
			pon2(1),
			pon3(2),
			pon4(3),
			pon5(4),
			pon6(5),
			pon7(6),
			pon8(7)
		}
       MAX-ACCESS  read-write
        STATUS  current
        DESCRIPTION
              "Cleared all of the ONT upgrade status of the pon port."
        ::= { ontFwUpgradeAction 2 }

    ontFwUpgradeClearQueuePerPon OBJECT-TYPE
        SYNTAX	BITS {
			pon1(0),
			pon2(1),
			pon3(2),
			pon4(3),
			pon5(4),
			pon6(5),
			pon7(6),
			pon8(7)
		}
       MAX-ACCESS  read-write
        STATUS  current
        DESCRIPTION
              "Cleared all of the ONT waiting queue of the pon port."
        ::= { ontFwUpgradeAction 3 }


  ontFwUpgradeInfo OBJECT IDENTIFIER ::= { ontFwUpgrade 3 }

  numOfOntInQueue OBJECT-TYPE
        SYNTAX      INTEGER
       MAX-ACCESS  read-only
        STATUS  current
        DESCRIPTION
              "The number of ont that are in FW upgrade queue."
        ::= { ontFwUpgradeInfo 1 }

-- ******************************************************************
-- *
-- 144.portBridgeSetup
-- *
-- ******************************************************************
-- *
-- * portBridgeSetup Table
-- *
		portBridgeState OBJECT-TYPE
        SYNTAX  EnabledStatus
        MAX-ACCESS  read-write
        STATUS  current
        DESCRIPTION
                      	""
        ::= { portBridgeSetup 1 }

        portBridgePortTable OBJECT-TYPE
        SYNTAX	SEQUENCE OF PortBridgePortEntry
        MAX-ACCESS  not-accessible
        STATUS  current
        DESCRIPTION
                 	""
        ::= { portBridgeSetup 2 }

		portBridgePortEntry OBJECT-TYPE
        SYNTAX	PortBridgePortEntry
        MAX-ACCESS	not-accessible
        STATUS	current
        DESCRIPTION    	"An entry in portBridgePortTable."
        INDEX          	{ dot1dBasePort }
        ::= { portBridgePortTable 1 }

        PortBridgePortEntry ::=
           SEQUENCE {
        	portBridgePortState		EnabledStatus
           }

        portBridgePortState OBJECT-TYPE
        SYNTAX  EnabledStatus
        MAX-ACCESS  read-write
        STATUS  current
        DESCRIPTION
                      	"Port Bridge enabled/disabled on the port.
                      	Enable(1) means local switching is allowed in this port."
        ::= { portBridgePortEntry 1 }

-- ******************************************************************
-- *
-- 145.CDR mib
-- *
-- ******************************************************************
-- *
-- * CDR IGMP
-- *
	cdrIgmp OBJECT IDENTIFIER ::= { cdr 1 }

	cdrIgmpSetup OBJECT IDENTIFIER ::= { cdrIgmp 1 }

	cdrIgmpActive OBJECT-TYPE
		SYNTAX INTEGER {
			disable(0),
			enable(1)
		}
		MAX-ACCESS  read-write
		STATUS  current
		DESCRIPTION
			"Enables or disables CDR(Call Detail Record) for IGMP."
		::= { cdrIgmpSetup 1 }

	cdrIgmpLogSize OBJECT-TYPE
		SYNTAX INTEGER
		MAX-ACCESS read-write
        STATUS current
        DESCRIPTION
			"Sets the maximum number of logs of CDR IGMP."
		::= { cdrIgmpSetup 2 }

	cdrIgmpStatus OBJECT IDENTIFIER ::= { cdrIgmp 2 }

	cdrIgmpStatusTable OBJECT-TYPE
		SYNTAX SEQUENCE OF CdrIgmpStatusEntry
		MAX-ACCESS not-accessible
		STATUS current
		DESCRIPTION ""
		::= { cdrIgmpStatus 1 }

	cdrIgmpStatusEntry OBJECT-TYPE
	SYNTAX CdrIgmpStatusEntry
	MAX-ACCESS not-accessible
	STATUS current
	DESCRIPTION "IGMP CDR log"
	INDEX {
		cdrIgmpStatusEntryIndex
	}
	::= { cdrIgmpStatusTable 1 }

	CdrIgmpStatusEntry ::= SEQUENCE {
		cdrIgmpStatusEntryIndex INTEGER,
		cdrIgmpEventTime DisplayString,
		cdrIgmpEventType INTEGER,
		cdrIgmpGroup InetAddress,
		cdrIgmpPrivilege INTEGER,
		cdrIgmpUptime DisplayString,
		cdrIgmpChannel DisplayString
	}

	cdrIgmpStatusEntryIndex OBJECT-TYPE
		SYNTAX INTEGER
		MAX-ACCESS read-only
		STATUS current
		DESCRIPTION "CDR IGMP table entry index."
		::= { cdrIgmpStatusEntry 1 }

	cdrIgmpEventTime OBJECT-TYPE
		SYNTAX DisplayString
		MAX-ACCESS read-only
		STATUS current
		DESCRIPTION "Time of event occurrence."
		::= { cdrIgmpStatusEntry 2 }

	cdrIgmpEventType OBJECT-TYPE
		SYNTAX INTEGER {
			leaveAutonomous(0),
			leaveTimeout(1),
			leaveEnforce(2),
			joinSuccess(3),
			joinFail(4),
			unknown(5)
		}
		MAX-ACCESS read-only
		STATUS current
		DESCRIPTION "IGMP report type."
		::= { cdrIgmpStatusEntry 3 }

	cdrIgmpGroup OBJECT-TYPE
		SYNTAX InetAddress (SIZE(4|16))
		MAX-ACCESS read-only
		STATUS current
		DESCRIPTION "IGMP group address."
		::= { cdrIgmpStatusEntry 4 }

	cdrIgmpPrivilege OBJECT-TYPE
		SYNTAX INTEGER {
			permit(0),
			preview(1),
			reject(2),
			unknown(3)
		}
		MAX-ACCESS read-only
		STATUS current
		DESCRIPTION ""
		::= { cdrIgmpStatusEntry 5 }

	cdrIgmpUptime OBJECT-TYPE
		SYNTAX DisplayString
		MAX-ACCESS read-only
		STATUS current
		DESCRIPTION "Group uptime."
		::= { cdrIgmpStatusEntry 6 }

	cdrIgmpChannel OBJECT-TYPE
		SYNTAX DisplayString
		MAX-ACCESS read-only
		STATUS current
		DESCRIPTION "IGMP channel."
		::= { cdrIgmpStatusEntry 7 }

--  classifierSetup

        classifierRuleTable	OBJECT-TYPE
        SYNTAX	SEQUENCE OF ClassifierRuleEntry
        MAX-ACCESS  not-accessible
        STATUS  current
        DESCRIPTION
                 	""
        ::= { classifierSetup 1 }

		classifierRuleEntry OBJECT-TYPE
        SYNTAX	ClassifierRuleEntry
        MAX-ACCESS	not-accessible
        STATUS	current
        DESCRIPTION    	"An entry in classifierRuleTable."
        INDEX          	{classifierName }
        ::= { classifierRuleTable 1 }

      	ClassifierRuleEntry ::=
		SEQUENCE {
        	classifierName		DisplayString,
        	classifierEnable	INTEGER,
        	classifierPacketFormat INTEGER,
        	classifierVlanId 	INTEGER,
        	classifier8021pPriority INTEGER,
        	classifierEtherType INTEGER,
        	classifierSrcMAC 	MacAddress,
        	classifierIncomingPort INTEGER,
        	classifierDstMAC 	MacAddress,
        	classifierDSCP		INTEGER,
        	classifierIpProtocol INTEGER,
        	classifierEstablishOnly INTEGER,
        	classifierSrcIp	    IpAddress,
        	classifierSrcIpMask	INTEGER,
        	classifierSrcSocket INTEGER,
        	classifierDstIp		IpAddress,
        	classifierDstIpMask	INTEGER,
        	classifierDstSocket INTEGER,
        	classifierRowstatus RowStatus,
        	classifierIp6Dscp INTEGER,
        	classifierIp6NextHeader INTEGER,
        	classifierIp6EstbOnly INTEGER,
        	classifierSrcIp6 DisplayString,
        	classifierSrcIp6PrefixLen INTEGER,
        	classifierDstIp6 DisplayString,
        	classifierDstIp6PrefixLen INTEGER,
        	classifierOutgoingPort INTEGER
           }

        classifierName OBJECT-TYPE
        SYNTAX  DisplayString
        MAX-ACCESS  read-only
        STATUS  current
        DESCRIPTION
                      	"Name of classifier rule."
        ::= { classifierRuleEntry 1 }

        classifierEnable OBJECT-TYPE
        SYNTAX  EnabledStatus
        MAX-ACCESS  read-write
        STATUS  current
        DESCRIPTION
        	"Classifier rule enabled/disabled."
        ::= { classifierRuleEntry 2 }

        classifierPacketFormat OBJECT-TYPE
        SYNTAX  INTEGER
        {
      		all(1),
 		ethernetIIUntagged(2),
		ethernetIITagged(3),
     		ethernet802dot3Untagged(4),
      		ethernet802dot3Tagged(5)
        }
        MAX-ACCESS  read-write
        STATUS  current
        DESCRIPTION
        	"Packet format for classifier rule. All(1), 802.3 untagged(2), 802.3 tagged(3), EthernetII untagged(4), EthernetII tagged(5)."
        ::= { classifierRuleEntry 3 }

   		classifierVlanId OBJECT-TYPE
        SYNTAX  INTEGER
        MAX-ACCESS  read-write
        STATUS  current
        DESCRIPTION
                      	"Vlan id for classifer rule, 1~4094."
        ::= { classifierRuleEntry 4 }

   		classifier8021pPriority OBJECT-TYPE
        SYNTAX  INTEGER
        MAX-ACCESS  read-write
        STATUS  current
        DESCRIPTION
                      	"802.1p priority for classifier rule, 0~7."
        ::= { classifierRuleEntry 5 }

   		classifierEtherType OBJECT-TYPE
        SYNTAX  INTEGER
        MAX-ACCESS  read-write
        STATUS  current
        DESCRIPTION
                      	"Ether type for classifier rule, in decimal expression."
        ::= { classifierRuleEntry 6 }

        classifierSrcMAC OBJECT-TYPE
        SYNTAX  MacAddress
        MAX-ACCESS  read-write
        STATUS  current
        DESCRIPTION
                      	"Source mac address for classifier rule"
        ::= { classifierRuleEntry 7 }

        classifierIncomingPort OBJECT-TYPE
        SYNTAX  INTEGER
        MAX-ACCESS  read-write
        STATUS  current
        DESCRIPTION
                      	"Incoming Port for classifier rule"
        ::= { classifierRuleEntry 8 }

        classifierDstMAC OBJECT-TYPE
        SYNTAX  MacAddress
        MAX-ACCESS  read-write
        STATUS  current
        DESCRIPTION
                      	"Destination mac address for classifier rule"
        ::= { classifierRuleEntry 9 }

        classifierDSCP OBJECT-TYPE
        SYNTAX  INTEGER
        MAX-ACCESS  read-write
        STATUS  current
        DESCRIPTION
                      	"DSCP for classifier rule"
        ::= { classifierRuleEntry 10 }

        classifierIpProtocol OBJECT-TYPE
        SYNTAX  INTEGER
        MAX-ACCESS  read-write
        STATUS  current
        DESCRIPTION
                      	"IP Protocol for classifier rule"
        ::= { classifierRuleEntry 11 }

        classifierEstablishOnly OBJECT-TYPE
        SYNTAX  EnabledStatus
        MAX-ACCESS  read-write
        STATUS  current
        DESCRIPTION
                      	"IP Protocol for EstablishOnly for classifier rule"
        ::= { classifierRuleEntry 12 }

    	classifierSrcIp OBJECT-TYPE
        SYNTAX  IpAddress
        MAX-ACCESS  read-write
        STATUS  current
        DESCRIPTION
                      	"Source IP address for classifier rule"
        ::= { classifierRuleEntry 13 }

        classifierSrcIpMask OBJECT-TYPE
        SYNTAX  INTEGER
        MAX-ACCESS  read-write
        STATUS  current
        DESCRIPTION
                      	"Source IP Mask for classifier rule"
        ::= { classifierRuleEntry 14 }

        classifierSrcSocket OBJECT-TYPE
        SYNTAX  INTEGER
        MAX-ACCESS  read-write
        STATUS  current
        DESCRIPTION
                      	"Source Socket Number for classifier rule"
        ::= { classifierRuleEntry 15 }

        classifierDstIp OBJECT-TYPE
        SYNTAX  IpAddress
        MAX-ACCESS  read-write
        STATUS  current
        DESCRIPTION
                      	"Destination IP address for classifier rule"
        ::= { classifierRuleEntry 16 }

        classifierDstIpMask OBJECT-TYPE
        SYNTAX  INTEGER
        MAX-ACCESS  read-write
        STATUS  current
        DESCRIPTION
                      	"Destination IP Mask for classifier rule"
        ::= { classifierRuleEntry 17 }

        classifierDstSocket OBJECT-TYPE
        SYNTAX  INTEGER
        MAX-ACCESS  read-write
        STATUS  current
        DESCRIPTION
                      	"Destination Socket Number for classifier rule"
        ::= { classifierRuleEntry 18 }

        classifierRowstatus OBJECT-TYPE
        SYNTAX  RowStatus
        MAX-ACCESS  read-create
        STATUS  current
        DESCRIPTION
                      	"Row Status for classifier rule"
        ::= { classifierRuleEntry 19 }

        classifierIp6Dscp OBJECT-TYPE
        SYNTAX  INTEGER
        MAX-ACCESS  read-write
        STATUS  current
        DESCRIPTION
                      	"DSCP in Ipv6 header"
        ::= { classifierRuleEntry 20 }

        classifierIp6NextHeader OBJECT-TYPE
        SYNTAX  INTEGER
        MAX-ACCESS  read-write
        STATUS  current
        DESCRIPTION
                      	"Ipv6 Next Header"
        ::= { classifierRuleEntry 21 }

        classifierIp6EstbOnly OBJECT-TYPE
        SYNTAX  INTEGER
        MAX-ACCESS  read-write
        STATUS  current
        DESCRIPTION
                      	"Ipv6 Establish Only"
        ::= { classifierRuleEntry 22 }

        classifierSrcIp6 OBJECT-TYPE
        SYNTAX  DisplayString
        MAX-ACCESS  read-write
        STATUS  current
        DESCRIPTION
                      	"Source Ipv6 address"
        ::= { classifierRuleEntry 23 }

        classifierSrcIp6PrefixLen OBJECT-TYPE
        SYNTAX  INTEGER
        MAX-ACCESS  read-write
        STATUS  current
        DESCRIPTION
                      	"Source Ipv6 address prefix length"
        ::= { classifierRuleEntry 24 }

        classifierDstIp6 OBJECT-TYPE
        SYNTAX  DisplayString
        MAX-ACCESS  read-write
        STATUS  current
        DESCRIPTION
                      	"Destination Ipv6 address"
        ::= { classifierRuleEntry 25 }

        classifierDstIp6PrefixLen OBJECT-TYPE
        SYNTAX  INTEGER
        MAX-ACCESS  read-write
        STATUS  current
        DESCRIPTION
                      	"Destination Ipv6 address prefic length"
        ::= { classifierRuleEntry 26 }

        classifierOutgoingPort OBJECT-TYPE
        SYNTAX  INTEGER
        MAX-ACCESS  read-write
        STATUS  current
        DESCRIPTION
                      	"Outgoing Port for classifier rule"
        ::= { classifierRuleEntry 27 }

      classifierRuleSet OBJECT-TYPE
        SYNTAX  DisplayString
        MAX-ACCESS  read-write
        STATUS  current
        DESCRIPTION
                      	"classifier Rule Set."
        ::= { classifierSetup 2 }

--  policySetup

        policyTable	OBJECT-TYPE
        SYNTAX	SEQUENCE OF PolicyEntry
        MAX-ACCESS  not-accessible
        STATUS  current
        DESCRIPTION
                 	""
        ::= { policySetup 1 }

 		policyEntry OBJECT-TYPE
        SYNTAX	PolicyEntry
        MAX-ACCESS	not-accessible
        STATUS	current
        DESCRIPTION    	"An entry in policyTable."
        INDEX          	{policyName }
        ::= { policyTable 1 }

      	PolicyEntry ::=
		SEQUENCE {
        	policyName			DisplayString,
        	policyEnable		INTEGER,
        	policyClassifier  	DisplayString,
        	policyVlanId		INTEGER,
        	policyEgressPort 	INTEGER,
        	policyOutPktFormat  INTEGER,
        	policy8021pPriority INTEGER,
        	policyDSCP          INTEGER,
        	policyTOS           INTEGER,
--        	policyBandwidth     INTEGER,
			policySir		    INTEGER,
			policyPir		    INTEGER,
        	policyOutOfProfileDSCP   INTEGER,
        	policyOutOfProfileGpCosqNew   INTEGER,
        	policyForwardingAction   INTEGER,
        	policyPriorityAction     INTEGER,
        	policyDiffServAction 	 INTEGER,
        	policyOutgoingAction	 BITS,
        	policyMeteringEnable     INTEGER,
            policyOutOfProfileAction BITS,
            policyRowstatus 		 RowStatus,
          policyMirrorPort		INTEGER,
					policyCounter				EnabledStatus,
					policyLogging				EnabledStatus
        }

        policyName OBJECT-TYPE
        SYNTAX  DisplayString
        MAX-ACCESS  read-only
        STATUS  current
        DESCRIPTION
                      	"Name of policy rule."
        ::= { policyEntry 1 }

        policyEnable OBJECT-TYPE
        SYNTAX  EnabledStatus
        MAX-ACCESS  read-write
        STATUS  current
        DESCRIPTION
        	"Policy rule enabled/disabled."
        ::= { policyEntry 2 }

        policyClassifier OBJECT-TYPE
        SYNTAX  DisplayString
        MAX-ACCESS  read-only
        STATUS  current
        DESCRIPTION
                      	"Classifier of policy rule."
        ::= { policyEntry 3 }

        policyVlanId OBJECT-TYPE
        SYNTAX  INTEGER
        MAX-ACCESS  read-write
        STATUS  current
        DESCRIPTION
                      	"Vlan id for policy rule, 1~4094."
        ::= { policyEntry 4 }

        policyEgressPort OBJECT-TYPE
        SYNTAX  INTEGER
        MAX-ACCESS  read-write
        STATUS  current
        DESCRIPTION
                      	"Egress Port for policy rule"
        ::= { policyEntry 5 }

        policyOutPktFormat OBJECT-TYPE
        SYNTAX  INTEGER
        {
        	tag(1),
        	untag(2)
        }
        MAX-ACCESS  read-write
        STATUS  current
        DESCRIPTION
                      	"Outgoing packet format for Egress port for policy rule"
        ::= { policyEntry 6 }

        policy8021pPriority OBJECT-TYPE
        SYNTAX  INTEGER
        MAX-ACCESS  read-write
        STATUS  current
        DESCRIPTION
                      	"802.1p priority for policy rule, 0~7."
        ::= { policyEntry 7 }

        policyDSCP OBJECT-TYPE
        SYNTAX  INTEGER
        MAX-ACCESS  read-write
        STATUS  current
        DESCRIPTION
                      	"DSCP for policy rule."
        ::= { policyEntry 8 }

        policyTOS OBJECT-TYPE
        SYNTAX  INTEGER
        MAX-ACCESS  read-write
        STATUS  current
        DESCRIPTION
                      	"TOS for policy rule, 0~7"
        ::= { policyEntry 9 }

--        policyBandwidth OBJECT-TYPE
--        SYNTAX  INTEGER
--        MAX-ACCESS  read-write
--        STATUS  current
--       DESCRIPTION
--                      	"Bandwidth for policy rule"
--        ::= { policyEntry 10 }

        policySir OBJECT-TYPE
        SYNTAX  INTEGER
        MAX-ACCESS  read-write
        STATUS  current
        DESCRIPTION
                      	"SIR for policy rule"
        ::= { policyEntry 10 }

        policyPir OBJECT-TYPE
        SYNTAX  INTEGER
        MAX-ACCESS  read-write
        STATUS  current
        DESCRIPTION
                      	"Pir for policy rule"
        ::= { policyEntry 11 }

        policyOutOfProfileDSCP OBJECT-TYPE
        SYNTAX  INTEGER
        MAX-ACCESS  read-write
        STATUS  current
        DESCRIPTION
                      	"Out Of Profile DSCP for policy rule."
        ::= { policyEntry 12 }

        policyOutOfProfileGpCosqNew OBJECT-TYPE
        SYNTAX  INTEGER
        MAX-ACCESS  read-write
        STATUS  current
        DESCRIPTION
                      	"Out Of Profile Green packet to cosq new value."
        ::= { policyEntry 13 }

        policyForwardingAction OBJECT-TYPE
        SYNTAX  INTEGER
        {
        	noChange(1),
        	discardThePacket(2),
        	doNotDropTheMatchingFramePreviouslyMarkedForDopping(3)
        }
        MAX-ACCESS  read-write
        STATUS  current
        DESCRIPTION
                      	"Forwarding Action for policy rule"
        ::= { policyEntry 14 }

        policyPriorityAction OBJECT-TYPE
        SYNTAX  INTEGER
        {
        	noChange(1),
        	setThePackets802dot1Priority(2),
        	sendThePacketToPriorityQueue(3),
        	replaceThe802dot1PriorityFieldWithTheIpTosValue(4)
        }
        MAX-ACCESS  read-write
        STATUS  current
        DESCRIPTION
                      	"Priority Action for policy rule"
        ::= { policyEntry 15}

        policyDiffServAction OBJECT-TYPE
        SYNTAX  INTEGER
        {
        	noChange(1),
        	setThePacketsTosField(2),
        	replaceTheIpTosFieldWithThe802dot1PriorityValue(3),
        	setTheDiffservCodepointFieldInTheFrame(4)
        }
        MAX-ACCESS  read-write
        STATUS  current
        DESCRIPTION
                      	"DiffServ Action for policy rule"
        ::= { policyEntry 16}

        policyOutgoingAction OBJECT-TYPE
		SYNTAX	BITS {
			sendThePacketToTheMirrorPort(1),
			sendThePacketToTheEgressPort(2),
			sendTheMatchingFramesToTheEgressPort(3),
			setThePacketsVlanId(4)
		}
		MAX-ACCESS  read-create
		STATUS      current
		DESCRIPTION
	        "Outgoing Action for policy rule"
		::= { policyEntry 17 }

        policyMeteringEnable OBJECT-TYPE
        SYNTAX  INTEGER
        MAX-ACCESS  read-write
        STATUS  current
        DESCRIPTION
        	"Metering for Policy rule enabled/disabled."
        ::= { policyEntry 18 }

        policyOutOfProfileAction OBJECT-TYPE
		SYNTAX	BITS {
			dropThePacket(1),
			changeTheDscpValue(2),
			setOutDropPrecedence(3),
			doNotDropTheMatchingFramePreviouslyMarkedForDropping(4),
			setGpToCosqNew(5)
		}
		MAX-ACCESS  read-create
		STATUS      current
		DESCRIPTION
	        "Out Of Profile Action for policy rule"
		::= { policyEntry 19 }

        policyRowstatus OBJECT-TYPE
        SYNTAX  RowStatus
        MAX-ACCESS  read-create
        STATUS  current
        DESCRIPTION
                      	"Row Status for policy rule"
        ::= { policyEntry 20 }

        policyMirrorPort OBJECT-TYPE
        SYNTAX  INTEGER
        MAX-ACCESS  read-write
        STATUS  current
        DESCRIPTION
        	"Mirror Port."
        ::= { policyEntry 21 }

        policyCounter OBJECT-TYPE
        SYNTAX  EnabledStatus
        MAX-ACCESS  read-write
        STATUS  current
        DESCRIPTION
            "Counter enabled/disabled for policy."
        ::= { policyEntry 22 }

        policyLogging OBJECT-TYPE
        SYNTAX  EnabledStatus
        MAX-ACCESS  read-write
        STATUS  current
        DESCRIPTION
            "Logging enabled/disabled for policy."
        ::= { policyEntry 23 }

        policyRuleSet OBJECT-TYPE
        SYNTAX  DisplayString
        MAX-ACCESS  read-write
        STATUS  current
        DESCRIPTION
                      	"policy Rule Set."
        ::= { policySetup 2 }

	policyClearCounterAll OBJECT-TYPE
	SYNTAX  EnabledStatus
	MAX-ACCESS  read-write
	STATUS  current
	DESCRIPTION
			"Clear policy all counter, always return disable"
	::= { policySetup 3 }

	policyClearTable OBJECT-TYPE
	SYNTAX      SEQUENCE OF PolicyClearEntry
  	MAX-ACCESS  not-accessible
	STATUS      current
	DESCRIPTION
            ""
  ::= { policySetup 4 }

		policyClearEntry OBJECT-TYPE
	  SYNTAX      PolicyClearEntry
	  MAX-ACCESS  not-accessible
	  STATUS      current
	  DESCRIPTION
	  		"An entry in policyClearTable"
	  INDEX {
	  	policyName
	  }
		::= { policyClearTable 1 }

		PolicyClearEntry ::=
	        SEQUENCE {
				policyClearCounter		EnabledStatus
			}

		policyClearCounter OBJECT-TYPE
		SYNTAX  EnabledStatus
		MAX-ACCESS  read-write
		STATUS  current
		DESCRIPTION
				"Clear policy counter, always return disable"
		::= { policyClearEntry 1 }

  policyCounterTable	OBJECT-TYPE
  SYNTAX	SEQUENCE OF PolicyCounterEntry
  MAX-ACCESS  not-accessible
  STATUS  current
  DESCRIPTION
           	""
  ::= { policySetup 5 }

 		policyCounterEntry OBJECT-TYPE
        SYNTAX	PolicyCounterEntry
        MAX-ACCESS	not-accessible
        STATUS	current
        DESCRIPTION    	"An entry in policyCounterTable."
        INDEX          	{policyName, classifierName}
        ::= { policyCounterTable 1 }

      	PolicyCounterEntry ::=
				SEQUENCE {
        	policyIncommingPort		INTEGER,
        	policyPacketCount			Counter64
        }

        policyIncommingPort OBJECT-TYPE
        SYNTAX  INTEGER
        MAX-ACCESS  not-accessible
        STATUS  current
        DESCRIPTION
        	"incomming Port for policy rule, dot1dBasePort or 0 for all port."
        ::= { policyCounterEntry 1 }

		policyPacketCount OBJECT-TYPE
		SYNTAX  Counter64
		MAX-ACCESS  read-only
		STATUS  current
		DESCRIPTION
			"Counter for the policy, 65535 means counter disabled."
		::= { policyCounterEntry 2 }


--  148.uniPortOpModeSetup

-- 		uniPortOpModePortTable

        uniPortOpModePortTable  OBJECT-TYPE
        SYNTAX	SEQUENCE OF UniPortOpModePortEntry
        MAX-ACCESS  not-accessible
        STATUS  current
        DESCRIPTION
                 	""
        ::= { uniPortOpModeSetup 1 }

		uniPortOpModePortEntry  OBJECT-TYPE
        SYNTAX	UniPortOpModePortEntry
        MAX-ACCESS	not-accessible
        STATUS	current
        DESCRIPTION    	"An entry in uniPortOpModePortTable."
        INDEX          	{ dot1dBasePort }
        ::= { uniPortOpModePortTable 1 }

        UniPortOpModePortEntry ::=
           SEQUENCE {
        	uniPortOpModePortVlanTranslation		INTEGER,
        	uniPortOpModePortVlanXlateMissDrop			INTEGER,
        	uniPortOpModePortEgrVlanXlateMissDrop			INTEGER
           }

        uniPortOpModePortVlanTranslation OBJECT-TYPE
        SYNTAX  INTEGER {
            enable(0),
        	disable(1)
        }
        MAX-ACCESS  read-write
        STATUS  current
        DESCRIPTION
                      	""
        ::= { uniPortOpModePortEntry 1 }

        uniPortOpModePortVlanXlateMissDrop OBJECT-TYPE
        SYNTAX  INTEGER {
            enable(0),
        	disable(1)
        }
        MAX-ACCESS  read-write
        STATUS  current
        DESCRIPTION
                     	""
        ::= { uniPortOpModePortEntry 2 }

        uniPortOpModePortEgrVlanXlateMissDrop OBJECT-TYPE
        SYNTAX  INTEGER {
            enable(0),
        	disable(1)
        }
        MAX-ACCESS  read-write
        STATUS  current
        DESCRIPTION
                     	""
        ::= { uniPortOpModePortEntry 3 }

--  149.macInfo

--  	macTable
      	macTable	OBJECT-TYPE
        SYNTAX	SEQUENCE OF MacEntry
        MAX-ACCESS  not-accessible
        STATUS  current
        DESCRIPTION
                 	""
        ::= { macInfo 1 }

		macEntry OBJECT-TYPE
        SYNTAX	MacEntry
        MAX-ACCESS	not-accessible
        STATUS	current
        DESCRIPTION    	"An entry in macTable."
        INDEX          	{ macVid, macMacAddr }
        ::= { macTable 1 }

        MacEntry ::=
           SEQUENCE {
           	macVid	INTEGER,
        	macMacAddr	MacAddress,
        	macPort	INTEGER,
        	macType	INTEGER,
        	macUniportAid		DisplayString,
			macGemflow	DisplayString
           }

        macVid OBJECT-TYPE
        SYNTAX  INTEGER
        MAX-ACCESS  read-only
        STATUS  current
        DESCRIPTION
                      	""
        ::= { macEntry 1 }

        macMacAddr OBJECT-TYPE
        SYNTAX  MacAddress
        MAX-ACCESS  read-only
        STATUS  current
        DESCRIPTION
                      	""
        ::= { macEntry 2 }

        macPort OBJECT-TYPE
        SYNTAX  INTEGER
        MAX-ACCESS  read-only
        STATUS  current
        DESCRIPTION
                      	""
        ::= { macEntry 3 }

        macType OBJECT-TYPE
        SYNTAX  INTEGER{
            other(1),
        	invalid(2),
			learned(3),
			self(4),
			mgmt(5)
        }
        MAX-ACCESS  read-only
        STATUS  current
        DESCRIPTION 	"The status of this entry.  The meanings of the values
 	are:
 	    other(1) - none of the following.  This may include
 	        the case where some other MIB object (not the
 	        corresponding instance of dot1qTpFdbPort, nor an
 	        entry in the dot1qStaticUnicastTable) is being
 	        used to determine if and how frames addressed to
 	        the value of the corresponding instance of
 	        dot1qTpFdbAddress are being forwarded.
 	    invalid(2) - this entry is no longer valid (e.g., it
 	        was learned but has since aged out), but has not
 	        yet been flushed from the table.
 	    learned(3) - the value of the corresponding instance
 	        of dot1qTpFdbPort was learned and is being used.

 	    self(4) - the value of the corresponding instance of
 	        dot1qTpFdbAddress represents one of the device's
 	        addresses.  The corresponding instance of
 	        dot1qTpFdbPort indicates which of the device's
 	        ports has this address.
 	    mgmt(5) - the value of the corresponding instance of
 	        dot1qTpFdbAddress is also the value of an
 	        existing instance of dot1qStaticAddress."
        ::= { macEntry 4 }

        macUniportAid OBJECT-TYPE
        SYNTAX  DisplayString
        MAX-ACCESS  read-only
        STATUS  current
        DESCRIPTION
                      	""
        ::= { macEntry 5 }

		macGemflow OBJECT-TYPE
        SYNTAX  DisplayString
        MAX-ACCESS  read-only
        STATUS  current
        DESCRIPTION
                      	""
        ::= { macEntry 6 }

-- ******************************************************************
-- *
-- 150.antiMacSpoofSetup
-- *
-- ******************************************************************
-- *
-- * antiMacSpoofSetup Table
-- *
		antiMacSpoofState OBJECT-TYPE
        SYNTAX  EnabledStatus
        MAX-ACCESS  read-write
        STATUS  current
        DESCRIPTION
                      	""
        ::= { antiMacSpoofSetup 1 }

        antiMacSpoofPortTable OBJECT-TYPE
        SYNTAX	SEQUENCE OF AntiMacSpoofPortEntry
        MAX-ACCESS  not-accessible
        STATUS  current
        DESCRIPTION
                 	""
        ::= { antiMacSpoofSetup 2 }

		antiMacSpoofPortEntry OBJECT-TYPE
        SYNTAX	AntiMacSpoofPortEntry
        MAX-ACCESS	not-accessible
        STATUS	current
        DESCRIPTION    	"An entry in antiMacSpoofPortTable."
        INDEX          	{ dot1dBasePort }
        ::= { antiMacSpoofPortTable 1 }

        AntiMacSpoofPortEntry ::=
           SEQUENCE {
        	antiMacSpoofPortState		EnabledStatus
           }

        antiMacSpoofPortState OBJECT-TYPE
        SYNTAX  EnabledStatus
        MAX-ACCESS  read-write
        STATUS  current
        DESCRIPTION
                      	"Anti-mac Spoofing enabled/disabled on the port.
                      	Enable(1) means mac-spoofing is not allowed in this port."
        ::= { antiMacSpoofPortEntry 1 }

-- ******************************************************************
-- *
-- 153.protectSwitch
-- *
-- ******************************************************************
-- *
-- * protectSwitch
-- *
	protectSwitchMsc OBJECT IDENTIFIER ::= { protectSwitch 1 }

	protectSwitchPon OBJECT IDENTIFIER ::= { protectSwitch 2 }

        protectSwitchPonTable OBJECT-TYPE
        SYNTAX	SEQUENCE OF ProtectSwitchPonEntry
        MAX-ACCESS  not-accessible
        STATUS  current
        DESCRIPTION
                 	"This table manages GPON type-B protection switch."
        ::= { protectSwitchPon 1 }

	protectSwitchPonEntry OBJECT-TYPE
        SYNTAX	ProtectSwitchPonEntry
        MAX-ACCESS	not-accessible
        STATUS	current
        DESCRIPTION    	"An entry in protectSwitchPonEntry."
        INDEX          	{ dot1dBasePort, passivePort }
        ::= { protectSwitchPonTable 1 }

        ProtectSwitchPonEntry ::=
           SEQUENCE {
        	passivePort			INTEGER,
        	currWorkingPort			INTEGER,
        	currStandbyPort			INTEGER,
        	delimiterDetectedOnStandbyPort	INTEGER,
        	lastSwitchOverReason		INTEGER,
        	lastSwitchOverTimeStampYear	INTEGER,
        	lastSwitchOverTimeStampMonth	INTEGER,
        	lastSwitchOverTimeStampDay	INTEGER,
        	lastSwitchOverTimeStampHour	INTEGER,
        	lastSwitchOverTimeStampMinute	INTEGER,
        	lastSwitchOverTimeStampSecond	INTEGER,
        	switchOverTimes			INTEGER,
        	triggerSwitchOver		INTEGER,
        	protectSwitchPonRowstatus	RowStatus
           }

        passivePort OBJECT-TYPE
        SYNTAX  INTEGER
        MAX-ACCESS  not-accessible
        STATUS  current
        DESCRIPTION   	"The passive port of this protection pair."
        ::= { protectSwitchPonEntry 1 }

        currWorkingPort OBJECT-TYPE
        SYNTAX  INTEGER {
           noData(0)
        }
        MAX-ACCESS  read-only
        STATUS  current
        DESCRIPTION   	"The current working port. System is trying to bring up ONU at this port."
        ::= { protectSwitchPonEntry 2 }

        currStandbyPort OBJECT-TYPE
        SYNTAX  INTEGER {
           noData(0)
        }
        MAX-ACCESS  read-only
        STATUS  current
        DESCRIPTION   	"The current standby port. After a switch-over event occurs, it will be the next working port."
        ::= { protectSwitchPonEntry 3 }

        delimiterDetectedOnStandbyPort OBJECT-TYPE
        SYNTAX  INTEGER {
           noData(0),
           true(1),
           false(2)
        }
        MAX-ACCESS  read-only
        STATUS  current
        DESCRIPTION   	"It indicates whether the current standby port can detect delimiter on the PON fiber.
                         true(1) indicates at least one delimiter is detected when user query this MIB,
                         false(2) indicates no delimiter is detected."
        ::= { protectSwitchPonEntry 4 }

        lastSwitchOverReason OBJECT-TYPE
        SYNTAX  INTEGER {
           noData(0),
           lossOfSignal(1),
           manual(2),
           chipConnectionFailure(3),
           noOnuDetected(4)
        }
        MAX-ACCESS  read-only
        STATUS  current
        DESCRIPTION   	"It indicates the reason causes the last switch-over event.
                         noData(0) indicates no switch-over event happened.
                         lossOfSignal(1) indicates LOS happened on the working port.
                         manual(2) indicates administrator triggered it manully.
                         chipConnectionFailure(3) indicates system lost the connection to the GPON chip.
                         noOnuDetected(4) indicates no ONU detected at working port."
        ::= { protectSwitchPonEntry 5 }

        lastSwitchOverTimeStampYear OBJECT-TYPE
        SYNTAX  INTEGER
        MAX-ACCESS  read-only
        STATUS  current
        DESCRIPTION   	"It indicates the year the last switch-over event happened."
        ::= { protectSwitchPonEntry 6 }

        lastSwitchOverTimeStampMonth OBJECT-TYPE
        SYNTAX  INTEGER
        MAX-ACCESS  read-only
        STATUS  current
        DESCRIPTION   	"It indicates the month the last switch-over event happened."
        ::= { protectSwitchPonEntry 7 }

        lastSwitchOverTimeStampDay OBJECT-TYPE
        SYNTAX  INTEGER
        MAX-ACCESS  read-only
        STATUS  current
        DESCRIPTION   	"It indicates the day the last switch-over event happened."
        ::= { protectSwitchPonEntry 8 }

        lastSwitchOverTimeStampHour OBJECT-TYPE
        SYNTAX  INTEGER
        MAX-ACCESS  read-only
        STATUS  current
        DESCRIPTION   	"It indicates the hour the last switch-over event happened."
        ::= { protectSwitchPonEntry 9 }

        lastSwitchOverTimeStampMinute OBJECT-TYPE
        SYNTAX  INTEGER
        MAX-ACCESS  read-only
        STATUS  current
        DESCRIPTION   	"It indicates the minute the last switch-over event happened."
        ::= { protectSwitchPonEntry 10 }

        lastSwitchOverTimeStampSecond OBJECT-TYPE
        SYNTAX  INTEGER
        MAX-ACCESS  read-only
        STATUS  current
        DESCRIPTION   	"It indicates the second the last switch-over event happened."
        ::= { protectSwitchPonEntry 11 }

        switchOverTimes OBJECT-TYPE
        SYNTAX  INTEGER
        MAX-ACCESS  read-only
        STATUS  current
        DESCRIPTION   	"It indicates the times of switch-over event happened since the protection pair was activated."
        ::= { protectSwitchPonEntry 12 }

        triggerSwitchOver OBJECT-TYPE
        SYNTAX  INTEGER
        MAX-ACCESS  read-write
        STATUS  current
        DESCRIPTION   	"Setting this MIB to 1 to trigger a switch-over manually."
        ::= { protectSwitchPonEntry 13 }

        protectSwitchPonRowstatus OBJECT-TYPE
        SYNTAX  RowStatus
        MAX-ACCESS  read-create
        STATUS  current
        DESCRIPTION   	"Row Status for a protection pair."
        ::= { protectSwitchPonEntry 14 }

-- ******************************************************************
-- *
-- 157. rate threshold port mib
-- *
-- ******************************************************************



-- *
-- * rate threshold port table
-- *

        rateThresholdPortTable OBJECT-TYPE
        SYNTAX	SEQUENCE OF RateThresholdPortEntry
        MAX-ACCESS  not-accessible
        STATUS  current
        DESCRIPTION
                 	""
        ::= { rateThresholdSetup 1 }

		rateThresholdPortEntry OBJECT-TYPE
        SYNTAX	RateThresholdPortEntry
        MAX-ACCESS	not-accessible
        STATUS	current
        DESCRIPTION    	"An entry in rateThresholdPortTable."
        INDEX          	{ dot1dBasePort }
        ::= { rateThresholdPortTable 1 }

        RateThresholdPortEntry ::=
           SEQUENCE {
        	rateThresholdPortIngress  INTEGER,
        	rateThresholdPortEgress    INTEGER,
        	rateUsagePercentageIngress INTEGER,
        	rateUsagePercentageEgress  INTEGER,
        	rateUsageKbpsIngress       INTEGER,
        	rateUsageKbpsEgress        INTEGER

           }

        rateThresholdPortIngress OBJECT-TYPE
        SYNTAX  INTEGER
        MAX-ACCESS  read-write
        STATUS  current
        DESCRIPTION
                      	"Ingress rate threshold on the port. (unit is kbps and 0 is disable the threshold).
                      	The range of XE port is from 0 to 10000000 Kbps.
                      	The range of GPON port is from 0 to 2500000 Kbps.
                      	The range of GE port is from 0 to 1000000 Kbps."
        ::= { rateThresholdPortEntry 1 }

        rateThresholdPortEgress OBJECT-TYPE
        SYNTAX  INTEGER
        MAX-ACCESS  read-write
        STATUS  current
        DESCRIPTION
                      	"Egress rate threshold on the port. (unit is kbps and 0 is disable the threshold).
                      	The range of XE port is from 0 to 10000000 Kbps.
                      	The range of GPON port is from 0 to 2500000 Kbps.
                      	The range of GE port is from 0 to 1000000 Kbps."
        ::= { rateThresholdPortEntry 2 }

        rateUsagePercentageIngress OBJECT-TYPE
        SYNTAX  INTEGER
        MAX-ACCESS  read-only
        STATUS  current
        DESCRIPTION
                      	"The egress rate usage on the port( uint is percentage).
                      	The 100% rate of XE port is 10000000 Kbps.
                      	The 100% rate of GPON port is 2500000 Kbps.
                      	The 100% rate of GE port is 1000000 Kbps."
        ::= { rateThresholdPortEntry 3 }

        rateUsagePercentageEgress OBJECT-TYPE
        SYNTAX  INTEGER
        MAX-ACCESS  read-only
        STATUS  current
        DESCRIPTION
                      	"The ingress rate usage on the port( uint is percentage).
                      	The 100% rate of XE port is 10000000 Kbps.
                      	The 100% rate of GPON port is 2500000 Kbps.
                      	The 100% rate of GE port is 1000000 Kbps."
        ::= { rateThresholdPortEntry 4 }

        rateUsageKbpsIngress OBJECT-TYPE
        SYNTAX  INTEGER
        MAX-ACCESS  read-only
        STATUS  current
        DESCRIPTION
                      	"The egress rate usage on the port( uint is Kbps).
                      	The maximum rate of XE port is 10000000 Kbps.
                      	The maximum rate of GPON port is 2500000 Kbps.
                      	The maximum rate of GE port is 1000000 Kbps."
        ::= { rateThresholdPortEntry 5 }

        rateUsageKbpsEgress OBJECT-TYPE
        SYNTAX  INTEGER
        MAX-ACCESS  read-only
        STATUS  current
        DESCRIPTION
                      	"The egress rate usage on the port( uint is Kbps).
                      	The maximum rate of XE port is 10000000 Kbps.
                      	The maximum rate of GPON port is 2500000 Kbps.
                      	The maximum rate of GE port is 1000000 Kbps."
        ::= { rateThresholdPortEntry 6 }

-- ******************************************************************
-- *
-- 158.erpsSetup
-- *
-- ******************************************************************
-- *
-- * erpsSetup Table
-- *
		erpsState OBJECT-TYPE
        SYNTAX  EnabledStatus
        MAX-ACCESS  read-write
        STATUS  current
        DESCRIPTION
                      	""
        ::= { erpsSetup 1 }

        erpsRingTable OBJECT-TYPE
        SYNTAX	SEQUENCE OF ErpsRingEntry
        MAX-ACCESS  not-accessible
        STATUS  current
        DESCRIPTION
                 	""
        ::= { erpsSetup 2 }

		erpsRingEntry OBJECT-TYPE
        SYNTAX	ErpsRingEntry
        MAX-ACCESS	not-accessible
        STATUS	current
        DESCRIPTION    	"An entry in erpsRingTable."
        INDEX          	{ erpsRingIndex }
        ::= { erpsRingTable 1 }

        ErpsRingEntry ::=
           SEQUENCE {
			erpsPort0               INTEGER,
			erpsPort1               INTEGER,
			erpsRingId              INTEGER,
			erpsCcmPort0GroupName   DisplayString,
			erpsCcmPort0Level       INTEGER,
			erpsCcmPort0Vlan        INTEGER,
			erpsCcmPort0TxName      INTEGER,
			erpsCcmPort0Period      INTEGER,
			erpsCcmPort0Priority    INTEGER,
			erpsCcmPort0IntPriority INTEGER,
			erpsCcmPort0RxName      INTEGER,
			erpsCcmPort1GroupName   DisplayString,
			erpsCcmPort1Level       INTEGER,
			erpsCcmPort1Vlan        INTEGER,
			erpsCcmPort1TxName      INTEGER,
			erpsCcmPort1Period      INTEGER,
			erpsCcmPort1Priority    INTEGER,
			erpsCcmPort1IntPriority INTEGER,
			erpsCcmPort1RxName      INTEGER,
			erpsRapsPort0Vlan       INTEGER,
			erpsRapsPort0priority   INTEGER,
			erpsRapsPort0Level      INTEGER,
			erpsRapsPort1Vlan       INTEGER,
			erpsRapsPort1priority   INTEGER,
			erpsRapsPort1Level      INTEGER,
			erpsRevertiveMode       EnabledStatus,
			erpsWtr                 INTEGER,
			erpsRplOwner            INTEGER,
			erpsRplNeighbour        INTEGER,
			erpsTunnelPort          INTEGER,
        	erpsRingRowStatus	    RowStatus,
			erpsRingIndex           INTEGER
			}

		erpsPort0 OBJECT-TYPE
        SYNTAX  INTEGER
        MAX-ACCESS  read-write
        STATUS  current
        DESCRIPTION
                      	"Erps ring port0."
        ::= { erpsRingEntry 1 }

        erpsPort1 OBJECT-TYPE
        SYNTAX  INTEGER
        MAX-ACCESS  read-write
        STATUS  current
        DESCRIPTION
                      	"Erps ring port1."
        ::= { erpsRingEntry 2 }

        erpsRingId OBJECT-TYPE
        SYNTAX  INTEGER
        MAX-ACCESS  read-write
        STATUS  current
        DESCRIPTION
                      	"Erps ring Id."
        ::= { erpsRingEntry 3 }

        erpsCcmPort0GroupName OBJECT-TYPE
        SYNTAX  DisplayString
        MAX-ACCESS  read-write
        STATUS  current
        DESCRIPTION
                      	"Erps ring port0 ccm group name."
        ::= { erpsRingEntry 4 }

        erpsCcmPort0Level OBJECT-TYPE
        SYNTAX  INTEGER
        MAX-ACCESS  read-write
        STATUS  current
        DESCRIPTION
                      	"Erps ring port0 ccm levle."
        ::= { erpsRingEntry 5 }

        erpsCcmPort0Vlan OBJECT-TYPE
        SYNTAX  INTEGER
        MAX-ACCESS  read-write
        STATUS  current
        DESCRIPTION
                      	"Erps ring port0 ccm vlan."
        ::= { erpsRingEntry 6 }

        erpsCcmPort0TxName OBJECT-TYPE
        SYNTAX  INTEGER
        MAX-ACCESS  read-write
        STATUS  current
        DESCRIPTION
                      	"Erps ring port0 ccm tx name."
        ::= { erpsRingEntry 7 }

        erpsCcmPort0Period OBJECT-TYPE
        SYNTAX  INTEGER{
        none(0),
        erpsCcm3ms(1),
        erpsCcm10ms(2),
        erpsCcm100ms(3),
        erpsCcm1s(4),
        erpsCcm10s(5),
        erpsCcm1min(6),
        erpsCcm10min(7)
		}
        MAX-ACCESS  read-write
        STATUS  current
        DESCRIPTION
                      	"Erps ring port0 ccm period."
        ::= { erpsRingEntry 8 }

        erpsCcmPort0Priority OBJECT-TYPE
        SYNTAX  INTEGER
        MAX-ACCESS  read-write
        STATUS  current
        DESCRIPTION
                      	"Erps ring port0 ccm priority."
        ::= { erpsRingEntry 9 }

        erpsCcmPort0IntPriority OBJECT-TYPE
        SYNTAX  INTEGER
        MAX-ACCESS  read-write
        STATUS  current
        DESCRIPTION
                      	"Erps ring port0 ccm int priority."
        ::= { erpsRingEntry 10 }

        erpsCcmPort0RxName OBJECT-TYPE
        SYNTAX  INTEGER
        MAX-ACCESS  read-write
        STATUS  current
        DESCRIPTION
                      	"Erps ring port 0 ccm rx name."
        ::= { erpsRingEntry 11 }

        erpsCcmPort1GroupName OBJECT-TYPE
        SYNTAX  DisplayString
        MAX-ACCESS  read-write
        STATUS  current
        DESCRIPTION
                      	"Erps ring port1 ccm group name."
        ::= { erpsRingEntry 12 }

        erpsCcmPort1Level OBJECT-TYPE
        SYNTAX  INTEGER
        MAX-ACCESS  read-write
        STATUS  current
        DESCRIPTION
                      	"Erps ring port1 ccm levle."
        ::= { erpsRingEntry 13 }

        erpsCcmPort1Vlan OBJECT-TYPE
        SYNTAX  INTEGER
        MAX-ACCESS  read-write
        STATUS  current
        DESCRIPTION
                      	"Erps ring port1 ccm vlan."
        ::= { erpsRingEntry 14 }

        erpsCcmPort1TxName OBJECT-TYPE
        SYNTAX  INTEGER
        MAX-ACCESS  read-write
        STATUS  current
        DESCRIPTION
                      	"Erps ring port1 ccm tx name."
        ::= { erpsRingEntry 15 }

        erpsCcmPort1Period OBJECT-TYPE
        SYNTAX  INTEGER{
        none(0),
        erpsCcm3ms(1),
        erpsCcm10ms(2),
        erpsCcm100ms(3),
        erpsCcm1s(4),
        erpsCcm10s(5),
        erpsCcm1min(6),
        erpsCcm10min(7)
        }
        MAX-ACCESS  read-write
        STATUS  current
        DESCRIPTION
                      	"Erps ring port1 ccm period."
        ::= { erpsRingEntry 16 }

        erpsCcmPort1Priority OBJECT-TYPE
        SYNTAX  INTEGER
        MAX-ACCESS  read-write
        STATUS  current
        DESCRIPTION
                      	"Erps ring port1 ccm priority."
        ::= { erpsRingEntry 17 }

        erpsCcmPort1IntPriority OBJECT-TYPE
        SYNTAX  INTEGER
        MAX-ACCESS  read-write
        STATUS  current
        DESCRIPTION
                      	"Erps ring port1 ccm int priority."
        ::= { erpsRingEntry 18 }

        erpsCcmPort1RxName OBJECT-TYPE
        SYNTAX  INTEGER
        MAX-ACCESS  read-write
        STATUS  current
        DESCRIPTION
                      	"Erps ring port1 ccm rx name."
        ::= { erpsRingEntry 19 }

        erpsRapsPort0Vlan OBJECT-TYPE
        SYNTAX  INTEGER
        MAX-ACCESS  read-write
        STATUS  current
        DESCRIPTION
                      	"Erps ring port0 raps vlan."
        ::= { erpsRingEntry 20 }

        erpsRapsPort0priority OBJECT-TYPE
        SYNTAX  INTEGER
        MAX-ACCESS  read-write
        STATUS  current
        DESCRIPTION
                      	"Erps ring port0 raps priority."
        ::= { erpsRingEntry 21 }

        erpsRapsPort0Level OBJECT-TYPE
        SYNTAX  INTEGER
        MAX-ACCESS  read-write
        STATUS  current
        DESCRIPTION
                      	"Erps ring port0 rap level."
        ::= { erpsRingEntry 22 }

        erpsRapsPort1Vlan OBJECT-TYPE
        SYNTAX  INTEGER
        MAX-ACCESS  read-write
        STATUS  current
        DESCRIPTION
                      	"Erps ring port1 raps vlan."
        ::= { erpsRingEntry 23 }

        erpsRapsPort1priority OBJECT-TYPE
        SYNTAX  INTEGER
        MAX-ACCESS  read-write
        STATUS  current
        DESCRIPTION
                      	"Erps ring port1 raps priority."
        ::= { erpsRingEntry 24 }

        erpsRapsPort1Level OBJECT-TYPE
        SYNTAX  INTEGER
        MAX-ACCESS  read-write
        STATUS  current
        DESCRIPTION
                      	"Erps ring port1 raps level."
        ::= { erpsRingEntry 25 }

        erpsRevertiveMode OBJECT-TYPE
        SYNTAX  EnabledStatus
        MAX-ACCESS  read-write
        STATUS  current
        DESCRIPTION
                      	"Erps ring RevertiveMode enable/disable."
        ::= { erpsRingEntry 26 }

        erpsWtr OBJECT-TYPE
        SYNTAX  INTEGER
        MAX-ACCESS  read-write
        STATUS  current
        DESCRIPTION
                      	"Erps ring WTR."
        ::= { erpsRingEntry 27 }

        erpsRplOwner OBJECT-TYPE
        SYNTAX  INTEGER{
        none(0),
        port0(1),
        port1(2)
        }
        MAX-ACCESS  read-write
        STATUS  current
        DESCRIPTION
                      	"Erps ring owner port."
        ::= { erpsRingEntry 28 }

        erpsRplNeighbour OBJECT-TYPE
        SYNTAX  INTEGER{
        none(0),
        port0(1),
        port1(2)
        }
        MAX-ACCESS  read-write
        STATUS  current
        DESCRIPTION
                      	"Erps ring neighbour port."
        ::= { erpsRingEntry 29 }

        erpsTunnelPort OBJECT-TYPE
        SYNTAX  INTEGER{
        none(0),
        port0(1),
        port1(2)
        }
        MAX-ACCESS  read-write
        STATUS  current
        DESCRIPTION
                      	"Erps ring tunnel port."
        ::= { erpsRingEntry 30 }

		erpsRingRowStatus OBJECT-TYPE
        SYNTAX  RowStatus
        MAX-ACCESS  read-create
        STATUS  current
        DESCRIPTION
                      	"Erps ring enable/disable."
        ::= { erpsRingEntry 31 }

		erpsRingIndex OBJECT-TYPE
        SYNTAX  INTEGER
        MAX-ACCESS  read-only
        STATUS  current
        DESCRIPTION
                      	"Erps ring index."
        ::= { erpsRingEntry 32 }

-- ******************************************************************
-- *
-- 159.wred
-- *
-- ******************************************************************
-- *
-- * wred Table
-- *
		wredState OBJECT-TYPE
        SYNTAX  EnabledStatus
        MAX-ACCESS  read-write
        STATUS  current
        DESCRIPTION
                      	""
        ::= { wred 1 }

-- ******************************************************************
-- *
-- 160.dhcpClientTest
-- *
-- ******************************************************************
-- *
-- * dhcpClientTest Table
-- *
        dhcpClientTestTimeout OBJECT-TYPE
        SYNTAX  INTEGER
        MAX-ACCESS  read-write
        STATUS  current
        DESCRIPTION
                        "The timeout of each DHCP session."
        ::= { dhcpClientTest 1 }

        dhcpClientTestPortTable OBJECT-TYPE
        SYNTAX  SEQUENCE OF DhcpClientTestPortEntry
        MAX-ACCESS  not-accessible
        STATUS  current
        DESCRIPTION
                        ""
        ::= { dhcpClientTest 2 }

        dhcpClientTestPortEntry OBJECT-TYPE
        SYNTAX  DhcpClientTestPortEntry
        MAX-ACCESS  not-accessible
        STATUS  current
        DESCRIPTION     "An entry in dhcpClientTestPortTable."
        INDEX           { dot1dBasePort }
        ::= { dhcpClientTestPortTable 1 }

        DhcpClientTestPortEntry ::=
           SEQUENCE {
             dhcpClientTestPortState     INTEGER,
             dhcpClientTestPortIp            IpAddress,
             dhcpClientTestPortOptNniSvid    INTEGER,
             dhcpClientTestPortOptSnicvid    INTEGER,
             dhcpClientTestPortOptOntid      INTEGER,
             dhcpClientTestPortOptOntcardid  INTEGER,
             dhcpClientTestPortOptUniport    INTEGER,
             dhcpClientTestPortOptOntsn      DisplayString,
             dhcpClientTestPortStartSniSvid  INTEGER,
             dhcpClientTestPortStopSniSvid  INTEGER,
           }

        dhcpClientTestPortState OBJECT-TYPE
        SYNTAX  INTEGER {
            test_process_does_not_start_yet(0),
            test_process_is_stopped_by_command(1),
            test_process_is_ongoing(2),
            receive_dhcp_offer_fail(3),
            receive_dhcp_ack_fail(4),
            test_process_successful(5)
        }
        MAX-ACCESS  read-only
        STATUS  current
        DESCRIPTION
                        "Display DHCP client-test result."
        ::= { dhcpClientTestPortEntry 1 }

        dhcpClientTestPortIp OBJECT-TYPE
        SYNTAX  IpAddress
        MAX-ACCESS  read-only
        STATUS  current
        DESCRIPTION
                        "Display DHCP client-test IP address."
        ::= { dhcpClientTestPortEntry 2 }

        dhcpClientTestPortOptNniSvid OBJECT-TYPE
        SYNTAX  INTEGER (0..4094)
        MAX-ACCESS  read-write
        STATUS  current
        DESCRIPTION
                        "Configure DHCP client-test option for NNI SVID, 0 represents empty."
        ::= { dhcpClientTestPortEntry 3 }

        dhcpClientTestPortOptSnicvid OBJECT-TYPE
        SYNTAX  INTEGER (0..4094)
        MAX-ACCESS  read-write
        STATUS  current
        DESCRIPTION
                        "Configure DHCP client-test option for SNI CVID, 0 represents empty."
        ::= { dhcpClientTestPortEntry 4 }

        dhcpClientTestPortOptOntid OBJECT-TYPE
        SYNTAX  INTEGER (0..128)
        MAX-ACCESS  read-write
        STATUS  current
        DESCRIPTION
                        "Configure DHCP client-test option for ont id, 0 represents empty."
        ::= { dhcpClientTestPortEntry 5 }

        dhcpClientTestPortOptOntcardid OBJECT-TYPE
        SYNTAX  INTEGER (0..16)
        MAX-ACCESS  read-write
        STATUS  current
        DESCRIPTION
                        "Configure DHCP client-test option for ont card id, 0 represents empty."
        ::= { dhcpClientTestPortEntry 6 }

        dhcpClientTestPortOptUniport OBJECT-TYPE
        SYNTAX  INTEGER (0..128)
        MAX-ACCESS  read-write
        STATUS  current
        DESCRIPTION
                        "Configure DHCP client-test option for uniport, 0 represents empty."
        ::= { dhcpClientTestPortEntry 7 }

        dhcpClientTestPortOptOntsn OBJECT-TYPE
        SYNTAX  DisplayString
        MAX-ACCESS  read-write
        STATUS  current
        DESCRIPTION
                        "Configure DHCP client-test option for ONT serial number (0~16 characters)."
        ::= { dhcpClientTestPortEntry 8 }

        dhcpClientTestPortStartSniSvid OBJECT-TYPE
        SYNTAX  INTEGER (1..4094)
        MAX-ACCESS  read-write
        STATUS  current
        DESCRIPTION
                        "Start DHCP client-test on SNI SVID."
        ::= { dhcpClientTestPortEntry 9 }

        dhcpClientTestPortStopSniSvid OBJECT-TYPE
        SYNTAX  INTEGER (1..4094)
        MAX-ACCESS  read-write
        STATUS  current
        DESCRIPTION
                        "Stop DHCP client-test on SNI SVID."
        ::= { dhcpClientTestPortEntry 10 }

-- ******************************************************************
-- *
-- 161.sysTimeRef
-- *
-- ******************************************************************
-- *
-- * sysTimeRef Table
-- *
        sysTimeRefPTPState OBJECT-TYPE
        SYNTAX  EnabledStatus
        MAX-ACCESS  read-write
        STATUS  current
        DESCRIPTION
                        "The status of timing reference ptp."
        ::= { sysTimeRef 1 }

-- ******************************************************************
-- *
-- 162.dhcpL2Agent
-- *
-- ******************************************************************
-- *
-- * dhcpL2Agent Table
-- *

        dhcpL2AgentTable OBJECT-TYPE
        SYNTAX  SEQUENCE OF DhcpL2AgentEntry
        MAX-ACCESS  not-accessible
        STATUS  current
        DESCRIPTION
                        ""
        ::= { dhcpL2Agent 1 }

        dhcpL2AgentEntry OBJECT-TYPE
        SYNTAX  DhcpL2AgentEntry
        MAX-ACCESS  not-accessible
        STATUS  current
        DESCRIPTION     "An entry in dhcpL2AgentTable."
        INDEX           { dhcpL2AgentVid }
        ::= { dhcpL2AgentTable 1 }

        DhcpL2AgentEntry ::=
           SEQUENCE {
             dhcpL2AgentVid     INTEGER,
             dhcpL2AgentEnable            INTEGER,
             dhcpL2AgentOpt82CircuitIdInfo    DisplayString,
             dhcpL2AgentOpt82RemoteIdInfo    DisplayString,
             dhcpL2AgentRowStatus      RowStatus,
             dhcpL2AgentOpt18InterfaceIdInfo	DisplayString,
             dhcpL2AgentOpt37RemoteIdInfo		DisplayString,
             dhcpL2AgentLDRAEnable            INTEGER
			 }

        dhcpL2AgentVid OBJECT-TYPE
        SYNTAX  INTEGER (1..4094)
        MAX-ACCESS  read-only
        STATUS  current
        DESCRIPTION
                        "Display DHCP L2 agent by Vlan."
        ::= { dhcpL2AgentEntry 1 }

        dhcpL2AgentEnable OBJECT-TYPE
        SYNTAX  INTEGER{
        disable(0),
        enable(1)
        }
        MAX-ACCESS  read-only
        STATUS  current
        DESCRIPTION
                        "Enables DHCP L2 agent by Vlan."
        ::= { dhcpL2AgentEntry 2 }

        dhcpL2AgentOpt82CircuitIdInfo OBJECT-TYPE
        SYNTAX  DisplayString
        MAX-ACCESS  read-write
        STATUS  current
        DESCRIPTION
                "set option info of dhcp option82 circuit-id, maximun length is 127 characters.
                (Note: When transform info to circuit ID, the transform result will be truncated to 127 characters)
                 Input string is composed by the following components
                 special characters except % and space e.g. ~`!@#$^&*()-=_+{}<>?,./
                 %%: equals character %
                 %space: equals character space
                 %mac: client source mac
                 %hname: host device name
                 %pid: pon port index
                 %oid: ont index
                 %ocid: ont card index
                 %upid: uniport index
                 %nnisvlan: SVLAN ID on network-network interface
                 %snisvlan: SVLAN ID on service-network interface
                 %snicvlan: CVLAN ID on service-network interface
                 %sn: serial number of remote ont
                 %ontname: will be translated into ONT model name
                 %ontdesc: will be translated into ONT description
                 %ontpasswd: will be translated into ONT password
                 Note :
                    (1) For DHCP snooping feature
                        A. dhcpSnpVlanEntryOption82Enable
                        B. dhcpSnpVlanEntryInfo
                        C. dhcpSnpVlanEntryOption82FormatEnable
                        D. dhcpL2AgentOpt82CircuitIdInfo or dhcpL2AgentOpt82RemoteIdInfo
                        For pon ports, OLT uses below rules as dhcp option-82 configurations.
                            (D) > (C) > (A) = (B)
                    (2) For DHCP relay feature
                        A. dhcpRelayOption82Enable
                        B. dhcpRelayInfoEnable
                        C. dhcpRelayOption82Format
                        D. dhcpL2AgentOpt82CircuitIdInfo or dhcpL2AgentOpt82RemoteIdInfo
                        For pon ports, OLT uses below rules as dhcp option-82 configurations.
                            (D) > (C) > (A) = (B)
                    (3) For DHCP smart-relay feature
                        A. globalDhcpRelayOption82Enable
                        B. globalDhcpRelayInfoEnable
                        C. globalDhcpRelayOption82Format
                        D. dhcpL2AgentOpt82CircuitIdInfo or dhcpL2AgentOpt82RemoteIdInfo
                        For pon ports, OLT uses below rules as dhcp option-82 configurations.
                            (D) > (C) > (A) = (B)
                 "
        ::= { dhcpL2AgentEntry 3 }

        dhcpL2AgentOpt82RemoteIdInfo OBJECT-TYPE
        SYNTAX  DisplayString
        MAX-ACCESS  read-write
        STATUS  current
        DESCRIPTION
               "set option info of dhcp option82 remote-id, maximun length is 95 characters.
                (Note: When transform info to circuit ID, the transform result will be truncated to 95 characters)
                 Input string is composed by the following components
                 special characters except % and space e.g. ~`!@#$^&*()-=_+{}<>?,./
                 %%: equals character %
                 %space: equals character space
                 %mac: client source mac
                 %hname: host device name
                 %pid: pon port index
                 %oid: ont index
                 %ocid: ont card index
                 %upid: uniport index
                 %nnisvlan: SVLAN ID on network-network interface
                 %snisvlan: SVLAN ID on service-network interface
                 %snicvlan: CVLAN ID on service-network interface
                 %sn: serial number of remote ont
                 %ontname: will be translated into ONT model name
                 %ontdesc: will be translated into ONT description
                 %ontpasswd: will be translated into ONT password
                 Note :
                    (1) For DHCP snooping feature
                        A. dhcpSnpVlanEntryOption82Enable
                        B. dhcpSnpVlanEntryInfo
                        C. dhcpSnpVlanEntryOption82FormatEnable
                        D. dhcpL2AgentOpt82CircuitIdInfo or dhcpL2AgentOpt82RemoteIdInfo
                        For pon ports, OLT uses below rules as dhcp option-82 configurations.
                            (D) > (C) > (A) = (B)
                    (2) For DHCP relay feature
                        A. dhcpRelayOption82Enable
                        B. dhcpRelayInfoEnable
                        C. dhcpRelayOption82Format
                        D. dhcpL2AgentOpt82CircuitIdInfo or dhcpL2AgentOpt82RemoteIdInfo
                        For pon ports, OLT uses below rules as dhcp option-82 configurations.
                            (D) > (C) > (A) = (B)
                    (3) For DHCP smart-relay feature
                        A. globalDhcpRelayOption82Enable
                        B. globalDhcpRelayInfoEnable
                        C. globalDhcpRelayOption82Format
                        D. dhcpL2AgentOpt82CircuitIdInfo or dhcpL2AgentOpt82RemoteIdInfo
                        For pon ports, OLT uses below rules as dhcp option-82 configurations.
                            (D) > (C) > (A) = (B)
                "
        ::= { dhcpL2AgentEntry 4 }

        dhcpL2AgentRowStatus OBJECT-TYPE
        SYNTAX  RowStatus
        MAX-ACCESS  read-write
        STATUS  current
        DESCRIPTION
                        ""
        ::= { dhcpL2AgentEntry 5 }

	dhcpL2AgentOpt18InterfaceIdInfo OBJECT-TYPE
        SYNTAX  DisplayString
        MAX-ACCESS  read-write
        STATUS  current
        DESCRIPTION
                "set option info of dhcp option18 interface-id, maximun length is 127 characters.
                (Note: When transform info to circuit ID, the transform result will be truncated to 127 characters)
                 Input string is composed by the following components
                 special characters except % and space e.g. ~`!@#$^&*()-=_+{}<>?,./
                 %%: equals character %
                 %space: equals character space
                 %mac: client source mac
                 %hname: host device name
                 %pid: pon port index
                 %oid: ont index
                 %ocid: ont card index
                 %upid: uniport index
                 %nnisvlan: SVLAN ID on network-network interface
                 %snisvlan: SVLAN ID on service-network interface
                 %snicvlan: CVLAN ID on service-network interface
                 %sn: serial number of remote ont
                 %ontname: will be translated into ONT model name
                 %ontdesc: will be translated into ONT description
                 %ontpasswd: will be translated into ONT password
                "
        ::= { dhcpL2AgentEntry 6 }

        dhcpL2AgentOpt37RemoteIdInfo OBJECT-TYPE
        SYNTAX  DisplayString
        MAX-ACCESS  read-write
        STATUS  current
        DESCRIPTION
                "set option info of dhcp option37 remote-id, maximun length is 95 characters.
                (Note: When transform info to circuit ID, the transform result will be truncated to 95 characters)
                 Input string is composed by the following components
                 special characters except % and space e.g. ~`!@#$^&*()-=_+{}<>?,./
                 %%: equals character %
                 %space: equals character space
                 %mac: client source mac
                 %hname: host device name
                 %pid: pon port index
                 %oid: ont index
                 %ocid: ont card index
                 %upid: uniport index
                 %nnisvlan: SVLAN ID on network-network interface
                 %snisvlan: SVLAN ID on service-network interface
                 %snicvlan: CVLAN ID on service-network interface
                 %sn: serial number of remote ont
                 %ontname: will be translated into ONT model name
                 %ontdesc: will be translated into ONT description
                 %ontpasswd: will be translated into ONT password
                "
        ::= { dhcpL2AgentEntry 7 }

        dhcpL2AgentLDRAEnable OBJECT-TYPE
        SYNTAX  INTEGER{
         		enable(1),
         		disable(2)
        }
        MAX-ACCESS  read-write
        STATUS  current
        DESCRIPTION
                        "Enables LDRA by Vlan."
        ::= { dhcpL2AgentEntry 8 }

-- 	******************************************************************
-- *
-- 163. mac forced forwarding
-- *
-- ******************************************************************

    macFFState OBJECT-TYPE
    SYNTAX  EnabledStatus
    MAX-ACCESS  read-write
    STATUS  current
    DESCRIPTION
                  	"mac forced forwarding enabled/disabled for the OLT."
    ::= { macForcedForwarding 1 }

    maxNumberOfMacFF OBJECT-TYPE
    SYNTAX  INTEGER
    MAX-ACCESS  read-only
    STATUS  current
    DESCRIPTION
                  	"The maximum number of mac forced forwarding entries that can be created"
    ::= { macForcedForwarding 2 }

-- 		macFFTable
    macFFTable OBJECT-TYPE
    SYNTAX	SEQUENCE OF MacFFEntry
    MAX-ACCESS  not-accessible
    STATUS  current
    DESCRIPTION
             	""
    ::= { macForcedForwarding 3 }

			macFFEntry OBJECT-TYPE
	        SYNTAX	MacFFEntry
	        MAX-ACCESS	not-accessible
	        STATUS	current
	        DESCRIPTION    	"The mac forced forwarding entry."
	        INDEX          	{ macFFVlan, macFFIpSubnet, macFFIpMaskBits}
	        ::= { macFFTable 1 }

        MacFFEntry ::=
           SEQUENCE {
        	macFFVlan		INTEGER,
        	macFFIpSubnet	IpAddress,
        	macFFIpMaskBits	INTEGER,
	       	macFFGateway	IpAddress,
	       	macFFRowStatus	RowStatus
           }

        macFFVlan OBJECT-TYPE
        SYNTAX  INTEGER
        MAX-ACCESS  not-accessible
        STATUS  current
        DESCRIPTION
                     	"The VLAN of the mac forced forwarding entry.(1-4094)"
        ::= { macFFEntry 1 }

        macFFIpSubnet OBJECT-TYPE
        SYNTAX  IpAddress
        MAX-ACCESS  not-accessible
        STATUS  current
        DESCRIPTION
                     	"The ip subnet address of the mac forced forwarding entry."
        ::= { macFFEntry 2 }

        macFFIpMaskBits OBJECT-TYPE
        SYNTAX  INTEGER
        MAX-ACCESS  not-accessible
        STATUS  current
        DESCRIPTION
                     	"The ip subnet mask bits(1-30) of the mac forced forwarding entry."
        ::= { macFFEntry 3 }

        macFFGateway OBJECT-TYPE
        SYNTAX  IpAddress
        MAX-ACCESS  read-write
        STATUS  current
        DESCRIPTION
                     	"The gateway of the mac forced forwarding entry."
        ::= { macFFEntry 4 }

        macFFRowStatus OBJECT-TYPE
        SYNTAX  RowStatus
        MAX-ACCESS  read-create
        STATUS  current
        DESCRIPTION
                     	"The status of the mac forced forwarding entry."

        ::= { macFFEntry 5 }


END
